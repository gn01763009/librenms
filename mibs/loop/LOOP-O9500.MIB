--======================================================================--
--  Loop Telecommunication International, Inc.                          --
--  Copyright (c) 2008-2015. All rights reserved.                       --
--======================================================================--

--======================================================================--
-- MIB definition of Loop-O9500                                         --
--                                                                      --
-- Version V3.17.01  12/14/2020                                         --
--======================================================================--

 
        L-O9500-Private   DEFINITIONS ::= BEGIN




IMPORTS
    enterprises, Counter, IpAddress
        FROM RFC1155-SMI
    DisplayString
        FROM RFC1213-MIB
    Integer32, Counter32
        FROM SNMPv2-SMI
    TRAP-TYPE
        FROM RFC-1215
    OBJECT-TYPE
        FROM RFC-1212
    NOTIFICATION-TYPE
        FROM SNMPv2-SMI;

--           NoYes  ::= INTEGER {
--                      no(1),
--                      yes(2),
--                      not-available(3)
--                  }


    UnitID ::= INTEGER {
        unit-1(1),
        unit-2(2),
        unit-3(3),
        unit-4(4),
        unit-5(5),
        unit-6(6),
        unit-7(7),
        unit-8(8),
        unit-9(9),
        unit-10(10),
        unit-11(11),
        unit-12(12),
        unit-13(13),
        unit-14(14),
        unit-15(15),
        unit-16(16),
        unit-17(17),
        unit-18(18),
        unit-19(19),
        unit-20(20),
        unit-INBAND(21),
        te-mapper(26),
        none(254),
        idle(255)
    }

    RealUnitID ::= INTEGER {
        unit-1(1),
        unit-2(2),
        unit-3(3),
        unit-4(4),
        unit-11(11),
        unit-12(12),
        unit-13(13),
        unit-14(14),
        unit-15(15),
        unit-16(16)
    }

    CardID ::= INTEGER {
        xcu1-w(1),
        xcu2-e(2),
        unit-1(3),
        unit-2(4),
        unit-3(5),
        unit-4(6),
        unit-5(7),
        unit-6(8),
        unit-7(9),
        unit-8(10),
        unit-9(11),
        unit-10(12),
        unit-11(13),
        unit-12(14),
        unit-13(15),
        unit-14(16),
        unit-15(17),
        unit-16(18),
        unit-17(19),
        unit-18(20),
        unit-19(21),
        unit-20(22),
        pwr1(23),
        pwr2(24),
        conn(25),
        te-mapper-loVT(26),
        te-mapper-line(27)
    }

    -- Chassis slot definition
    ChassisSlot ::= INTEGER {
        working(1),
        standby(2),
        unit1(3),
        unit2(4),
        unit3(5),
        unit4(6),
        unit11(13),
        unit12(14),
        unit13(15),
        unit14(16),
        unit15(17),
        unit16(18)
    }


    LSSlotID ::= INTEGER {
        slot-11(11),
        slot-12(12),
        slot-13(13),
        slot-14(14),
        slot-15(15),
        slot-16(16)
--                        slot-17(17),
--                        slot-18(18),
--                        slot-19(19),
--                        slot-20(20)
    }

    LSmapSlot ::= INTEGER {
        slot-11(11),
        slot-12(12),
        slot-13(13),
        slot-14(14),
        slot-15(15),
        slot-16(16),
--                        slot-17(17),
--                        slot-18(18),
--                        slot-19(19),
--                        slot-20(20),
        slot-inband(21),
        slot-virtualTE1(23)
    }

    XcuNum ::= INTEGER {
        xcu1-w(1),
        xcu2-e(2)
    }

    PortNum ::= INTEGER {
        port-1(1),
        port-2(2)
    }

    PortID ::= INTEGER {
        port-1(1),
        port-2(2),
        port-3(3),
        port-4(4),
        port-5(5),
        port-6(6),
        port-7(7),
        port-8(8),
        port-9(9),
        port-10(10),
        port-11(11),
        port-12(12),
        port-13(13),
        port-14(14),
        port-15(15),
        port-16(16),
        port-17(17),
        port-18(18),
        port-19(19),
        port-20(20),
        port-21(21),
        port-22(22),
        port-23(23),
        port-24(24),
        port-25(25),
        port-26(26),
        port-27(27),
        port-28(28),
        port-29(29),
        port-30(30),
        port-31(31),
        port-32(32),
        port-33(33),
        port-34(34),
        port-35(35),
        port-36(36),
        port-37(37),
        port-38(38),
        port-39(39),
        port-40(40),
        port-41(41),
        port-42(42),
        port-43(43),
        port-44(44),
        port-45(45),
        port-46(46),
        port-47(47),
        port-48(48),
        port-49(49),
        port-50(50),
        port-51(51),
        port-52(52),
        port-53(53),
        port-54(54),
        port-55(55),
        port-56(56),
        port-57(57),
        port-58(58),
        port-59(59),
        port-60(60),
        port-61(61),
        port-62(62),
        port-63(63),
        port-64(64),
        not-available(100),
        eth-1(101),
        eth-2(102),
        eth-3(103),
        eth-4(104),
        eth-5(105),
        eth-6(106),
        eth-7(107),
        eth-8(108),
        p1-1(111),
        p1-2(112),
        p1-3(113),
        p2-1(114),
        p2-2(115),
        p2-3(116),
        p3-1(117),
        p3-2(118),
        p3-3(119),
        p4-1(120),
        p4-2(121),
        p4-3(122),
        none(254),
        idle(255)
    }

    TsiPortID ::= INTEGER {
        port-1(1),
        port-2(2),
        port-3(3),
        port-4(4),
        port-5(5),
        port-6(6),
        port-7(7),
        port-8(8),
        port-9(9),
        port-10(10),
        port-11(11),
        port-12(12),
        port-13(13),
        port-14(14),
        port-15(15),
        port-16(16),
        port-17(17),
        port-18(18),
        port-19(19),
        port-20(20),
        port-21(21),
        port-22(22),
        port-23(23),
        port-24(24),
        port-25(25),
        port-26(26),
        port-27(27),
        port-28(28),
        not-available(100),
        none(254),
        idle(255)
    }

    Vte1ID ::= INTEGER {
        vte1(1),
        vte2(2),
        vte3(3),
        vte4(4),
        vte5(5),
        vte6(6),
        vte7(7),
        vte8(8),
        vte9(9),
        vte10(10),
        vte11(11),
        vte12(12),
        vte13(13),
        vte14(14),
        vte15(15),
        vte16(16),
        vte17(17),
        vte18(18),
        vte19(19),
        vte20(20),
        vte21(21),
        vte22(22),
        vte23(23),
        vte24(24),
        vte25(25),
        vte26(26),
        vte27(27),
        vte28(28)
    }

    ThreePortID ::= INTEGER {
        port-1(1),
        port-2(2),
        port-3(3)
    }

    FourPortID ::= INTEGER {
        port-1(1),
        port-2(2),
        port-3(3),
        port-4(4)
    }

    SixPortID ::= INTEGER {
        port-1(1),
        port-2(2),
        port-3(3),
        port-4(4),
        port-5(5),
        port-6(6)
    }

    G2PortID ::= INTEGER {
        port-1(1),
        port-3(2)
    }

    TdmoeEthIndex ::= INTEGER {
        eth-1 (1),
        eth-2 (2),
        eth-3 (3),
        eth-4 (4)
    }

    TdmoeTribPort ::= INTEGER{
        trib-1  (1),
        trib-2  (2),
        trib-3  (3),
        trib-4  (4)
    }

    TdmoeAlmTribPort ::= INTEGER{
        trib-1  (1),
        trib-2  (2),
        trib-3  (3),
        trib-4  (4),
        none    (5)
    }

    TdmoeBundleId ::= INTEGER {
        idle(1),
        bundle0(2),
        bundle1(3),
        bundle2(4),
        bundle3(5),
        bundle4(6),
        bundle5(7),
        bundle6(8),
        bundle7(9),
        bundle8(10),
        bundle9(11),
        bundle10(12),
        bundle11(13),
        bundle12(14),
        bundle13(15),
        bundle14(16),
        bundle15(17),
        bundle16(18),
        bundle17(19),
        bundle18(20),
        bundle19(21),
        bundle20(22),
        bundle21(23),
        bundle22(24),
        bundle23(25),
        bundle24(26),
        bundle25(27),
        bundle26(28),
        bundle27(29),
        bundle28(30),
        bundle29(31),
        bundle30(32),
        bundle31(33)
    }

    TdmoeBundleId2 ::= INTEGER {
        bundle0(1),
        bundle1(2),
        bundle2(3),
        bundle3(4),
        bundle4(5),
        bundle5(6),
        bundle6(7),
        bundle7(8),
        bundle8(9),
        bundle9(10),
        bundle10(11),
        bundle11(12),
        bundle12(13),
        bundle13(14),
        bundle14(15),
        bundle15(16),
        bundle16(17),
        bundle17(18),
        bundle18(19),
        bundle19(20),
        bundle20(21),
        bundle21(22),
        bundle22(23),
        bundle23(24),
        bundle24(25),
        bundle25(26),
        bundle26(27),
        bundle27(28),
        bundle28(29),
        bundle29(30),
        bundle30(31),
        bundle31(32)
    }

    WanID ::= INTEGER {
        xx(0),
        wan-1(1),
        wan-2(2),
        wan-3(3),
        wan-4(4),
        wan-5(5),
        wan-6(6),
        wan-7(7),
        wan-8(8),
        wan-9(9),
        wan-10(10),
        wan-11(11),
        wan-12(12),
        wan-13(13),
        wan-14(14),
        wan-15(15),
        wan-16(16),
        wan-17(17),
        wan-18(18),
        wan-19(19),
        wan-20(20),
        wan-21(21),
        wan-22(22),
        wan-23(23),
        wan-24(24),
        wan-25(25),
        wan-26(26),
        wan-27(27),
        wan-28(28),
        wan-29(29),
        wan-30(30),
        wan-31(31),
        wan-32(32),
        wan-33(33),
        wan-34(34),
        wan-35(35),
        wan-36(36),
        wan-37(37),
        wan-38(38),
        wan-39(39),
        wan-40(40),
        wan-41(41),
        wan-42(42),
        wan-43(43),
        wan-44(44),
        wan-45(45),
        wan-46(46),
        wan-47(47),
        wan-48(48),
        wan-49(49),
        wan-50(50),
        wan-51(51),
        wan-52(52),
        wan-53(53),
        wan-54(54),
        wan-55(55),
        wan-56(56),
        wan-57(57),
        wan-58(58),
        wan-59(59),
        wan-60(60),
        wan-61(61),
        wan-62(62),
        wan-63(63),
        wan-64(64)
    }

    TimeslotID ::= INTEGER {
        ts-1(1),
        ts-2(2),
        ts-3(3),
        ts-4(4),
        ts-5(5),
        ts-6(6),
        ts-7(7),
        ts-8(8),
        ts-9(9),
        ts-10(10),
        ts-11(11),
        ts-12(12),
        ts-13(13),
        ts-14(14),
        ts-15(15),
        ts-16(16),
        ts-17(17),
        ts-18(18),
        ts-19(19),
        ts-20(20),
        ts-21(21),
        ts-22(22),
        ts-23(23),
        ts-24(24),
        ts-25(25),
        ts-26(26),
        ts-27(27),
        ts-28(28),
        ts-29(29),
        ts-30(30),
        ts-31(31),
        ts-32(32)
    }

    LsAlarmPort ::= INTEGER {
        port-1(1),
        port-2(2),
        port-3(3),
        port-4(4),
        port-5(5),
        port-6(6),
        port-7(7),
        port-8(8),
        port-9(9),
        port-10(10),
        port-11(11),
        port-12(12),
        eth-1(101),
        eth-2(102),
        eth-3(103),
        eth-4(104),
        eth-5(105),
        eth-6(106),
        eth-7(107),
        eth-8(108),
        p1-1(111),
        p1-2(112),
        p1-3(113),
        p2-1(114),
        p2-2(115),
        p2-3(116),
        p3-1(117),
        p3-2(118),
        p3-3(119),
        p4-1(120),
        p4-2(121),
        p4-3(122),
        none(254)
    }


-- AlarmNum is defined in alarm.h

    AlarmNum ::= INTEGER {
        unknown(0),
        sys-alm-cut-off(1),
        sys-alm-power-unqp-loss(2),
        sys-alm-fan-fail(3),
        sys-alm-fan-module-uneqp(4),
        sys-alm-management(5),
        sys-alm-overheat(6),
        sys-alm-ts-sync-loss(7),
        sys-alm-log-on-off(8),
        sys-alm-sfp-uneqp(9),
        sys-alm-card-in(10),
        sys-alm-card-out(11),
        sys-alm-card-mismatch(12),
        sys-alm-port-mismatch(13),
        sys-alm-card-fail(14),
        sys-alm-card-registration(15),
        sys-alm-sncp-switch(16),
        sys-alm-msp-switch(17),
        sys-alm-trib-protection(18),
        sys-alm-xcu-takeover(19),
        sys-alm-trib-takeover(20),
        sys-alm-xcu-sync(21),
        sys-alm-sfp-tx-fail(22),
        sys-alm-sfp-rx-fail(23),
        sys-alm-sfp-temperatue(24),
        sys-alm-link-switch(25),
        sys-alm-link-id-mismatch(26),
        sys-alm-msp-sprring(27),
        sys-alm-cort-tx-err(28),
        external-alarm-1(29),
        external-alarm-2(30),
        external-alarm-3(31),
        external-alarm-4(32),
        sys-alm-trib-port-switch(33),
        sys-alm-protection(34),
        dbra-alm-protection(35),

        pi-los-alarm(36),
        rs-lof-alarm(37),
        rs-tim-alarm(38),
        ms-sd-alarm(39),
        ms-sf-alarm(40),
        ms-ais-alarm(41),
        ms-rdi-alarm(42),
        ms-rei-alarm(43),
        ms-b1-bip-alarm(44),
        ms-b2-bip-alarm(45),
        ms-rei-tca-alarm(46),
        rs-b1-bip-tca-alarm(47),
        ms-b2-bip-tca-alarm(48),

        featurePDHringAlarm(51),
        featureIPv6Alarm(52),
        featureOSPFAlarm(53),

        serialNumberMismatch(61),
        systemMismatch(62),
        systemFanNeed(63),

        au-lop-alarm(71),
        au-ais-alarm(72),
        hp-sd-alarm(73),
        hp-sf-alarm(74),
        hp-uneq-alarm(75),
        hp-plm-alarm(76),
        hp-tim-alarm(77),
        hp-rdi-p-alarm(78),
        hp-rdi-s-alarm(79),
        hp-rdi-c-alarm(80),
        hp-lom-alarm(82),
        hp-rei-alarm(83),
        hp-b3-bip-alarm(84),
        hp-rei-tca-alarm(87),
        hp-b3-bip-tca-alarm(88),

        clockHoldOver(97),
        systemStart(98),
        warmStart(99),

        tu-lop-alarm(106),
        tu-ais-alarm(107),
        lp-sd-alarm(108),
        lp-sf-alarm(109),
        lp-uneq-alarm(110),
        lp-plm-alarm(111),
        lp-tim-alarm(112),
        lp-rdi-p-alarm(113),
        lp-rdi-s-alarm(114),
        lp-rdi-c-alarm(115),
        lp-rei-b3-alarm(117),
        lp-rei-v5-alarm(118),
        lp-b3-bip-alarm(119),
        lp-v5-bip-alarm(120),
        lp-rei-b3-tca-alarm(123),
        lp-rei-v5-tca-alarm(124),
        lp-b3-bip-tca-alarm(125),
        lp-v5-bip-tca-alarm(126),

-- SONET is below, the number of offset is 100
        los-pi-alarm(136),
        lof-s-alarm(137),
        none1(138),
        sd-L-alarm(139),
        sf-L-alarm(140),
        ais-L-alarm(141),
        rdi-L-alarm(142),
        rei-L-alarm(143),
        b1-bip-s-alarm(144),
        b2-bip-L-alarm(145),
        rei-L-tca-alarm(146),
        b1-bip-s-tca-alarm(147),
        b2-bip-L-tca-alarm(148),

        lop-p-alarm(171),
        ais-p-alarm(172),
        sd-p-alarm(173),
        sf-p-alarm(174),
        uneq-p-alarm(175),
        plm-p-alarm(176),
        tim-p-alarm(177),
        rdi-p-p-alarm(178),
        rdi-s-p-alarm(179),
        rdi-c-p-alarm(180),
        lom-p-alarm(182),
        rei-p-alarm(183),
        b3-bip-p-alarm(184),
        rei-p-tca-alarm(187),
        b3-bip-p-tca-alarm(188),

        lop-v-alarm(206),
        ais-v-alarm(207),
        sd-v-alarm(208),
        sf-v-alarm(209),
        uneq-v-alarm(210),
        plm-v-alarm(211),
        tim-v-alarm(212),
        rdi-p-v-alarm(213),
        rdi-s-v-alarm(214),
        rdi-c-v-alarm(215),
        b3-rei-v-alarm(217),
        v5-rei-v-alarm(218),
        b3-bip-v-alarm(219),
        v5-bip-v-alarm(220),
        b3-rei-v-tca-alarm(223),
        v5-rei-v-tca-alarm(224),
        b3-bip-v-tca-alarm(225),
        v5-bip-v-tca-alarm(226),

-- the below is for e1t1 cards from 300
        e1t1-line-los(300),
        e1t1-line-ais(301),
        e1t1-line-uas(302),
        e1t1-line-rai-yel(303),
        e1t1-bpv-tca(304),

-- the below is for enet cards from 400
        enet-linkdown(400),
        enet-fcs-tca(401),
        enet-fifo-tca(402),
        enet-drop-fr-tca(403),

-- the below is for 4ge-eos cards from 420
        geLinkDown(420),
        geSfpTxFail(421),
        geSfpRxFail(422),
        geSfpTemperatureOverrange(423),
        geSfpVccOverrange(424),
        geSfpTxBiasOverrange(425),
        geSfpTxPowerOverrange(426),
        geSfpRxPowerOverrange(427),
        geFcsTca(430),
        geFifoTca(431),
        geDropFrTca(432),

-- the below is for 8GESW cards from 440
        ge8LinkDown(440),
        ge8SfpTxFail(441),
        ge8SfpRxFail(442),
        ge8SfpTemperatureOverrange(443),
        ge8SfpVccOverrange(444),
        ge8SfpTxBiasOverrange(445),
        ge8SfpTxPowerOverrange(446),
        ge8SfpRxPowerOverrange(447),
        ge8FcsTca(450),
        ge8FifoTca(451),
        ge8DropFrTca(452),
        ge8VCGLinkDown(455),
        ge8SFPUnequipped(456),        

-- the below is for e3t3 cards from 500
        e3t3-line-los(500),
        e3t3-line-ais(501),
        e3t3-line-uas(502),
        e3t3-line-rai-yell(503),
        e3t3-line-lof(504),
        e3t3-line-idle(505),
        e3t3-line-p-c-bits(506),
        e3t3-line-fas(556),

-- the below is for e3t3-m13 cards from 600
        e3t3-m13-ais(600),

-- the below is for 7fom cards from 700
        fom7-line-los(700),
        fom7-line-lof(701),
        fom7-line-rai(702),
        fom7-line-uas(703),
        fom7-e1t1-ais(750),

-- the below is for te-mapper from 1000
        ds0-sncp-alm-protection(991),

        tem-tu-lop-alarm(1001),
        tem-tu-ais-alarm(1002),
        tem-lp-uneq-alarm(1003),
        tem-lp-plm-alarm(1004),
        tem-lp-tim-alarm(1005),
        tem-lp-rdi-p-alarm(1006),
        tem-lp-rdi-s-alarm(1007),
        tem-lp-rdi-c-alarm(1008),
        tem-lp-v5-rei-alarm(1009),
        tem-lp-v5-bip-alarm(1010),

        tem-tca-lp-v5-rei-alarm(1014),
        tem-tca-lp-v5-bip-alarm(1015),

        tem-lop-v-alarm(1021),
        tem-ais-v-alarm(1022),
        tem-uneq-v-alarm(1023),
        tem-plm-v-alarm(1024),
        tem-tim-v-alarm(1025),
        tem-rdi-p-v-alarm(1026),
        tem-rdi-s-v-alarm(1027),
        tem-rdi-c-v-alarm(1028),
        tem-v5-rei-v-alarm(1029),
        tem-v5-bip-v-alarm(1030),

        tem-line-lof-alarm(1041),
        tem-line-ais-alarm(1042),
        tem-line-rai-yel-alarm(1043),

        tem-tca-line-es-alarm(1051),
        tem-tca-line-ses-alarm(1052),
        tem-tca-line-uas-alarm(1053),

-- the below is for low-speed cards from 1000

        e1-rai(1121),
        e1-ais(1122),
        e1-los(1123),
        e1-lof(1124),
        e1-bpv(1125),
        e1-es(1126),
        e1-uas(1127),
        e1-css(1128),
        ais-ins(1129),
        e1-tcpa(1130),

        t1-yel(1141),
        t1-ais(1142),
        t1-los(1143),
        t1-lof(1144),
        t1-bpv(1145),
        t1-es(1146),
        t1-uas(1147),
        t1-css(1148),
        t1-tcpa(1150),

        gshdsl-htuc-los-loop1(1201),
        gshdsl-htuc-los-loop2(1202),
        gshdsl-htur-los-loop1(1203),
        gshdsl-htur-los-loop2(1204),
        gshdsl-htuc-e1t1-los-lof(1205),
        gshdsl-htur-e1t1-los-lof(1206),
        gshdsl-htuc-es-15m-loop1(1207),
        gshdsl-htuc-es-15m-loop2(1208),
        gshdsl-htur-es-15m-loop1(1209),
        gshdsl-htur-es-15m-loop2(1210),
        gshdsl-htuc-e1t1-es-15m(1211),
        gshdsl-htur-e1t1-es-15m(1212),
        gshdsl-htuc-ses-15m-loop1(1213),
        gshdsl-htuc-ses-15m-loop2(1214),
        gshdsl-htur-ses-15m-loop1(1215),
        gshdsl-htur-ses-15m-loop2(1216),
        gshdsl-htuc-e1t1-ses-15m(1217),
        gshdsl-htur-e1t1-ses-15m(1218),
        gshdsl-htuc-es-24h-loop1(1219),
        gshdsl-htuc-es-24h-loop2(1220),
        gshdsl-htur-es-24h-loop1(1221),
        gshdsl-htur-es-24h-loop2(1222),
        gshdsl-htuc-e1t1-es-24h(1223),
        gshdsl-htur-e1t1-es-24h(1224),
        gshdsl-htuc-ses-24h-loop1(1225),
        gshdsl-htuc-ses-24h-loop2(1226),
        gshdsl-htur-ses-24h-loop1(1227),
        gshdsl-htur-ses-24h-loop2(1228),
        gshdsl-htuc-e1t1-ses-24h(1229),
        gshdsl-htur-e1t1-ses-24h(1230),
        gshdsl-sealing-current(1231),
        gshdsl-mclk-loss(1232),
        gshdsl-htuc-dte-rts(1233),
        gshdsl-htur-dte-rts(1234),
        gshdsl-htuc-dte-extclk(1235),
        gshdsl-htur-dte-extclk(1236),
        gshdsl-dying-gasp-alarm(1237),
        gshdsl-loop-attenu-alarm(1238),
        gshdsl-low-noise-margin(1239),
        gshdsl-htur-link-down(1240),

        lan1-link-down(1301),
        lan2-link-down(1302),
        lan3-link-down(1303),
        lan4-link-down(1304),
        lan5-link-down(1305),
        lan6-link-down(1306),
        lan7-link-down(1307),
        lan8-link-down(1308),

        ocudp-los(1361),
        ocudp-oos(1362),
        ocudp-es (1365),
        ocudp-ses(1366),
        ocudp-uas(1367),
        ocudp-loopbk(1368),
        ocudp-test(1369),
        ocudp-lof(1370),

        lso-los(1401),
        lso-yel(1402),
        lso-es(1403),
        lso-ses(1404),
        lso-uas(1405),

        tdmoe-arp-Lost(1431),
        tdmoe-rx-Lost(1432),
        tdmoe-loss-of-bundle(1433),
        tdmoe-jit-buf-underrun(1434),
        tdmoe-jit-buf-overrun(1435),
        tdmoe-eth1-link-down(1436),
        tdmoe-eth2-link-down(1437),
        tdmoe-eth3-link-down(1438),
        tdmoe-eth4-link-down(1439),
        tdmoe-sfp1-tx-power-high(1440),
        tdmoe-sfp2-tx-power-high(1441),
        tdmoe-sfp1-tx-power-low(1442),
        tdmoe-sfp2-tx-power-low(1443),
        tdmoe-sfp1-rx-power-high(1444),
        tdmoe-sfp2-rx-power-high(1445),
        tdmoe-sfp1-rx-power-low(1446),
        tdmoe-sfp2-rx-power-low(1447),
        tdmoe-sfp1-tx-bias-high(1448),
        tdmoe-sfp2-tx-bias-high(1449),
        tdmoe-sfp1-tx-bias-low(1450),
        tdmoe-sfp2-tx-bias-low(1451),
        tdmoe-bp-pri-hb-lost(1452),
        tdmoe-bp-sec-hb-lost(1453),
        tdmoe-bp-bundle-sw-to-pri(1454),
        tdmoe-bp-bundle-sw-to-sec(1455),
        tdmoe-bundle-l-bit(1456),
        tdmoe-bundle-r-bit(1457),


        dte-unsync(1501),
        x50-unsync(1502),

        dte-ext-clk-loss(1511),
        dte-rts-loss(1512),
        dte-remote-alarm(1513),

        rts-loss(1521),
        lolc(1522),
        loch(1523),
        cre(1524),
        g703-los(1601),

        dc-n1-p1(1701),
        dc-n1-p2(1702),
        dc-n1-p3(1703),
        dc-n1-p4(1704),
        dc-n2-p1(1705),
        dc-n2-p2(1706),
        dc-n2-p3(1707),
        dc-n2-p4(1708),

        fomOptLocalLof(1801),
        fomOptLocalLos(1802),
        fomOptLocalRai(1803),
        fomOptRemoteLof(1804),
        fomOptRemoteLos(1805),
        fomOptLocalEs(1806),
        fomOptLocalSes(1807),
        fomOptLocalUas(1808),
        fomE1LocalLof(1817),
        fomE1RemoteLof(1818),
        fomE1LocalEs(1819),
        fomE1LocalSes(1820),
        fomE1LocalUas(1821),
        fomE1LocalBpv(1822),

        ttaInputTrigger(1901),
        ttaOutputTrigger(1902),
        ttaRoundTripTimeRange(1903),
        ttaLocalChannelLost(1904),
        ttaRemoteChannelLost(1905),
        ttaIRIGLoss(1906),
        ttaTestTrigger(1907),
        ttaTestResponse(1908),

        wan1LinkDown(2001),
        wan2LinkDown(2002),
        wan3LinkDown(2003),
        wan4LinkDown(2004),
        wan5LinkDown(2005),
        wan6LinkDown(2006),
        wan7LinkDown(2007),
        wan8LinkDown(2008),
        wan9LinkDown(2009),
        wan10LinkDown(2010),
        wan11LinkDown(2011),
        wan12LinkDown(2012),
        wan13LinkDown(2013),
        wan14LinkDown(2014),
        wan15LinkDown(2015),
        wan16LinkDown(2016),
        wan17LinkDown(2017),
        wan18LinkDown(2018),
        wan19LinkDown(2019),
        wan20LinkDown(2020),
        wan21LinkDown(2021),
        wan22LinkDown(2022),
        wan23LinkDown(2023),
        wan24LinkDown(2024),
        wan25LinkDown(2025),
        wan26LinkDown(2026),
        wan27LinkDown(2027),
        wan28LinkDown(2028),
        wan29LinkDown(2029),
        wan30LinkDown(2030),
        wan31LinkDown(2031),
        wan32LinkDown(2032),
        wan33LinkDown(2033),
        wan34LinkDown(2034),
        wan35LinkDown(2035),
        wan36LinkDown(2036),
        wan37LinkDown(2037),
        wan38LinkDown(2038),
        wan39LinkDown(2039),
        wan40LinkDown(2040),
        wan41LinkDown(2041),
        wan42LinkDown(2042),
        wan43LinkDown(2043),
        wan44LinkDown(2044),
        wan45LinkDown(2045),
        wan46LinkDown(2046),
        wan47LinkDown(2047),
        wan48LinkDown(2048),
        wan49LinkDown(2049),
        wan50LinkDown(2050),
        wan51LinkDown(2051),
        wan52LinkDown(2052),
        wan53LinkDown(2053),
        wan54LinkDown(2054),
        wan55LinkDown(2055),
        wan56LinkDown(2056),
        wan57LinkDown(2057),
        wan58LinkDown(2058),
        wan59LinkDown(2059),
        wan60LinkDown(2060),
        wan61LinkDown(2061),
        wan62LinkDown(2062),
        wan63LinkDown(2063),
        wan64LinkDown(2064),

        unknown-alarm(9999)
    }

    AlmStatus ::= INTEGER {
        cleared(1),
        active(2),
        abs(3),
        disabled(4),
        to-primary(5),
        to-secondary(6),
        portDisabled(7),
        not-available(100)
    }

    Severity ::= INTEGER {
        critical(1),
        major(2),
        minor(3),
        information(4),
        not-available(100)
    }

    LsAlarmSeverity ::= INTEGER {
        disable(1),
        major(2),
        critical(3),
        minor(4)
    }

    LsAlarmSeverityDisp ::= INTEGER {
        major(1),
        critical(2),
        minor(3),
        indication(4),
        clear(5),
        na(6)
    }

    CardModel ::= INTEGER {
        xcu(1),
        e1t1(2),
        e3t3(4),
        b155-622(6),
        power(7),
        connect-card(8),
        enet-sw(10),
        enet(12),
        e1-75ohm(13),
        fom7(14),
        e3t3m13(15),
        geEos(16),
        geEos622(18),
        b2g5(19),
        unknown(20),
        ge8eos2g5(25),
        ge8eos622(26),
        te-mapper(99),
-- LS card
        rs232-8(102),
        oct-rt-b(103),
        ls-optical(109),
        em(110),
        fxs(111),
        fxo(113),
        magneto(116),
        ocudp8(117),
        quad-e1(118),
        quad-t1(119),
        dte-a(122),
        gshdsl-4(123),
        gshdsl-2(124),
        g703(125),
        dry-contact(128),
        fom1(129),
        conference(137),
        octDte(138),
        triE1(139),
        triT1(140),
        tdmoe(143),
        oct-dbra(144),
        rs232a(148),
        tta(150),
        dte6(151),
        v35-a(190),
        x21-a(191),
        v36-a(192),
        rs422-a(193),
        eia530-rs449-a(194),
        empty(254),
        other(255)
    }

    RegModel ::= INTEGER {
        xcu(1),
        e1(2),
        t1(3),
        e3(4),
        t3(5),
        stm4(6),
        stm1(7),
        oc12(8),
        oc3(9),
        enet-sw(10),
        enet(12),
        e1-75ohm(13),
        fom7(14),
        t3-m13(15),
        geEos(16),
        geEos622(18),
        stm16(19),
        oc48(21),
        ge8eos2g5(25),
        ge8eos622(26),
        te-mapper(99),
-- LS card
        rs232-8(102),
        oct-rt-b(103),
        ls-optical(109),
        em(110),
        fxs(111),
        fxo(113),
        magneto(116),
        ocudp8(117),
        quad-e1(118),
        quad-t1(119),
        dte-a(122),
        gshdsl-4(123),
        gshdsl-2(124),
        g703(125),
        dry-contact(128),
        fom1(129),
        conference(137),
        octDte(138),
        triE1(139),
        triT1(140),
        tdmoe(143),
        oct-dbra(144),
        rs232a(148),
        tta(150),
        dte6(151),
        v35-a(190),
        x21-a(191),
        v36-a(192),
        rs422-a(193),
        eia530-rs449-a(194),
        empty(254)
    }

    MsgLen  ::= INTEGER {
        null(1),
        len-16-BYTE-space(2),
--                        len-64-BYTE-space(3),
        len-16-BYTE-null(4),
--                        len-64-BYTE-null(5),
        len-1-BYTE(6)
    }

    HoMappingType ::= INTEGER {
        vc4-sts3c(2),
        three-au3-sts1(3),
        au4tug3(4)
    }

    LoMappingType ::= INTEGER {
        tu3(2),
        au3-sts1(3),
        tu11-vt15(4),
        tu12-vt2(5),
        bypass(6)
    }

    Au4Au3Type  ::= INTEGER {
        no-ho-map(1),
--        vc4(2),
        vc4-sts3c(2),
        au3-sts1c(3),
        au4-sts3c(4),
        not-available(100)
    }

    Tu1xVtxType ::= INTEGER {
        no-lo-map(1),
        tu3(2),
--        c3(3),
        c3-sts1(3),
        tu11-vt15(4),
        tu12-vt2(5),
        bypass(6),
        not-available(100)
    }

    NewXcModel ::= INTEGER {
        e1(1),
        t1(2),
        e3(3),
        t3(4),
        stm4(5),
        stm1(6),
        oc12(7),
        oc3(8),
        enet-sw(9),
        enet(11),
        fom7(13),
        t3-m13(14),
        geEos(15),
        geEos622(17),
        stm16(18),
        oc48(20),
        xcu(21),
        te-mapper(22),
        ge8eos2g5(24),
        ge8eos622(25),
        not-available(100),
        na(255)
    }

    XcSetErrCode ::= INTEGER {
        success(1),
        fail(2),
        please-select-index-or-number-within-range(3),
        source-must-be-ADM-mode(4),
        destination-must-be-non-ADM-mode(5),
        used-for-protection-already(6),
        please-register-card-first(7),
        ethernet-to-PDH-XC-not-allowed(8),
        mismatched-granularity(9),
        not-enough-free-channel-or-mismatched-granularity(10),
        channel-count-over-range(11),
        function-not-supported(12),
        mapping-not-allowed(13),
        exceed-backplane-bandwidth(14),
        please-wait-till-card-registration-completed(15),
        must-select-not-available-for-all-unused-parameters(16),
        uni-directional-XC-not-allowed-in-LCAS-mode(17),
        e1-to-t1-XC-not-allowed(18)
    }

    XcDelErrCode ::= INTEGER {
        success(1),
        fail(2),
        please-select-index-or-number-within-range(3),
        source-must-be-ADM-mode(4),
        destination-must-be-non-ADM-mode(5),
        used-for-protection-already(6),
        please-register-card-first(7),
        ethernet-to-PDH-XC-not-allowed(8),
        mismatched-granularity(9),
        not-enough-free-channel-or-mismatched-granularity(10),
        channel-count-over-range(11),
        function-not-supported(12),
        mapping-not-allowed(13),
        exceed-backplane-bandwidth(14),
        please-wait-till-card-registration-completed(15),
        must-select-not-available-for-all-unused-parameters(16),
        uni-directional-XC-not-allowed-in-LCAS-mode(17),
        e1-to-t1-XC-not-allowed(18)
    }

    XcType ::= INTEGER {
        uni-xc(1),
        bi-xc(2),
        pp-add-drop(5),
        not-available(100)
    }

    XcMap ::= INTEGER {
        map-1(1),
        map-2(2),
        not-available(100)
    }

    XcSlot ::= INTEGER {
        xcu1-w(1),
        xcu2-e(2),
        unit-1(3),
        unit-2(4),
        unit-3(5),
        unit-4(6),
        te-mapper(11),
        not-available(100)
    }

    ChannelNum ::= INTEGER {
        channel-1(1),
        channel-2(2),
        channel-3(3),
        channel-4(4),
        channel-5(5),
        channel-6(6),
        channel-7(7),
        channel-8(8),
        channel-9(9),
        channel-10(10),
        channel-11(11),
        channel-12(12),
        channel-13(13),
        channel-14(14),
        channel-15(15),
        channel-16(16),
        channel-17(17),
        channel-18(18),
        channel-19(19),
        channel-20(20),
        channel-21(21),
        channel-22(22),
        channel-23(23),
        channel-24(24),
        channel-25(25),
        channel-26(26),
        channel-27(27),
        channel-28(28),
        channel-29(29),
        channel-30(30),
        channel-31(31),
        channel-32(32),
        channel-33(33),
        channel-34(34),
        channel-35(35),
        channel-36(36),
        channel-37(37),
        channel-38(38),
        channel-39(39),
        channel-40(40),
        channel-41(41),
        channel-42(42),
        channel-43(43),
        channel-44(44),
        channel-45(45),
        channel-46(46),
        channel-47(47),
        channel-48(48),
        channel-49(49),
        channel-50(50),
        channel-51(51),
        channel-52(52),
        channel-53(53),
        channel-54(54),
        channel-55(55),
        channel-56(56),
        channel-57(57),
        channel-58(58),
        channel-59(59),
        channel-60(60),
        channel-61(61),
        channel-62(62),
        channel-63(63),
        channel-64(64),
        not-available(100)
    }

    Aug1Sts3Num ::= INTEGER {
        aug1-sts3-1(1),
        aug1-sts3-2(2),
        aug1-sts3-3(3),
        aug1-sts3-4(4),
        not-available(100)
    }

    Vc3Sts1Num ::= INTEGER {
        vc3-sts1-1(1),
        vc3-sts1-2(2),
        vc3-sts1-3(3),
        not-available(100)
    }

    Vc1xVtxNum ::= INTEGER {
        vc1x-vtx-1(1),
        vc1x-vtx-2(2),
        vc1x-vtx-3(3),
        vc1x-vtx-4(4),
        vc1x-vtx-5(5),
        vc1x-vtx-6(6),
        vc1x-vtx-7(7),
        vc1x-vtx-8(8),
        vc1x-vtx-9(9),
        vc1x-vtx-10(10),
        vc1x-vtx-11(11),
        vc1x-vtx-12(12),
        vc1x-vtx-13(13),
        vc1x-vtx-14(14),
        vc1x-vtx-15(15),
        vc1x-vtx-16(16),
        vc1x-vtx-17(17),
        vc1x-vtx-18(18),
        vc1x-vtx-19(19),
        vc1x-vtx-20(20),
        vc1x-vtx-21(21),
        vc1x-vtx-22(22),
        vc1x-vtx-23(23),
        vc1x-vtx-24(24),
        vc1x-vtx-25(25),
        vc1x-vtx-26(26),
        vc1x-vtx-27(27),
        vc1x-vtx-28(28),
        not-available(100)
    }

    TU1xVtxNum ::= INTEGER {
        tu1x-vtx-1(1),
        tu1x-vtx-2(2),
        tu1x-vtx-3(3),
        tu1x-vtx-4(4),
        tu1x-vtx-5(5),
        tu1x-vtx-6(6),
        tu1x-vtx-7(7),
        tu1x-vtx-8(8),
        tu1x-vtx-9(9),
        tu1x-vtx-10(10),
        tu1x-vtx-11(11),
        tu1x-vtx-12(12),
        tu1x-vtx-13(13),
        tu1x-vtx-14(14),
        tu1x-vtx-15(15),
        tu1x-vtx-16(16),
        tu1x-vtx-17(17),
        tu1x-vtx-18(18),
        tu1x-vtx-19(19),
        tu1x-vtx-20(20),
        tu1x-vtx-21(21),
        tu1x-vtx-22(22),
        tu1x-vtx-23(23),
        tu1x-vtx-24(24),
        tu1x-vtx-25(25),
        tu1x-vtx-26(26),
        tu1x-vtx-27(27),
        tu1x-vtx-28(28),
        not-available(100)
    }

    VcgPortNum ::= INTEGER {
        wan1-GE(1),
        wan2-FE(2),
        wan3-FE(3),
        wan4-FE(4),
        wan5-FE(5),
        wan6-FE(6),
        wan7-FE(7),
        wan8-FE(8),
        wan9-FE(9)
    }

    LanPortNum ::= INTEGER {
        lan1-GE(1),
        lan2-FE(2),
        lan3-FE(3),
        lan4-FE(4),
        lan5-FE(5),
        lan6-FE(6),
        lan7-FE(7),
        lan8-FE(8),
        lan9-FE(9)
    }

    SwPortNum ::= INTEGER {
        wan1-GE(1),
        wan2-FE(2),
        wan3-FE(3),
        wan4-FE(4),
        wan5-FE(5),
        wan6-FE(6),
        wan7-FE(7),
        wan8-FE(8),
        wan9-FE(9),
        lan1-GE(10),
        lan2-FE(11),
        lan3-FE(12),
        lan4-FE(13),
        lan5-FE(14),
        lan6-FE(15),
        lan7-FE(16),
        lan8-FE(17),
        lan9-FE(18)
    }

    LoopbackType ::= INTEGER {
        no-loopback(1),
        local-loopback(2),
        payload-loopback(3),
        line-loopback(4)
    }

    SncpUserCmd ::= INTEGER {
        clear(1),
        force-switch-to-primary(2),
        force-switch-to-secondary(3),
        manual-switch-to-primary(4),
        manual-switch-to-secondary(5),
        lockout-of-protection(6),
        not-available(100)
    }

    LoPathPerfAnomalyType ::= INTEGER {
        rei(1),
        bip(2)
    }

    LedStatusType ::= INTEGER {
        off(1),
        green(2),
        red(3),
        amber(4),
        flash-green(5),
        flash-red(6),
        flash-amber(7),
        green-red-flash(8),
        none(100)
    }

    NiNum  ::= INTEGER {
        none(1),
        lan(2),
        xcu1-dcc1(3),
        xcu1-dcc2(4),
        xcu2-dcc1(5),
        xcu2-dcc2(6),
        trib1-dcc1(7),
        trib1-dcc2(8),
        trib2-dcc1(9),
        trib2-dcc2(10),
        trib3-dcc1(11),
        trib3-dcc2(12),
        trib4-dcc1(13),
        trib4-dcc2(14),
-- In-band
        in-band-1(15),
        in-band-2(16),
        in-band-3(17),
        in-band-4(18),
        in-band-5(19),
        in-band-6(20),
        in-band-7(21),
        in-band-8(22),
        in-band-9(23),
        in-band-10(24),
        in-band-11(25),
        in-band-12(26),
        in-band-13(27),
        in-band-14(28),
        in-band-15(29),
        in-band-16(30)
    }

    NiIndex  ::= INTEGER {
        lan(1),
        xcu1-dcc1(2),
        xcu1-dcc2(3),
        xcu2-dcc1(4),
        xcu2-dcc2(5),
        trib1-dcc1(6),
        trib1-dcc2(7),
        trib2-dcc1(8),
        trib2-dcc2(9),
        trib3-dcc1(10),
        trib3-dcc2(11),
        trib4-dcc1(12),
        trib4-dcc2(13),
        in-band-1(14),
        in-band-2(15),
        in-band-3(16),
        in-band-4(17),
        in-band-5(18),
        in-band-6(19),
        in-band-7(20),
        in-band-8(21),
        in-band-9(22),
        in-band-10(23),
        in-band-11(24),
        in-band-12(25),
        in-band-13(26),
        in-band-14(27),
        in-band-15(28),
        in-band-16(29)
    }

    NiMode ::= INTEGER {
        disable(1),
        bridge(2),
        router(3)

    }

    SsmABCD ::= INTEGER {
        ssm0000(1),
        ssm0001(2),
        ssm0010(3),
        ssm0011(4),
        ssm0100(5),
        ssm0101(6),
        ssm0110(7),
        ssm0111(8),
        ssm1000(9),
        ssm1001(10),
        ssm1010(11),
        ssm1011(12),
        ssm1100(13),
        ssm1101(14),
        ssm1110(15),
        ssm1111(16)
    }

    GeVcgPort ::= INTEGER {
        wan1(1),
        wan2(2),
        wan3(3),
        wan4(4)
    }

    GeLanPort ::= INTEGER {
        lan1(1),
        lan2(2),
        lan3(3),
        lan4(4)
    }

    Ge8LanPort ::= INTEGER {
        lan1(1),
        lan2(2),
        lan3(3),
        lan4(4),
        lan5(5),
        lan6(6),
        lan7(7),
        lan8(8)
    }

    Ge8SwPort ::= INTEGER {
        wan1(1),
        wan2(2),
        wan3(3),
        wan4(4),
        lan1(5),
        lan2(6),
        lan3(7),
        lan4(8),
        lan5(9),
        lan6(10),
        lan7(11),
        lan8(12),
        vcg1(13),
        vcg2(14),
        vcg3(15),
        vcg4(16),
        vcg5(17),
        vcg6(18),
        vcg7(19),
        vcg8(20),
        vcg9(21),
        vcg10(22),
        vcg11(23),
        vcg12(24),
        vcg13(25),
        vcg14(26),
        vcg15(27),
        vcg16(28),
        vcg17(29),
        vcg18(30),
        vcg19(31),
        vcg20(32),
        vcg21(33),
        vcg22(34),
        vcg23(35),
        vcg24(36),
        vcg25(37),
        vcg26(38),
        vcg27(39),
        vcg28(40),
        vcg29(41),
        vcg30(42),
        vcg31(43),
        vcg32(44),
        vcg33(45),
        vcg34(46),
        vcg35(47),
        vcg36(48),
        vcg37(49),
        vcg38(50),
        vcg39(51),
        vcg40(52),
        vcg41(53),
        vcg42(54),
        vcg43(55),
        vcg44(56),
        vcg45(57),
        vcg46(58),
        vcg47(59),
        vcg48(60)
    }

    GeVcgNum ::= INTEGER {
        vcg1(1),
        vcg2(2),
        vcg3(3),
        vcg4(4),
        vcg5(5),
        vcg6(6),
        vcg7(7),
        vcg8(8),
        vcg9(9),
        vcg10(10),
        vcg11(11),
        vcg12(12),
        vcg13(13),
        vcg14(14),
        vcg15(15),
        vcg16(16),
        vcg17(17),
        vcg18(18),
        vcg19(19),
        vcg20(20),
        vcg21(21),
        vcg22(22),
        vcg23(23),
        vcg24(24),
        vcg25(25),
        vcg26(26),
        vcg27(27),
        vcg28(28),
        vcg29(29),
        vcg30(30),
        vcg31(31),
        vcg32(32),
        vcg33(33),
        vcg34(34),
        vcg35(35),
        vcg36(36),
        vcg37(37),
        vcg38(38),
        vcg39(39),
        vcg40(40),
        vcg41(41),
        vcg42(42),
        vcg43(43),
        vcg44(44),
        vcg45(45),
        vcg46(46),
        vcg47(47),
        vcg48(48)
    }

    GeCAASPortID ::= INTEGER {
        port-1(1),
        port-2(2),
        port-3(3),
        port-4(4),
        port-5(5),
        port-6(6),
        port-7(7),
        port-8(8),
        port-9(9),
        port-10(10),
        port-11(11),
        port-12(12),
        port-13(13),
        port-14(14),
        port-15(15),
        port-16(16),
        port-17(17),
        port-18(18),
        port-19(19),
        port-20(20),
        port-21(21),
        port-22(22),
        port-23(23),
        port-24(24),
        port-25(25),
        port-26(26),
        port-27(27),
        port-28(28),
        port-29(29),
        port-30(30),
        port-31(31),
        port-32(32),
        port-33(33),
        port-34(34),
        port-35(35),
        port-36(36),
        port-37(37),
        port-38(38),
        port-39(39),
        port-40(40),
        port-41(41),
        port-42(42),
        port-43(43),
        port-44(44),
        port-45(45),
        port-46(46),
        port-47(47),
        port-48(48),
        port-49(49),
        port-50(50),
        port-51(51),
        port-52(52),
        port-53(53),
        port-54(54),
        port-55(55),
        port-56(56),
        port-57(57),
        port-58(58),
        port-59(59),
        port-60(60),
        port-61(61),
        port-62(62),
        port-63(63),
        port-64(64),
        not-available(100),
        vcg1(101),
        vcg2(102),
        vcg3(103),
        vcg4(104),
        vcg5(105),
        vcg6(106),
        vcg7(107),
        vcg8(108),
        vcg9(109),
        vcg10(110),
        vcg11(111),
        vcg12(112),
        vcg13(113),
        vcg14(114),
        vcg15(115),
        vcg16(116),
        vcg17(117),
        vcg18(118),
        vcg19(119),
        vcg20(120),
        vcg21(121),
        vcg22(122),
        vcg23(123),
        vcg24(124),
        vcg25(125),
        vcg26(126),
        vcg27(127),
        vcg28(128),
        vcg29(129),
        vcg30(130),
        vcg31(131),
        vcg32(132),
        vcg33(133),
        vcg34(134),
        vcg35(135),
        vcg36(136),
        vcg37(137),
        vcg38(138),
        vcg39(139),
        vcg40(140),
        vcg41(141),
        vcg42(142),
        vcg43(143),
        vcg44(144),
        vcg45(145),
        vcg46(146),
        vcg47(147),
        vcg48(148)
    }

loopTelecom 	OBJECT IDENTIFIER ::= { enterprises 823 }
loop-O9500 	OBJECT IDENTIFIER ::= { loopTelecom 9500 }
    system              OBJECT IDENTIFIER  ::= { loop-O9500   1  }
    b155-622-card       OBJECT IDENTIFIER  ::= { loop-O9500   2  }
    hdE1-card              OBJECT IDENTIFIER  ::= { loop-O9500   3  }
    hdT1-card              OBJECT IDENTIFIER  ::= { loop-O9500   4  }
    enet-card           OBJECT IDENTIFIER  ::= { loop-O9500   5  }
    e3-card             OBJECT IDENTIFIER  ::= { loop-O9500   6  }
    t3-card             OBJECT IDENTIFIER  ::= { loop-O9500   7  }
    fom7-card           OBJECT IDENTIFIER  ::= { loop-O9500   8  }
    ge8EosCard          OBJECT IDENTIFIER  ::= { loop-O9500  13  }
-- LS card
    dte-card            OBJECT IDENTIFIER  ::= { loop-O9500  105  }
    x50-card            OBJECT IDENTIFIER  ::= { loop-O9500  106  }
--        mdsl-card           OBJECT IDENTIFIER  ::= { loop-O9500  111  }
    em-card             OBJECT IDENTIFIER  ::= { loop-O9500  112  }
    fxs-card            OBJECT IDENTIFIER  ::= { loop-O9500  113  }
    fxo-card            OBJECT IDENTIFIER  ::= { loop-O9500  116  }
    mag-card            OBJECT IDENTIFIER  ::= { loop-O9500  117  }
    ocudp8Card          OBJECT IDENTIFIER  ::= { loop-O9500  118  }
    qe1-card            OBJECT IDENTIFIER  ::= { loop-O9500  121  }
    qt1-card            OBJECT IDENTIFIER  ::= { loop-O9500  122  }
    g703-card           OBJECT IDENTIFIER  ::= { loop-O9500  123  }
    gdsl2-card          OBJECT IDENTIFIER  ::= { loop-O9500  126  }
    gdsl4-card          OBJECT IDENTIFIER  ::= { loop-O9500  127  }
    dc-card             OBJECT IDENTIFIER  ::= { loop-O9500  128  }
    fom1card            OBJECT IDENTIFIER  ::= { loop-O9500  129  }
    ls-optical-card     OBJECT IDENTIFIER  ::= { loop-O9500  131  }
    oct-rt-b-card       OBJECT IDENTIFIER  ::= { loop-O9500  133  }
    conference-card     OBJECT IDENTIFIER  ::= { loop-O9500  138  }
    triE1card           OBJECT IDENTIFIER  ::= { loop-O9500  139  }
    triT1card           OBJECT IDENTIFIER  ::= { loop-O9500  140  }
    tdmoe-card          OBJECT IDENTIFIER  ::= { loop-O9500  151  }
    oct-dbra-card       OBJECT IDENTIFIER  ::= { loop-O9500  152  }
    octDte-card         OBJECT IDENTIFIER  ::= { loop-O9500  153  }
    rs232a-card         OBJECT IDENTIFIER  ::= { loop-O9500  157  }
    tta-card            OBJECT IDENTIFIER  ::= { loop-O9500  159  }
    dte6-card           OBJECT IDENTIFIER  ::= { loop-O9500  160  }
    cda6-card           OBJECT IDENTIFIER  ::= { loop-O9500  161  }


--======================================================================--
--======================================================================--
--  system MIB
--      unitModelTable           OBJECT IDENTIFIER ::= { system 1 }
--      systemInformationTable   OBJECT IDENTIFIER ::= { system 2 }
--      systemLedTable           OBJECT IDENTIFIER ::= { system 3 }
--      unitRegisterTable        OBJECT IDENTIFIER ::= { system 4 }
--      alarmSetupTable          OBJECT IDENTIFIER ::= { system 5 }
--         systemSetupTable         OBJECT IDENTIFIER ::= { alarmSetupTable 1 }
--         sdh-sonetAlarmTable      OBJECT IDENTIFIER ::= { alarmSetupTable 2 }
--             cPHYTable             OBJECT IDENTIFIER ::= { sdh-sonetAlarmTable 1 }
--                   cPHYMaskTable                OBJECT IDENTIFIER ::= { cPHYTable 1 }
--                   cPHYRelayTable               OBJECT IDENTIFIER ::= { cPHYTable 2 }
--                   cPHYSvrityTable              OBJECT IDENTIFIER ::= { cPHYTable 3 }
--             cRS-SectionTable        OBJECT IDENTIFIER ::= { sdh-sonetAlarmTable 2 }
--                   cRS-SectionMaskTable           OBJECT IDENTIFIER ::= { cRS-SectionTable 1 }
--                   cRS-SectionRelayTable          OBJECT IDENTIFIER ::= { cRS-SectionTable 2 }
--                   cRS-SectionSvrityTable        OBJECT IDENTIFIER ::= { cRS-SectionTable 3 }
--             cMS-LineTable        OBJECT IDENTIFIER ::= { sdh-sonetAlarmTable 3 }
--                   cMS-LineMaskTable           OBJECT IDENTIFIER ::= { cMS-LineTable 1 }
--                   cMS-LineRelayTable          OBJECT IDENTIFIER ::= { cMS-LineTable 2 }
--                   cMS-LineSvrityTable       OBJECT IDENTIFIER ::= { cMS-LineTable 3 }
--             cHo-STSPathTable  OBJECT IDENTIFIER ::= { sdh-sonetAlarmTable 4 }
--                   cHo-STSMaskTable     OBJECT IDENTIFIER ::= { cHo-STSPathTable 1 }
--                   cHo-STSRelayTable    OBJECT IDENTIFIER ::= { cHo-STSPathTable 2 }
--                   cHo-STSSvrityTable OBJECT IDENTIFIER ::= { cHo-STSPathTable 3 }
--             cLo-VTPathTable   OBJECT IDENTIFIER ::= { sdh-sonetAlarmTable 5 }
--                   cLo-VTMaskTable      OBJECT IDENTIFIER ::= { cLo-VTPathTable 1 }
--                   cLo-VTRelayTable     OBJECT IDENTIFIER ::= { cLo-VTPathTable 2 }
--                   cLo-VTSvrityTable  OBJECT IDENTIFIER ::= { cLo-VTPathTable 3 }
--         externalAlmTable          OBJECT IDENTIFIER ::= { alarmSetupTable 3 }
--         alarmSetupHexTable        OBJECT IDENTIFIER ::= { alarmSetupTable 4 }
--      currentAlarmStatusTable  OBJECT IDENTIFIER ::= { system 6 }
--             cPHYCurrStTable             OBJECT IDENTIFIER ::= { currentAlarmStatusTable 1 }
--                   cPHYStatusTable             OBJECT IDENTIFIER ::= { cPHYCurrStTable 1 }
--                   cPHYCountTable              OBJECT IDENTIFIER ::=  { cPHYCurrStTable 2 }
--             cRS-SectionCurrStTable        OBJECT IDENTIFIER ::= { currentAlarmStatusTable 2 }
--                   cRS-SectionStatusTable        OBJECT IDENTIFIER ::= { cRS-SectionCurrStTable 1 }
--                   cRS-SectionCountTable         OBJECT IDENTIFIER ::= { cRS-SectionCurrStTable 2 }
--             cMS-LineCurrStTable        OBJECT IDENTIFIER ::= { currentAlarmStatusTable 3 }
--                   cMS-LineStatusTable        OBJECT IDENTIFIER ::= { cMS-LineCurrStTable 1 }
--                   cMS-LineCountTable         OBJECT IDENTIFIER ::= {  cMS-LineCurrStTable 2 }
--             cHo-STSPathCurrStTable  OBJECT IDENTIFIER ::= { currentAlarmStatusTable 4 }
--                   cHo-STSPathStatusTable          OBJECT IDENTIFIER ::= { cHo-STSPathCurrStTable 1 }
--                   cHo-STSPathCountTable           OBJECT IDENTIFIER ::= { cHo-STSPathCurrStTable 2 }
--             cLo-VTPathCurrStTable   OBJECT IDENTIFIER ::= { currentAlarmStatusTable 5 }
--                   cLo-VTPathStatusTable           OBJECT IDENTIFIER ::= { cLo-VTPathCurrStTable 1 }
--                   cLo-VTPathCountTable            OBJECT IDENTIFIER ::=  { cLo-VTPathCurrStTable 2 }
--             alarmStatusHexTable     OBJECT IDENTIFIER ::= { currentAlarmStatusTable 6 }
--      alarmQueueTable         OBJECT IDENTIFIER  ::= { system 7 }
--      currentActiveAlarmTable OBJECT IDENTIFIER  ::= { system 8 }
--      systemXcTable           OBJECT IDENTIFIER  ::= { system 9 }
--         systemXcCreateTable     OBJECT IDENTIFIER ::= { systemXcTable 1 }
--         systemXcDeleteTable     OBJECT IDENTIFIER ::= { systemXcTable 2 }
--         systemXcDisplayTable    OBJECT IDENTIFIER ::= { systemXcTable 3 }
--         systemXcMapModifyTable  OBJECT IDENTIFIER ::= { systemXcTable 4 }
--         systemXcSummaryHexTab   OBJECT IDENTIFIER ::= { systemXcTable 5 }
--         new-systemXcSncpTsaTable     OBJECT IDENTIFIER ::= { systemXcTable 6 }
--         new-sysXcClrXcuPortTable  OBJECT IDENTIFIER ::= { systemXcTable 7 }
--         new-systemXcDisplayTable     OBJECT IDENTIFIER ::= { systemXcTable 8 }
--      commandControlTable     OBJECT IDENTIFIER  ::= { system 10 }
--      sysNetIfTable           OBJECT IDENTIFIER  ::= { system 11 }
--      timingSourceTable       OBJECT IDENTIFIER  ::= { system 12 }
--      pathGranularityTable    OBJECT IDENTIFIER  ::= { system 13 }
--      systemModeTable         OBJECT IDENTIFIER  ::= { system 14 }
--      systemProtectionTable   OBJECT IDENTIFIER  ::= { system 15 }
--                alsTable                          OBJECT IDENTIFIER  ::= { system 16 }
--      sdsfAlarmThresholdTable OBJECT IDENTIFIER  ::= { system 17 }
--      insertAisAlarmTable     OBJECT IDENTIFIER  ::= { system 18 }
--      overheadSetupTable      OBJECT IDENTIFIER  ::= { system 19 }
--      xcuLoopbackTable                OBJECT IDENTIFIER  ::= { system 20 }
--      diagnosticsTable        OBJECT IDENTIFIER  ::= { system 21 }
--      powerTable              OBJECT IDENTIFIER  ::= { system 22 }
--      fanTable                OBJECT IDENTIFIER  ::= { system 23 }

--      bridgeSpanningTreeTable OBJECT IDENTIFIER  ::= { system 24 }
--         rstpRootTable           OBJECT IDENTIFIER ::= { bridgeSpanningTreeTable 1 }
--         rstpBridgeTable         OBJECT IDENTIFIER ::= { bridgeSpanningTreeTable 2 }
--         rstpPortTable           OBJECT IDENTIFIER ::= { bridgeSpanningTreeTable 3 }
--      networkInterfaceTable   OBJECT IDENTIFIER  ::= { system 25 }
--      staticRouteTable        OBJECT IDENTIFIER  ::= { system 26 }
--      sntpSetupTable          OBJECT IDENTIFIER  ::= { system 27 }
--      dhcpInformationTable    OBJECT IDENTIFIER  ::= { system 28 }
--      perfThresholdTable      OBJECT IDENTIFIER  ::= { system 29 }
--      perfControlTable        OBJECT IDENTIFIER  ::= { system 30 }
--      perfDisplayTable        OBJECT IDENTIFIER  ::= { system 31 }
--      systemLogTable          OBJECT IDENTIFIER  ::= { system 32 }
--      xcuInfomationTable      OBJECT IDENTIFIER  ::= { system 33 }
--      dccChannelTable         OBJECT IDENTIFIER  ::= { system 34 }
--      trapEnableTable         OBJECT IDENTIFIER  ::= { system 35 }
--      handWavingLedTable      OBJECT IDENTIFIER  ::= { system 36 }
--      xcuSncpApsTab           OBJECT IDENTIFIER  ::= { system 37 }
--      xcuMspApsTab            OBJECT IDENTIFIER  ::= { system 38 }
--      xcuCustomerInfoTab      OBJECT IDENTIFIER  ::= { system 39 }
--      fileTransferTable       OBJECT IDENTIFIER  ::= { system 40 }
--      t3M13EnableTab          OBJECT IDENTIFIER  ::= { system 41 }
--      new-systemModeTable     OBJECT IDENTIFIER  ::= { system 42 }
--      new-sysProtectionTable  OBJECT IDENTIFIER  ::= { system 43 }
--      new-xcuSncpApsTab       OBJECT IDENTIFIER  ::= { system 44 }
--      radiusSetupTable        OBJECT IDENTIFIER  ::= { system 45 }
--      featureActivation       OBJECT IDENTIFIER  ::= { system 46 }
--      overheadConnection      OBJECT IDENTIFIER  ::= { system 47 }
--      consoleTelnetUser       OBJECT IDENTIFIER  ::= { system 48 }
--IPv6
--      v6networkInterfaceTable OBJECT IDENTIFIER  ::= { system 51 }
--      v6staticRouteTable      OBJECT IDENTIFIER  ::= { system 52 }
--      ospfDisplayTable        OBJECT IDENTIFIER  ::= { system 53 }
--         areaDisplayTab             OBJECT IDENTIFIER ::= { ospfDisplayTable 1 }
--         borderRouterTab            OBJECT IDENTIFIER ::= { ospfDisplayTable 2 }
--         interfaceDisplayTab        OBJECT IDENTIFIER ::= { ospfDisplayTable 3 }
--         routeDisplayTab            OBJECT IDENTIFIER ::= { ospfDisplayTable 4 }
--         neighborDisplayTab         OBJECT IDENTIFIER ::= { ospfDisplayTable 5 }
--      ospfSetupTable          OBJECT IDENTIFIER  ::= { system 54 }
--         areaSetupTab               OBJECT IDENTIFIER ::= { ospfSetupTable 1 }
--         routerIdSetupTab           OBJECT IDENTIFIER ::= { ospfSetupTable 2 }
--         ospfInterfaceSetupTab      OBJECT IDENTIFIER ::= { ospfSetupTable 3 }
--IPv6

--      softawareInfoTable      OBJECT IDENTIFIER  ::= { system 60 }
--      xcuPortEnableTable      OBJECT IDENTIFIER  ::= { system 61 }
--      hdCardPortEnableTable   OBJECT IDENTIFIER  ::= { system 62 }

-- LS function
--      tsiFunction             OBJECT IDENTIFIER  ::= { system 101 }
--      channelMap              OBJECT IDENTIFIER  ::= { system 102 }
--      pdhRingProtection       OBJECT IDENTIFIER  ::= { system 103 }
--      qe1PairProtection       OBJECT IDENTIFIER  ::= { system 104 }
--      lsLedStatus             OBJECT IDENTIFIER  ::= { system 105 }
--      lsBertTable             OBJECT IDENTIFIER  ::= { system 106 }
--      ds0sncpProtection       OBJECT IDENTIFIER  ::= { system 107 }
--      remDevUpgradeTable      OBJECT IDENTIFIER  ::= { system 108 }
--======================================================================================--
--  B155-622-card MIB Tree
--======================================================================================--
--      b155-622GranularityTab           OBJECT IDENTIFIER  ::= { b155-622-card 1 }
--      b155-622OverheadTable            OBJECT IDENTIFIER  ::= { b155-622-card 2 }
--      b155-622DccChannelTab            OBJECT IDENTIFIER  ::= { b155-622-card 3 }
--      b155-622ProtectionTab            OBJECT IDENTIFIER  ::= { b155-622-card 4 }
--      b155-622MspApsCmdTab             OBJECT IDENTIFIER  ::= { b155-622-card 5 }
--      b155-622MspStatusTab             OBJECT IDENTIFIER  ::= { b155-622-card 6 }
--      b155-622AlarmSetupTable          OBJECT IDENTIFIER  ::= { b155-622-card 7 }
--          bPHYTable              OBJECT IDENTIFIER  ::= { b155-622AlarmSetupTable 1 }
--                bPHYMaskTable                 OBJECT IDENTIFIER  ::= { bPHYTable 1 }
--                bPHYRelayTable                OBJECT IDENTIFIER  ::= { bPHYTable 2 }
--                bPHYSvrityTable               OBJECT IDENTIFIER  ::= { bPHYTable 3 }
--          bRS-SectionTable         OBJECT IDENTIFIER  ::= { b155-622AlarmSetupTable 2 }
--                bRS-SectionMaskTable          OBJECT IDENTIFIER  ::= { bRS-SectionTable 1 }
--                bRS-SectionRelayTable         OBJECT IDENTIFIER  ::= { bRS-SectionTable 2 }
--                bRS-SectionSvrityTable        OBJECT IDENTIFIER  ::= { bRS-SectionTable 3 }
--          bMS-LineTable         OBJECT IDENTIFIER  ::= { b155-622AlarmSetupTable 3 }
--                bMS-LineMaskTable             OBJECT IDENTIFIER  ::= { bMS-LineTable 1 }
--                bMS-LineRelayTable            OBJECT IDENTIFIER  ::= { bMS-LineTable 2 }
--                bMS-LineSvrityTable           OBJECT IDENTIFIER  ::= { bMS-LineTable 3 }
--          bHo-STSPathTable   OBJECT IDENTIFIER  ::= { b155-622AlarmSetupTable 4 }
--                bHo-STSMaskTable              OBJECT IDENTIFIER  ::= { bHo-STSPathTable 1 }
--                bHo-STSRelayTable             OBJECT IDENTIFIER  ::= { bHo-STSPathTable 2 }
--                bHo-STSSvrityTable            OBJECT IDENTIFIER  ::= { bHo-STSPathTable 3 }
--          bLo-VTPathTable       OBJECT IDENTIFIER  ::= { b155-622AlarmSetupTable 5 }
--                bLo-VTMaskTable               OBJECT IDENTIFIER  ::= { bLo-VTPathTable 1 }
--                bLo-VTRelayTable              OBJECT IDENTIFIER  ::= { bLo-VTPathTable 2 }
--                bLo-VTSvrityTable             OBJECT IDENTIFIER  ::= { bLo-VTPathTable 3 }
--         b155-622alarmSetupHexTab          OBJECT IDENTIFIER ::= { b155-622AlarmSetupTable 6 }
--      b155-622CurrAlmStTable           OBJECT IDENTIFIER::= { b155-622-card 8 }
--      b155-622CurrActAlmTable          OBJECT IDENTIFIER  ::= { b155-622-card 9 }
--      b155-622SfSdThreshTab            OBJECT IDENTIFIER  ::= { b155-622-card 10 }
--      b155-622InsertAisAlmTab          OBJECT IDENTIFIER  ::= { b155-622-card 11 }
--      b155-622SfpInfoTab               OBJECT IDENTIFIER  ::= { b155-622-card 12 }
--      b155-622PerfThreshTab            OBJECT IDENTIFIER  ::= { b155-622-card 13 }
--      b155-622PerfControlTab           OBJECT IDENTIFIER  ::= { b155-622-card 14 }
--      b155-622PerfDisplayTab           OBJECT IDENTIFIER  ::= { b155-622-card 15 }
--      b155-622CmdControlTab            OBJECT IDENTIFIER  ::= { b155-622-card 16 }
--      b155-622DiagnosticsTab           OBJECT IDENTIFIER  ::= { b155-622-card 17 }
--      b155-622LoopbackTab              OBJECT IDENTIFIER  ::= { b155-622-card 18 }
--      b155-622XcDisplayTab             OBJECT IDENTIFIER  ::= { b155-622-card 19 }
--      b155-622LedStatusTab             OBJECT IDENTIFIER  ::= { b155-622-card 20 }
--      b155-622SncpApsTab               OBJECT IDENTIFIER  ::= { b155-622-card 21 }
--      b155-622AlsTable                 OBJECT IDENTIFIER  ::= { b155-622-card 22 }
--      b155-622XcSummaryHexTab          OBJECT IDENTIFIER  ::= { b155-622-card 23 }
--      b155-622ModeTab                  OBJECT IDENTIFIER  ::= { b155-622-card 24 }
--      b155-622CustomerInfoTab          OBJECT IDENTIFIER  ::= { b155-622-card 25 }
--      b155-622TPSGProtectTab           OBJECT IDENTIFIER  ::= { b155-622-card 26 }
--      new-b155-622XcDisplayTab         OBJECT IDENTIFIER  ::= { b155-622-card 27 }
--      new-b155-622SncpApsTab               OBJECT IDENTIFIER  ::= { b155-622-card 28 }
--======================================================================================--
--  e1-card MIB Tree
--======================================================================================--
-- e1Config                    OBJECT IDENTIFIER ::= { e1-card 1 }
--   e1ChLineIntfSetupTab         OBJECT IDENTIFIER ::= { e1Config 1 }
--   e1J2SigLabelSetupTab         OBJECT IDENTIFIER ::= { e1Config 2 }
--   e1CustomerInfoSetupTab       OBJECT IDENTIFIER ::= { e1Config 3 }
--   e1TPSGProtectSetupTab        OBJECT IDENTIFIER ::= { e1Config 4 }
--   e1TuMapModeSetupTab          OBJECT IDENTIFIER ::= { e1Config 5 }

-- e1Alarm                     OBJECT IDENTIFIER ::= { e1-card 2 }
--   e1AlmMaskSetupTab            OBJECT IDENTIFIER ::= { e1Alarm 1 }
--   e1AlmRelaySetupTab           OBJECT IDENTIFIER ::= { e1Alarm 2 }
--   e1AlmSeveritySetupTab        OBJECT IDENTIFIER ::= { e1Alarm 3 }
--   e1InsertAisAlmSetupTab       OBJECT IDENTIFIER ::= { e1Alarm 4 }
--   e1CurrAlmStatusTab           OBJECT IDENTIFIER ::= { e1Alarm 5 }
--   e1CurrActAlmSummaryTab       OBJECT IDENTIFIER ::= { e1Alarm 6 }

-- e1LoopbackAndDiagnostics    OBJECT IDENTIFIER ::= { e1-card 3 }
--   e1LoopbackSetupTab           OBJECT IDENTIFIER ::= { e1LoopbackAndDiagnostics 1 }
--   e1DiagnosticsSetupTab        OBJECT IDENTIFIER ::= { e1LoopbackAndDiagnostics 2 }

-- e1Performance               OBJECT IDENTIFIER ::= { e1-card 4 }
--   e1PerformanceReport          OBJECT IDENTIFIER ::= { e1Performance 1 }
--     e1LoPath-VTPathCurrTab     OBJECT IDENTIFIER ::= { e1PerformanceReport 1 }
--     e1LoPath-VTPathIntvTab     OBJECT IDENTIFIER ::= { e1PerformanceReport 2 }
--     e1LoPath-VTPath7DaysTab    OBJECT IDENTIFIER ::= { e1PerformanceReport 3 }
--     e1LoPath-VTPathTotalTab    OBJECT IDENTIFIER ::= { e1PerformanceReport 4 }
--     e1LineCurrTab              OBJECT IDENTIFIER ::= { e1PerformanceReport 5 }
--     e1LineIntervalTab          OBJECT IDENTIFIER ::= { e1PerformanceReport 6 }
--     e1Line7DaysTab             OBJECT IDENTIFIER ::= { e1PerformanceReport 7 }
--     e1LineTotalTab             OBJECT IDENTIFIER ::= { e1PerformanceReport 8 }
--   e1PerfThreshSetupTab       OBJECT IDENTIFIER ::= { e1Performance 2 }
--   e1LineMonFramerSetupTab    OBJECT IDENTIFIER ::= { e1Performance 3 }
--   e1PerfControlTab           OBJECT IDENTIFIER ::= { e1Performance 4 }

-- e1SncpApsTab                OBJECT IDENTIFIER ::= { e1-card 5 }
-- e1LedStatusTab              OBJECT IDENTIFIER ::= { e1-card 6 }
-- e1CommandControlTab         OBJECT IDENTIFIER ::= { e1-card 7 }
-- e1XcDisplayTab              OBJECT IDENTIFIER ::= { e1-card 8 }
-- e1Consolidation             OBJECT IDENTIFIER ::= { e1-card 9 }
-- new-e1XcDisplayTab          OBJECT IDENTIFIER ::= { e1-card 10 }
-- new-e1SncpApsTab            OBJECT IDENTIFIER ::= { e1-card 11 }
--======================================================================================--
--  t1-card MIB Tree
--======================================================================================--
-- t1Config                    OBJECT IDENTIFIER ::= { t1-card 1 }
--   t1ChLineIntfSetupTab         OBJECT IDENTIFIER ::= { t1Config 1 }
--   t1J2SigLabelSetupTab         OBJECT IDENTIFIER ::= { t1Config 2 }
--   t1CustomerInfoSetupTab       OBJECT IDENTIFIER ::= { t1Config 3 }
--   t1TPSGProtectSetupTab        OBJECT IDENTIFIER ::= { t1Config 4 }
--   t1TuMapModeSetupTab          OBJECT IDENTIFIER ::= { t1Config 5 }

-- t1Alarm                     OBJECT IDENTIFIER ::= { t1-card 2 }
--   t1AlmMaskSetupTab            OBJECT IDENTIFIER ::= { t1Alarm 1 }
--   t1AlmRelaySetupTab           OBJECT IDENTIFIER ::= { t1Alarm 2 }
--   t1AlmSeveritySetupTab        OBJECT IDENTIFIER ::= { t1Alarm 3 }
--   t1InsertAisAlmSetupTab       OBJECT IDENTIFIER ::= { t1Alarm 4 }
--   t1CurrAlmStatusTab           OBJECT IDENTIFIER ::= { t1Alarm 5 }
--   t1CurrActAlmSummaryTab       OBJECT IDENTIFIER ::= { t1Alarm 6 }

-- t1LoopbackAndDiagnostics    OBJECT IDENTIFIER ::= { t1-card 3 }
--   t1LoopbackSetupTab           OBJECT IDENTIFIER ::= { t1LoopbackAndDiagnostics 1 }
--   t1DiagnosticsSetupTab        OBJECT IDENTIFIER ::= { t1LoopbackAndDiagnostics 2 }

-- t1Performance               OBJECT IDENTIFIER ::= { t1-card 4 }
--   t1PerformanceReport          OBJECT IDENTIFIER ::= { t1Performance 1 }
--     t1LoPath-VTPathCurrTab     OBJECT IDENTIFIER ::= { t1PerformanceReport 1 }
--     t1LoPath-VTPathIntvTab     OBJECT IDENTIFIER ::= { t1PerformanceReport 2 }
--     t1LoPath-VTPath7DaysTab    OBJECT IDENTIFIER ::= { t1PerformanceReport 3 }
--     t1LoPath-VTPathTotalTab    OBJECT IDENTIFIER ::= { t1PerformanceReport 4 }
--     t1LineCurrTab              OBJECT IDENTIFIER ::= { t1PerformanceReport 5 }
--     t1LineIntervalTab          OBJECT IDENTIFIER ::= { t1PerformanceReport 6 }
--     t1Line7DaysTab             OBJECT IDENTIFIER ::= { t1PerformanceReport 7 }
--     t1LineTotalTab             OBJECT IDENTIFIER ::= { t1PerformanceReport 8 }
--   t1PerfThreshSetupTab       OBJECT IDENTIFIER ::= { t1Performance 2 }
--   t1LineMonFramerSetupTab    OBJECT IDENTIFIER ::= { t1Performance 3 }
--   t1PerfControlTab           OBJECT IDENTIFIER ::= { t1Performance 4 }

-- t1SncpApsTab                OBJECT IDENTIFIER ::= { t1-card 5 }
-- t1LedStatusTab              OBJECT IDENTIFIER ::= { t1-card 6 }
-- t1CommandControlTab         OBJECT IDENTIFIER ::= { t1-card 7 }
-- t1XcDisplayTab              OBJECT IDENTIFIER ::= { t1-card 8 }
-- t1Consolidation             OBJECT IDENTIFIER ::= { t1-card 9 }
-- new-t1XcDisplayTab          OBJECT IDENTIFIER ::= { t1-card 10 }
-- new-t1SncpApsTab            OBJECT IDENTIFIER ::= { t1-card 11 }
--======================================================================================--
--  ethernet-card MIB Tree
--======================================================================================--
-- enetModeTable            OBJECT IDENTIFIER ::= { enet-card 1 }
-- enetWanVcgSetupTable     OBJECT IDENTIFIER ::= { enet-card 2 }
--    enetWanVcgConfigTable    OBJECT IDENTIFIER ::= { enetWanVcgSetupTable 1 } //payload, lcas, encap type
--    enetWanVcgAlmSetupTable  OBJECT IDENTIFIER ::= { enetWanVcgSetupTable 2 }
--    enetWanVcgGfpParaTable   OBJECT IDENTIFIER ::= { enetWanVcgSetupTable 3 }
--    enetWanVcgLapsParaTable  OBJECT IDENTIFIER ::= { enetWanVcgSetupTable 4 }
--    enetWanVcgTcaTable       OBJECT IDENTIFIER ::= { enetWanVcgSetupTable 5 }
--    enetWanVcgPppParaTable   OBJECT IDENTIFIER ::= { enetWanVcgSetupTable 6 }
--    enetWanVcgBcpParaTable   OBJECT IDENTIFIER ::= { enetWanVcgSetupTable 7 }

-- enetLinkSetupTable       OBJECT IDENTIFIER ::= { enet-card 3 }
--    enetLinkdownAlmSetupTab  OBJECT IDENTIFIER ::= { enetLinkSetupTable 1 }
--    enetLinkConfigTable      OBJECT IDENTIFIER ::= { enetLinkSetupTable 2 }
--    enetCustomInfoTable      OBJECT IDENTIFIER ::= { enetLinkSetupTable 3 }
--    enetFailPropagationTab   OBJECT IDENTIFIER ::= { enetLinkSetupTable 4 }
--    enetLinkIFGTable         OBJECT IDENTIFIER ::= { enetLinkSetupTable 5 }

-- enetWanVcgSizeTable      OBJECT IDENTIFIER ::= { enet-card 4 }
-- enetAlarmStatusTable     OBJECT IDENTIFIER ::= { enet-card 5 }
-- enetPerformanceTable     OBJECT IDENTIFIER ::= { enet-card 6 }
--    enetPerfThreshTable      OBJECT IDENTIFIER  ::= { enetPerformanceTable 1 }
--    enetPerfControlTable     OBJECT IDENTIFIER  ::= { enetPerformanceTable 2 }
--    enetPerfDisplayTable     OBJECT IDENTIFIER  ::= { enetPerformanceTable 3 }

-- enetWanVcgStatisticTable OBJECT IDENTIFIER ::= { enet-card 7 }
-- enetLedStatusTable       OBJECT IDENTIFIER ::= { enet-card 8 }
-- enetSwitchTable          OBJECT IDENTIFIER ::= { enet-card 10 }
--    enetSwStatisticTable    OBJECT IDENTIFIER ::= { enetSwitchTable 1 }
--    enetVlanTable           OBJECT IDENTIFIER ::= { enetSwitchTable 2 }
--        vlanSetupTable         OBJECT IDENTIFIER ::= { enetVlanTable 1 }
--        vlanPortAssociateTbl   OBJECT IDENTIFIER ::= { enetVlanTable 2 }
--        vlanPortCfgTable       OBJECT IDENTIFIER ::= { enetVlanTable 3 }
--        vlanTPIDTable          OBJECT IDENTIFIER ::= { enetVlanTable 4 }
--    enetPortmapTable        OBJECT IDENTIFIER ::= { enetSwitchTable 3 }

--    enetRstpTable           OBJECT IDENTIFIER ::= { enetSwitchTable 4 }  //This one is for Phase I only
--        enetV1RstpBrgInfoTab    OBJECT IDENTIFIER ::= { enetRstpTable 1 }
--        enetV1RstpPortInfoTab   OBJECT IDENTIFIER ::= { enetRstpTable 2 }

--    enetStpTable           OBJECT IDENTIFIER ::= { enetSwitchTable 5 }  //The followings are for Phase II only
--        enetMstpBrgInfoTab     OBJECT IDENTIFIER ::= { enetStpTable 1 }
--        enetStpPortEnTab       OBJECT IDENTIFIER ::= { enetStpTable 2 }
--        enetMstpInstanceTab    OBJECT IDENTIFIER ::= { enetStpTable 3 }
--        enetMstpInstPriorTab   OBJECT IDENTIFIER ::= { enetStpTable 4 }
--        enetMstpPortInfoTab    OBJECT IDENTIFIER ::= { enetStpTable 5 }
--        enetRstpPortInfoTab    OBJECT IDENTIFIER ::= { enetStpTable 6 }
--        enetRstpBrgInfoTab     OBJECT IDENTIFIER ::= { enetStpTable 7 }


--    enetPortTrunkTable      OBJECT IDENTIFIER ::= { enetSwitchTable 6 }
--    enetIgmpSnoopTable      OBJECT IDENTIFIER ::= { enetSwitchTable 7 }
--        enetIgmpSnoopingTab    OBJECT IDENTIFIER ::= { enetIgmpSnoopTable 1 }
--        enetIgmpFastLeaveTab   OBJECT IDENTIFIER ::= { enetIgmpSnoopTable 2 }
--        enetIgmpRouterPortTab  OBJECT IDENTIFIER ::= { enetIgmpSnoopTable 3 }
--        enetIgmpCrossVlanTab   OBJECT IDENTIFIER ::= { enetIgmpSnoopTable 4 }
--        enetIgmpMulticastIpTab OBJECT IDENTIFIER ::= { enetIgmpSnoopTable 5 }
--        enetIgmpMcIpRangeTab   OBJECT IDENTIFIER ::= { enetIgmpSnoopTable 6 }
--        enetIPMulticastTab     OBJECT IDENTIFIER ::= { enetIgmpSnoopTable 7 }
--    enetFlowControlTable    OBJECT IDENTIFIER ::= { enetSwitchTable 8 }

--    enetQosTable            OBJECT IDENTIFIER ::= { enetSwitchTable 9 }
--        enetQosClassOfServTab  OBJECT IDENTIFIER ::= { enetQosTable 1 }
--        enetQosAccessCtrlTab   OBJECT IDENTIFIER ::= { enetQosTable 2 }
--        enetQosTxScheduleTab   OBJECT IDENTIFIER ::= { enetQosTable 3 }
--        enetQosTxWredTab       OBJECT IDENTIFIER ::= { enetQosTable 4 }
--        enetQosRateCtrlTab     OBJECT IDENTIFIER ::= { enetQosTable 5 }
--    enetSwMACLearnTable     OBJECT IDENTIFIER ::= { enetSwitchTable 10 }

-- enetXcDisplayTable       OBJECT IDENTIFIER ::= { enet-card 11 }
-- enetCommandControlTable  OBJECT IDENTIFIER ::= { enet-card 12 }
-- enetLinkStatusTable      OBJECT IDENTIFIER ::= { enet-card 13 }
-- enetSncpApsTab           OBJECT IDENTIFIER ::= { enet-card 14 }
-- enetTPSGProtectTab       OBJECT IDENTIFIER ::= { enet-card 15 }
-- enetLcasStatusTable      OBJECT IDENTIFIER ::= { enet-card 16 }
--        enetLcasSinkStatusTab   OBJECT IDENTIFIER ::= { enetLcasStatusTable 1 }
--        enetLcasSourceStatusTab OBJECT IDENTIFIER ::= { enetLcasStatusTable 2 }
-- new-enetXcDisplayTable       OBJECT IDENTIFIER ::= { enet-card 17 }
-- new-enetSncpApsTab           OBJECT IDENTIFIER ::= { enet-card 18 }
--======================================================================================--
--  e3-card MIB Tree
--======================================================================================--
-- e3Config                    OBJECT IDENTIFIER ::= { e3-card 1 }
--   e3ChLineIntfSetupTab         OBJECT IDENTIFIER ::= { e3Config 1 }
--   e3OverheadSetup              OBJECT IDENTIFIER ::= { e3Config 2 }
--   e3CustomerInfoSetupTab       OBJECT IDENTIFIER ::= { e3Config 3 }
--   e3TPSGProtectSetupTab        OBJECT IDENTIFIER ::= { e3Config 4 }
--   e3MappingModeSetupTab        OBJECT IDENTIFIER ::= { e3Config 5 }
--   e3TPSGProtectSwitchTab       OBJECT IDENTIFIER ::= { e3Config 6 }

-- e3Alarm                     OBJECT IDENTIFIER ::= { e3-card 2 }
--   e3AlarmMask                  OBJECT IDENTIFIER ::= { e3Alarm 1 }
--   e3AlarmRelay                 OBJECT IDENTIFIER ::= { e3Alarm 2 }
--   e3AlmSeveritySetupTab        OBJECT IDENTIFIER ::= { e3Alarm 3 }
--   e3InsertAisAlmSetupTab       OBJECT IDENTIFIER ::= { e3Alarm 4 }
--   e3CurrAlmStatus              OBJECT IDENTIFIER ::= { e3Alarm 5 }
--   e3CurrActAlmSummaryTab       OBJECT IDENTIFIER ::= { e3Alarm 6 }

-- e3LoopbackAndDiagnostics    OBJECT IDENTIFIER ::= { e3-card 3 }
--   e3LoopbackSetupTab           OBJECT IDENTIFIER ::= { e3LoopbackAndDiagnostics 1 }
--   e3DiagnosticsSetupTab        OBJECT IDENTIFIER ::= { e3LoopbackAndDiagnostics 2 }

-- e3Performance               OBJECT IDENTIFIER ::= { e3-card 4 }
--   e3PerformanceReport          OBJECT IDENTIFIER ::= { e3Performance 1 }
--     e3LoPath-VTPathCurrTab     OBJECT IDENTIFIER ::= { e3PerformanceReport 1 }
--     e3LoPath-VTPathIntvTab     OBJECT IDENTIFIER ::= { e3PerformanceReport 2 }
--     e3LoPath-VTPath7DaysTab    OBJECT IDENTIFIER ::= { e3PerformanceReport 3 }
--     e3LoPath-VTPathTotalTab    OBJECT IDENTIFIER ::= { e3PerformanceReport 4 }
--     e3LineCurrTab              OBJECT IDENTIFIER ::= { e3PerformanceReport 5 }
--     e3LineIntervalTab          OBJECT IDENTIFIER ::= { e3PerformanceReport 6 }
--     e3Line7DaysTab             OBJECT IDENTIFIER ::= { e3PerformanceReport 7 }
--     e3LineTotalTab             OBJECT IDENTIFIER ::= { e3PerformanceReport 8 }
--   e3PerfThreshSetupTab       OBJECT IDENTIFIER ::= { e3Performance 2 }
--   e3LineMonFramerSetupTab    OBJECT IDENTIFIER ::= { e3Performance 3 }
--   e3PerfControlTab           OBJECT IDENTIFIER ::= { e3Performance 4 }

-- e3SncpApsTab                OBJECT IDENTIFIER ::= { e3-card 5 }
-- e3LedStatusTab              OBJECT IDENTIFIER ::= { e3-card 6 }
-- e3CommandControlTab         OBJECT IDENTIFIER ::= { e3-card 7 }
-- e3XcDisplayTab              OBJECT IDENTIFIER ::= { e3-card 8 }
-- new-e3XcDisplayTab          OBJECT IDENTIFIER ::= { e3-card 9 }
-- new-e3SncpApsTab            OBJECT IDENTIFIER ::= { e3-card 10 }

--======================================================================================--
--  t3-card MIB Tree
--======================================================================================--
-- t3Config                    OBJECT IDENTIFIER ::= { t3-card 1 }
--   t3ChLineIntfSetupTab         OBJECT IDENTIFIER ::= { t3Config 1 }
--   t3OverheadSetup              OBJECT IDENTIFIER ::= { e3Config 2 }
--   t3CustomerInfoSetupTab       OBJECT IDENTIFIER ::= { t3Config 3 }
--   t3TPSGProtectSetupTab        OBJECT IDENTIFIER ::= { t3Config 4 }
--   t3MappingModeSetupTab        OBJECT IDENTIFIER ::= { t3Config 5 }
--   t3TPSGProtectSwitchTab       OBJECT IDENTIFIER ::= { t3Config 6 }

-- t3Alarm                     OBJECT IDENTIFIER ::= { t3-card 2 }
--   t3AlarmMask                  OBJECT IDENTIFIER ::= { t3Alarm 1 }
--   t3AlarmRelay                 OBJECT IDENTIFIER ::= { t3Alarm 2 }
--   t3AlmSeveritySetupTab        OBJECT IDENTIFIER ::= { t3Alarm 3 }
--   t3InsertAisAlmSetupTab       OBJECT IDENTIFIER ::= { t3Alarm 4 }
--   t3CurrAlmStatus              OBJECT IDENTIFIER ::= { t3Alarm 5 }
--   t3CurrActAlmSummaryTab       OBJECT IDENTIFIER ::= { t3Alarm 6 }

-- t3LoopbackAndDiagnostics    OBJECT IDENTIFIER ::= { t3-card 3 }
--   t3LoopbackSetupTab           OBJECT IDENTIFIER ::= { t3LoopbackAndDiagnostics 1 }
--   t3DiagnosticsSetupTab        OBJECT IDENTIFIER ::= { t3LoopbackAndDiagnostics 2 }
--   t3M13LoopbackSetupTab        OBJECT IDENTIFIER ::= { t3LoopbackAndDiagnostics 3 }
--   t3M13DiagnosticsSetupTab     OBJECT IDENTIFIER ::= { t3LoopbackAndDiagnostics 4 }
--   t3M13RemoteLbSetupTab        OBJECT IDENTIFIER ::= { t3LoopbackAndDiagnostics 5 }

-- t3Performance               OBJECT IDENTIFIER ::= { t3-card 4 }
--   t3PerformanceReport        OBJECT IDENTIFIER ::= { t3Performance 1 }
--   t3PerfThreshSetupTab       OBJECT IDENTIFIER ::= { t3Performance 2 }
--   t3LineMonFramerSetupTab    OBJECT IDENTIFIER ::= { t3Performance 3 }
--   t3PerfControlTab           OBJECT IDENTIFIER ::= { t3Performance 4 }

-- t3SncpApsTab                OBJECT IDENTIFIER ::= { t3-card 5 }
-- t3LedStatusTab              OBJECT IDENTIFIER ::= { t3-card 6 }
-- t3CommandControlTab         OBJECT IDENTIFIER ::= { t3-card 7 }
-- t3XcDisplayTab              OBJECT IDENTIFIER ::= { t3-card 8 }
-- new-t3XcDisplayTab          OBJECT IDENTIFIER ::= { t3-card 9 }
-- new-t3SncpApsTab            OBJECT IDENTIFIER ::= { t3-card 10 }
--======================================================================================--
--  fom7-card MIB Tree
--======================================================================================--
-- fom7Config                    OBJECT IDENTIFIER ::= { fom7-card 1 }
--   fom7LoVTOverheadSetupTab       OBJECT IDENTIFIER ::= { fom7Config 1 }
--   fom7CustomerInfoSetupTab       OBJECT IDENTIFIER ::= { fom7Config 2 }
--   fom7TPSGProtectSetupTab        OBJECT IDENTIFIER ::= { fom7Config 3 }
--   fom7TPSGProtectSwitchTab       OBJECT IDENTIFIER ::= { fom7Config 4 }

-- fom7Alarm                     OBJECT IDENTIFIER ::= { fom7-card 2 }
--   fom7AlarmMaskSetupTab          OBJECT IDENTIFIER ::= { fom7Alarm 1 }
--   fom7AlarmRelaySetupTab         OBJECT IDENTIFIER ::= { fom7Alarm 2 }
--   fom7AlmSeveritySetupTab        OBJECT IDENTIFIER ::= { fom7Alarm 3 }
--   fom7InsertAisAlmSetupTab       OBJECT IDENTIFIER ::= { fom7Alarm 4 }
--   fom7CurrAlmStatusTab           OBJECT IDENTIFIER ::= { fom7Alarm 5 }
--   fom7CurrActAlmSummaryTab       OBJECT IDENTIFIER ::= { fom7Alarm 6 }
--   fom7FomStatusTab               OBJECT IDENTIFIER ::= { fom7Alarm 7 }

-- fom7Diagnostics               OBJECT IDENTIFIER ::= { fom7-card 3 }
--   fom7NEFomLbTab                 OBJECT IDENTIFIER ::= { fom7Diagnostics 1 }
--   fom7NEE1T1LbTab                OBJECT IDENTIFIER ::= { fom7Diagnostics 2 }
--   fom7NEE1T1BERTTab              OBJECT IDENTIFIER ::= { fom7Diagnostics 3 }
--   fom7FEFomLbTab                 OBJECT IDENTIFIER ::= { fom7Diagnostics 4 }
--   fom7FEE1T1LbTab                OBJECT IDENTIFIER ::= { fom7Diagnostics 5 }

-- fom7Performance               OBJECT IDENTIFIER ::= { fom7-card 4 }
--   fom7PerformanceReportTab       OBJECT IDENTIFIER ::= { fom7Performance 1 }
--   fom7PerfThreshSetupTab         OBJECT IDENTIFIER ::= { fom7Performance 2 }
--   fom7PerfControlTab             OBJECT IDENTIFIER ::= { fom7Performance 3 }

-- fom7SncpApsTab                OBJECT IDENTIFIER ::= { fom7-card 5 }
-- fom7LedStatusTab              OBJECT IDENTIFIER ::= { fom7-card 6 }
-- fom7SfpInfoTab                OBJECT IDENTIFIER ::= { fom7-card 7 }
-- fom7AlsSetupTab               OBJECT IDENTIFIER ::= { fom7-card 8 }

-- fom7CommandControlTab         OBJECT IDENTIFIER ::= { fom7-card 9 }
-- fom7XcDisplayTab              OBJECT IDENTIFIER ::= { fom7-card 10 }
-- new-fom7XcDisplayTab          OBJECT IDENTIFIER ::= { fom7-card 11 }
-- new-fom7SncpUpsrApsTab        OBJECT IDENTIFIER ::= { fom7-card 12 }
--======================================================================--
--  System MIB

--
--  unit Model Table
--
        unitModelTable  OBJECT-TYPE
            SYNTAX  SEQUENCE OF UnitModelEntry
            ACCESS  not-accessible
            STATUS  mandatory
            DESCRIPTION
                "Display unit model type, sync status,
                and unit configuration"
            ::= { system 1 }

        unitModelEntry  OBJECT-TYPE
            SYNTAX  UnitModelEntry
            ACCESS  not-accessible
            STATUS  mandatory
            DESCRIPTION
                "unit model entry"
            INDEX { ccUnitIndex }
            ::= { unitModelTable 1 }

        UnitModelEntry ::= SEQUENCE {
            ccUnitIndex                 UnitID,
            ccCardModelType             INTEGER,
            ccCurrentPortNum            INTEGER,
            ccRegisterModelType         INTEGER,
            ccRegisterPortNum           INTEGER,
            ccSwVersion                 DisplayString,
            ccRemark                    DisplayString,
            ccSerialNumber              DisplayString,
            ccCardState                 INTEGER,
            ccHwVersion                 DisplayString
        }

        ccUnitIndex  OBJECT-TYPE
            SYNTAX  UnitID
            ACCESS  read-only
            STATUS  mandatory
            DESCRIPTION
            "unit 1 to 4."
            ::= { unitModelEntry 1 }

        ccCardModelType  OBJECT-TYPE
            SYNTAX  INTEGER {
                    empty(1),
                    e1t1(2),
                    e3t3(4),
                    b155-622(6),
                    enet-sw(10),
                    enet(12),
                    e1-75ohm(13),
                    fom7(14),
                    e3t3m13(15),
                    geEos(16),
                    geEos622(18),
                    unknown(20),
                    ge8eos2g5(25),
                    ge8eos622(26),
                    b155-622-fl(56),
                    enet-sw-fl(60),
                    enet-fl(62),
                    ge8eos2g5-fl(75),
                    ge8eos622-fl(76),
-- LS card
                    v35(104),
                    em(108),
                    fxs(111),
                    fxo(112),
                    magneto(116),
                    ocudp8(117),
                    quad-e1(121),
                    quad-t1(122),
                    v35-a(125),
                    x21-a(126),
                    v36-a(127),
                    g703(128),
                    fom1(129),
                    gshdsl-2(131),
                    gshdsl-4(132),
                    rs422-a(133),
                    dry-contact(134),
                    eia530-rs449-a(137),
                    ls-optical(138),
                    conference(139),
                    oct-rt-b(140),
                    rs232-8(142),
                    triE1(148),
                    triT1(149),
                    tdmoe(151),
                    oct-dbra(152),
                    octDte(153),
                    rs232a(157),
                    tta(159),
                    dte6(160),
                    cda6(161),
                    na(255)
                }
            ACCESS  read-only
            STATUS  mandatory
            DESCRIPTION
                "unit card model type"
            ::= { unitModelEntry 2 }

        ccCurrentPortNum  OBJECT-TYPE
            SYNTAX  INTEGER
            ACCESS  read-only
            STATUS  mandatory
            DESCRIPTION
                "unit port number"
            ::= { unitModelEntry 3 }

        ccRegisterModelType  OBJECT-TYPE
            SYNTAX  INTEGER {
                    empty(1),
                    e1-no-protection(4),
                    e1-protected(5),
                    t1-no-protection(7),
                    t1-protected(8),
                    e3-no-protection(10),
                    e3-protected(11),
                    t3-no-protection(13),
                    t3-protected(14),
                    stm4-no-protection(16),
                    stm4-msp-1plus1(17),
                    stm1-no-protection(19),
                    stm1-msp-1plus1(20),
                    stm1-sncp(21),
                    oc12-msp-1plus1(23),
                    oc3-no-protection(25),
                    oc3-msp-1plus1(26),
                    oc3-sncp(27),
                    ethernet-switch-no-protection(28),
                    ethernet-switch-protected(29),
                    ethernet-no-protection(34),
                    ethernet-protected(35),
                    e1-75ohm-no-protection(37),
                    e1-75ohm-protected(38),
                    fom7-no-protection(40),
                    fom7-protected(41),
                    t3-m13-no-protection(43),
                    t3-m13-protected(44),
                    ge8eos622SwNoProtection(49),
                    ge8eos622SwProtection(50),
-- LS card
                    v35(104),
                    em(108),
                    fxs(111),
                    fxo(112),
                    magneto(116),
                    ocudp8(117),
                    quad-e1(121),
                    quad-t1(122),
                    v35-a(125),
                    x21-a(126),
                    v36-a(127),
                    g703(128),
                    fom1(129),
                    gshdsl-2(131),
                    gshdsl-4(132),
                    rs422-a(133),
                    dry-contact(134),
                    eia530-rs449-a(137),
                    ls-optical(138),
                    conference(139),
                    oct-rt-b(140),
                    rs232-8(142),
                    triE1(148),
                    triT1(149),
                    tdmoe(151),
                    oct-dbra(152),
                    octDte(153),
                    rs232a(157),
                    tta(159),
                    dte6(160),
                    cda6(161),
                    na(255)
                }
            ACCESS  read-only
            STATUS  mandatory
            DESCRIPTION
                "unit register model type"
            ::= { unitModelEntry 4 }

        ccRegisterPortNum  OBJECT-TYPE
            SYNTAX  INTEGER
            ACCESS  read-only
            STATUS  mandatory
            DESCRIPTION
                "unit port number"
            ::= { unitModelEntry 5 }

        ccSwVersion  OBJECT-TYPE
            SYNTAX  DisplayString (SIZE (0..255) )
            ACCESS  read-only
            STATUS  mandatory
            DESCRIPTION
                "unit software version"
            ::= { unitModelEntry 6 }

        ccRemark  OBJECT-TYPE
            SYNTAX  DisplayString (SIZE (0..255) )
            ACCESS  read-only
            STATUS  mandatory
            DESCRIPTION
                "unit remark"
            ::= { unitModelEntry 7 }

        ccSerialNumber  OBJECT-TYPE
            SYNTAX  DisplayString (SIZE (0..255) )
            ACCESS  read-only
            STATUS  mandatory
            DESCRIPTION
                "unit serial number"
            ::= { unitModelEntry 8 }
        ccCardState  OBJECT-TYPE
            SYNTAX  INTEGER {
                    empty(1),
                    initializing(2),
                    working(3),
                    unplugged(4),
                    failed(5),
                    unknownCard(6),
                    unregisterCard(7),
                    brandMismatch(11),
                    systemMismatch(12),
                    cardTypeMismatch(13),
                    portNumMismatch(14)
                }
            MAX-ACCESS  read-only
            STATUS  current
            DESCRIPTION
                "Card state"
            ::= { unitModelEntry 9 }
        ccHwVersion  OBJECT-TYPE
            SYNTAX  DisplayString (SIZE (0..255) )
            ACCESS  read-only
            STATUS  mandatory
            DESCRIPTION
                "unit hardware version"
            ::= { unitModelEntry 10 }

--
--  SYSTEM Information Table
--
    systemInformationTable  OBJECT IDENTIFIER ::= { system 2 }

        ccWorkingXcuSerialNumber  OBJECT-TYPE
            SYNTAX  INTEGER
            ACCESS  read-only
            STATUS  mandatory
            DESCRIPTION
                "Working XCU Serial Number"
            ::= { systemInformationTable 1 }

        ccWorkingXcuBoardVersion  OBJECT-TYPE
            SYNTAX  DisplayString (SIZE (0..255) )
            ACCESS  read-only
            STATUS  mandatory
            DESCRIPTION
                "Working XCU Mainboard Version"
            ::= { systemInformationTable 2 }

        ccWorkingXcuFwVersion  OBJECT-TYPE
            SYNTAX  DisplayString (SIZE (0..255) )
            ACCESS  read-only
            STATUS  mandatory
            DESCRIPTION
                "Working XCU firmware Version"
            ::= { systemInformationTable 3 }

        ccStandbyXcuSerialNumber  OBJECT-TYPE
            SYNTAX  INTEGER
            ACCESS  read-only
            STATUS  mandatory
            DESCRIPTION
                "Standby XCU Serial Number"
            ::= { systemInformationTable 4 }

        ccStandbyXcuBoardVersion  OBJECT-TYPE
            SYNTAX  DisplayString (SIZE (0..255) )
            ACCESS  read-only
            STATUS  mandatory
            DESCRIPTION
                "Standby XCU Mainboard Version"
            ::= { systemInformationTable 5 }

        ccStandbyXcuFwVersion  OBJECT-TYPE
            SYNTAX  DisplayString (SIZE (0..255) )
            ACCESS  read-only
            STATUS  mandatory
            DESCRIPTION
                "Standby XCU firmware Version"
            ::= { systemInformationTable 6 }

        ccTimeDate  OBJECT-TYPE
            SYNTAX  DisplayString (SIZE (0..255) )
            ACCESS  read-write
            STATUS  mandatory
            DESCRIPTION
                "Time and Date Format= hh:mm:ss mm/dd/yyyy"
            ::= { systemInformationTable 7 }

        ccXcuSync  OBJECT-TYPE
            SYNTAX  INTEGER {
                    un-sync(1),
                    sync(2),
                    waitToSync(3),
                    duringSync(4),
                    versionMismatch(5),
                    framePulseUnsync(6),
                    redundantSyncFail(7)
                }
            ACCESS  read-only
            STATUS  mandatory
            DESCRIPTION
                "XCU sync status"
            ::= { systemInformationTable 8 }

        ccXcuWorking  OBJECT-TYPE
            SYNTAX  INTEGER {
                    xcu1-w(1),
                    xcu2-e(2)
                }
            ACCESS  read-only
            STATUS  mandatory
            DESCRIPTION
                "working XCU"
            ::= { systemInformationTable 9 }

        ccOtherXcu  OBJECT-TYPE
            SYNTAX  INTEGER {
                    not-exist(1),
                    exist(2)
                }
            ACCESS  read-only
            STATUS  mandatory
            DESCRIPTION
                "other XCU exist or not"
            ::= { systemInformationTable 10 }

        ccSysSeverityLevel  OBJECT-TYPE
            SYNTAX  INTEGER {
                    critical(1),
                    major(2),
                    minor(3),
                    info(4),
                    none(5)
                }
            ACCESS  read-only
            STATUS  mandatory
            DESCRIPTION
                "highest sdh/sonet/tributary severity alarm present in the system
                (not including one-shot alarm)"
            ::= { systemInformationTable 11 }

        ccWorkingXcuCpuLoading  OBJECT-TYPE
            SYNTAX  INTEGER
            ACCESS  read-only
            STATUS  mandatory
            DESCRIPTION
                "Working XCU CPU loading"
            ::= { systemInformationTable 12 }

        ccStandbyXcuCpuLoading  OBJECT-TYPE
            SYNTAX  INTEGER
            ACCESS  read-only
            STATUS  mandatory
            DESCRIPTION
                "Standby XCU CPU loading"
            ::= { systemInformationTable 13 }

        ccWorkingXcuTemperature  OBJECT-TYPE
            SYNTAX  INTEGER
            ACCESS  read-only
            STATUS  mandatory
            DESCRIPTION
                "Working XCU CPU temperature"
            ::= { systemInformationTable 14 }

        ccStandbyXcuTemperature  OBJECT-TYPE
            SYNTAX  INTEGER
            ACCESS  read-only
            STATUS  mandatory
            DESCRIPTION
                "Standby XCU CPU temperature"
            ::= { systemInformationTable 15 }

        ccBackplaneType  OBJECT-TYPE
            SYNTAX  INTEGER {
                    bwOc12Stm4(1),
                    bwOc48Stm16(2),
                    bwOc48Stm16Fanless(3)
                }
            ACCESS  read-only
            STATUS  mandatory
            DESCRIPTION
                "Backplane type"
            ::= { systemInformationTable 16 }

        ccWestXcuName  OBJECT-TYPE
            SYNTAX  INTEGER{
                    xcu4(1),
                    xcu4FLA(2),
                    not-available(100)
                }
            ACCESS  read-only
            STATUS  mandatory
            DESCRIPTION
                "West XCU Name"
            ::= { systemInformationTable 17 }

        ccEastXcuName  OBJECT-TYPE
            SYNTAX  INTEGER{
                    xcu4(1),
                    xcu4FLA(2),
                    not-available(100)
                }
            ACCESS  read-only
            STATUS  mandatory
            DESCRIPTION
                "East XCU Name"
            ::= { systemInformationTable 18 }

        ccConsoleStatus  OBJECT-TYPE
            SYNTAX  INTEGER {
                    normal(1),
                    consoleLockout(2),
                    consoleLogin(3)
                }
            ACCESS  read-only
            STATUS  mandatory
            DESCRIPTION
                "Console status"
            ::= { systemInformationTable 19 }

        ccTelnetStatus  OBJECT-TYPE
            SYNTAX  INTEGER {
                    nosession(1),
                    telnetLockout(2),
                    telnetLogin(3)
                }
            ACCESS  read-only
            STATUS  mandatory
            DESCRIPTION
                "Telnet status"
            ::= { systemInformationTable 20 }


--
-- System Led
--
    systemLedTable  OBJECT IDENTIFIER ::= { system 3 }

        systemLedStatusTable  OBJECT-TYPE
            SYNTAX  SEQUENCE OF SystemLedEntry
            ACCESS  not-accessible
            STATUS  mandatory
            DESCRIPTION
                "Display system LED."
            ::= { systemLedTable 1 }

        systemLedEntry  OBJECT-TYPE
            SYNTAX  SystemLedEntry
            ACCESS  not-accessible
            STATUS  mandatory
            DESCRIPTION
                "System LED entry"
            INDEX { ccLedIndex }
            ::= { systemLedStatusTable 1 }

        SystemLedEntry ::= SEQUENCE {
            ccLedIndex                  INTEGER,
            ccLedName                   DisplayString(SIZE(0..20)),
            ccLedColor                  LedStatusType
        }

        ccLedIndex  OBJECT-TYPE
            SYNTAX  INTEGER (1..14)
            ACCESS  read-only
            STATUS  mandatory
            DESCRIPTION
                "system LED index"
            ::= { systemLedEntry 1 }

        ccLedName  OBJECT-TYPE
            SYNTAX  DisplayString(SIZE(0..20))
            ACCESS  read-only
            STATUS  mandatory
            DESCRIPTION
                "system LED name"
            ::= { systemLedEntry 2 }

        ccLedColor  OBJECT-TYPE
            SYNTAX  LedStatusType
            ACCESS  read-only
            STATUS  mandatory
            DESCRIPTION
                "system LED color"
            ::= { systemLedEntry 3 }

    systemLedStatusHexTable  OBJECT IDENTIFIER ::= { systemLedTable 2 }

        systemLedStatusHex  OBJECT-TYPE
            SYNTAX  OCTET STRING(SIZE(28))
            ACCESS  read-only
            STATUS  mandatory
            DESCRIPTION
                "Led status in Hex"
            ::= { systemLedStatusHexTable 1 }



--
--  Unit Register Table
--
    unitRegisterTable  OBJECT IDENTIFIER ::= { system 4 }

        ccRegisterUnit  OBJECT-TYPE
            SYNTAX  RealUnitID
            ACCESS  read-write
            STATUS  mandatory
            DESCRIPTION
                "Register Unit "
            ::= { unitRegisterTable 1 }

        ccRegisterModel  OBJECT-TYPE
            SYNTAX  INTEGER {
                    empty(1),
                    e1-no-protection(4),
                    e1-protected(5),
                    t1-no-protection(7),
                    t1-protected(8),
                    e3-no-protection(10),
                    e3-protected(11),
                    t3-no-protection(13),
                    t3-protected(14),
                    stm4-no-protection(16),
                    stm4-msp-1plus1(17),
                    stm1-no-protection(19),
                    stm1-msp-1plus1(20),
                    -- stm1-sncp(21),
                    oc12-msp-1plus1(23),
                    oc3-no-protection(25),
                    oc3-msp-1plus1(26),
                    -- oc3-sncp(27),
                    ethernet-switch-no-protection(28),
                    ethernet-switch-protected(29),
                    ethernet-no-protection(34),
                    ethernet-protected(35),
                    e1-75ohm-no-protection(37),
                    e1-75ohm-protected(38),
                    fom7-no-protection(40),
                    fom7-protected(41),
                    t3-m13-no-protection(43),
                    t3-m13-protected(44),
                    ge8eos622SwNoProtection(49),
                    ge8eos622SwProtection(50),
                    low-speed-card(101)
                }
            ACCESS  read-write
            STATUS  mandatory
            DESCRIPTION
                "Register Model"
            ::= { unitRegisterTable 2 }

        ccRegisterCmd  OBJECT-TYPE
            SYNTAX  INTEGER {
                    register(1),
                    unregister(2),
                    accept-curr-port-num(3),
                    change-protection-mode(4),
                    change-registration-mode(5)
                }
            ACCESS  read-write
            STATUS  mandatory
            DESCRIPTION
                "Register commands"
            ::= { unitRegisterTable 3 }

        ccRegisterResponse  OBJECT-TYPE
            SYNTAX  INTEGER {
                    ok(1),
                    unregister-first(2),
                    register-model-error(3),
                    none(4),
                    during-registration(5),
                    xc-existence-error(6),
                    xc-existed-on-port2-error(15)
                }
            ACCESS  read-only
            STATUS  mandatory
            DESCRIPTION
                "Register response"
            ::= { unitRegisterTable 4 }

--
-- XCU Port Loopback Control Table
--

    xcuPortLoopbackTable  OBJECT IDENTIFIER ::= { system 20 }

        xcu1Port1Loopback  OBJECT-TYPE
            SYNTAX  LoopbackType
            ACCESS  read-write
            STATUS  mandatory
            DESCRIPTION
                "XCU1-W port#1 Loopback"
            ::= { xcuPortLoopbackTable 1 }

        xcu1Port2Loopback  OBJECT-TYPE
            SYNTAX  LoopbackType
            ACCESS  read-write
            STATUS  mandatory
            DESCRIPTION
                "XCU1-W port#2 Loopback"
            ::= { xcuPortLoopbackTable 2 }

        xcu2Port1Loopback  OBJECT-TYPE
            SYNTAX  LoopbackType
            ACCESS  read-write
            STATUS  mandatory
            DESCRIPTION
                "XCU2-E port#1 Loopback"
            ::= { xcuPortLoopbackTable 3 }

        xcu2Port2Loopback  OBJECT-TYPE
            SYNTAX  LoopbackType
            ACCESS  read-write
            STATUS  mandatory
            DESCRIPTION
                "XCU2-E port#2 Loopback"
            ::= { xcuPortLoopbackTable 4 }

        xcuLoopbackTimer  OBJECT-TYPE
            SYNTAX  Counter
            ACCESS  read-write
            STATUS  mandatory
            DESCRIPTION
                "All XCU ports Loopback Timer"
            ::= { xcuPortLoopbackTable 5 }
--
--  Alarm Setup Table
--
    alarmSetupTable          OBJECT IDENTIFIER ::= { system 5 }

--
--  System Setup Table
--
        systemSetupTable  OBJECT-TYPE
            SYNTAX  SEQUENCE OF SystemSetupEntry
            ACCESS  not-accessible
            STATUS  mandatory
            DESCRIPTION
                "System alarm setup table"
            ::= { alarmSetupTable 1 }

        systemSetupEntry  OBJECT-TYPE
            SYNTAX  SystemSetupEntry
            ACCESS  not-accessible
            STATUS  mandatory
            DESCRIPTION
                "System alarm setup entry"
            INDEX { ccAlarmMaskIndex }
            ::= { systemSetupTable 1 }

        SystemSetupEntry ::= SEQUENCE {
            ccAlarmMaskIndex            INTEGER (1..30),
            ccAlarmMaskName             DisplayString (SIZE(0..40)),
            ccAlarmMaskAlm              INTEGER,
            ccAlarmMaskRelay            INTEGER,
            ccAlarmMaskSeverity         Severity,
            ccAlarmMaskRelayPeriod      INTEGER (0..86400)
        }

        ccAlarmMaskIndex  OBJECT-TYPE
            SYNTAX  INTEGER (1..30)
            ACCESS  read-only
            STATUS  mandatory
            DESCRIPTION
                "System alarm setup index"
            ::= { systemSetupEntry 1 }

        ccAlarmMaskName  OBJECT-TYPE
            SYNTAX  DisplayString (SIZE(0..40))
            ACCESS  read-only
            STATUS  mandatory
            DESCRIPTION
                "System alarm setup name"
            ::= { systemSetupEntry 2 }

        ccAlarmMaskAlm  OBJECT-TYPE
            SYNTAX  INTEGER {
                    disable(1),
                    enable(2)
                }
            ACCESS  read-write
            STATUS  mandatory
            DESCRIPTION
                "System alarm mask enable/disable"
            ::= { systemSetupEntry 3 }

        ccAlarmMaskRelay  OBJECT-TYPE
            SYNTAX  INTEGER {
                    disable(1),
                    enable(2),
                    auto(3),
                    period(4)
                }
            ACCESS  read-write
            STATUS  mandatory
            DESCRIPTION
                "System alarm relay enable/disable"
            ::= { systemSetupEntry 4 }

        ccAlarmMaskSeverity  OBJECT-TYPE
            SYNTAX  Severity
            ACCESS  read-write
            STATUS  mandatory
            DESCRIPTION
                "System alarm severity"
            ::= { systemSetupEntry 5 }

        ccAlarmMaskRelayPeriod  OBJECT-TYPE
            SYNTAX  INTEGER
            ACCESS  read-write
            STATUS  mandatory
            DESCRIPTION
                "System alarm relay period"
            ::= { systemSetupEntry 6 }

--
--  Physical Layer Alarm Table
--

    sdh-sonetAlarmTable OBJECT IDENTIFIER ::= { alarmSetupTable 2 }

--
--  Physical Layer Alarm Mask Table
--

    cPHYTable   OBJECT IDENTIFIER ::= { sdh-sonetAlarmTable 1 }

        cPHYMaskTable  OBJECT-TYPE
            SYNTAX  SEQUENCE OF PHYMaskEntry
            ACCESS  not-accessible
            STATUS  mandatory
            DESCRIPTION
                "Physical layer Alarm Mask Table"
            ::= { cPHYTable 1 }

        pHYMaskEntry  OBJECT-TYPE
            SYNTAX  PHYMaskEntry
            ACCESS  not-accessible
            STATUS  mandatory
            DESCRIPTION
                "Physical Alarm Mask entry"
            INDEX { cPHYMaskXCUindex , cPHYMaskPortindex }
            ::= { cPHYMaskTable 1 }

        PHYMaskEntry ::= SEQUENCE {
            cPHYMaskXCUindex            XcSlot,
            cPHYMaskPortindex           PortID,
            cPHYMaskLOS                 INTEGER
        }

        cPHYMaskXCUindex  OBJECT-TYPE
            SYNTAX  XcSlot
            ACCESS  read-only
            STATUS  mandatory
            DESCRIPTION
                "Alarm Mask XCU index"
            ::= { pHYMaskEntry 1 }

        cPHYMaskPortindex  OBJECT-TYPE
            SYNTAX  PortID
            ACCESS  read-only
            STATUS  mandatory
            DESCRIPTION
                "Alarm Mask Port index"
            ::= { pHYMaskEntry 2 }

        cPHYMaskLOS  OBJECT-TYPE
            SYNTAX  INTEGER {
                    disable(1),
                    enable(2)
                }
            ACCESS  read-write
            STATUS  mandatory
            DESCRIPTION
                "Alarm Mask Enable/Disable"
            ::= { pHYMaskEntry 3 }
--
--  Physical Layer Alarm Relay Table
--
        cPHYRelayTable  OBJECT-TYPE
            SYNTAX  SEQUENCE OF PHYRelayEntry
            ACCESS  not-accessible
            STATUS  mandatory
            DESCRIPTION
                "Physical layer Alarm Relay Table"
            ::= { cPHYTable 2 }

        pHYRelayEntry  OBJECT-TYPE
            SYNTAX  PHYRelayEntry
            ACCESS  not-accessible
            STATUS  mandatory
            DESCRIPTION
                "Physical Alarm entry"
            INDEX { cPHYRelayXCUindex , cPHYRelayPortindex }
            ::= { cPHYRelayTable 1 }

        PHYRelayEntry ::= SEQUENCE {
            cPHYRelayXCUindex           XcSlot,
            cPHYRelayPortindex          PortID,
            cPHYRelayLOS                INTEGER
        }

        cPHYRelayXCUindex  OBJECT-TYPE
            SYNTAX  XcSlot
            ACCESS  read-only
            STATUS  mandatory
            DESCRIPTION
                "Alarm Relay XCU index"
            ::= { pHYRelayEntry 1 }

        cPHYRelayPortindex  OBJECT-TYPE
            SYNTAX  PortID
            ACCESS  read-only
            STATUS  mandatory
            DESCRIPTION
                "Alarm Relay Port index"
            ::= { pHYRelayEntry 2 }

        cPHYRelayLOS  OBJECT-TYPE
            SYNTAX  INTEGER {
                    disable(1),
                    enable(2)
                }
            ACCESS  read-write
            STATUS  mandatory
            DESCRIPTION
                "Alarm Relay Enable/Disable"
            ::= { pHYRelayEntry 3 }

--
--  Physical Layer Alarm Severity Table
--
    cPHYSvrityTable  OBJECT IDENTIFIER ::= { cPHYTable 3 }

        cPHYSvrityLOS  OBJECT-TYPE
            SYNTAX  Severity
            ACCESS  read-write
            STATUS  mandatory
            DESCRIPTION
                "Alarm Severity Type"
            ::= { cPHYSvrityTable 1 }

--
--  RS-Section Layer Alarm Mask Table
--

    cRS-SectionTable   OBJECT IDENTIFIER ::= { sdh-sonetAlarmTable 2 }

        cRS-SectionMaskTable  OBJECT-TYPE
            SYNTAX  SEQUENCE OF RS-SectionMaskEntry
            ACCESS  not-accessible
            STATUS  mandatory
            DESCRIPTION
                "RS-Section layer Alarm Mask Table"
            ::= { cRS-SectionTable 1 }

        rS-SectionMaskEntry  OBJECT-TYPE
            SYNTAX  RS-SectionMaskEntry
            ACCESS  not-accessible
            STATUS  mandatory
            DESCRIPTION
                "RS-Section Alarm entry"
            INDEX { cRS-SectionMaskXCUindex , cRS-SectionMaskPortindex }
            ::= { cRS-SectionMaskTable 1 }

        RS-SectionMaskEntry ::= SEQUENCE {
            cRS-SectionMaskXCUindex     XcSlot,
            cRS-SectionMaskPortindex    PortID,
            cRS-SectionMaskLOF          INTEGER,
            cRS-SectionMaskBIP          INTEGER,
            cRS-SectionMaskTIM          INTEGER
        }

        cRS-SectionMaskXCUindex  OBJECT-TYPE
            SYNTAX  XcSlot
            ACCESS  read-only
            STATUS  mandatory
            DESCRIPTION
                "XCU index"
            ::= { rS-SectionMaskEntry 1 }

        cRS-SectionMaskPortindex  OBJECT-TYPE
            SYNTAX  PortID
            ACCESS  read-only
            STATUS  mandatory
            DESCRIPTION
                "Port index"
            ::= { rS-SectionMaskEntry 2 }

        cRS-SectionMaskLOF  OBJECT-TYPE
            SYNTAX  INTEGER {
                    disable(1),
                    enable(2)
                }
            ACCESS  read-write
            STATUS  mandatory
            DESCRIPTION
                "LOF Alarm Mask Enable/Disable"
            ::= { rS-SectionMaskEntry 3 }

        cRS-SectionMaskBIP  OBJECT-TYPE
            SYNTAX  INTEGER {
                    disable(1),
                    enable(2)
                }
            ACCESS  read-write
            STATUS  mandatory
            DESCRIPTION
                "BIP Alarm Mask Enable/Disable"
            ::= { rS-SectionMaskEntry 4 }

        cRS-SectionMaskTIM  OBJECT-TYPE
            SYNTAX  INTEGER {
                    disable(1),
                    enable(2)
                }
            ACCESS  read-write
            STATUS  mandatory
            DESCRIPTION
                "TIM Alarm Mask Enable/Disable"
            ::= { rS-SectionMaskEntry 5 }
--
--  RS-Section Layer Alarm Relay Table
--
        cRS-SectionRelayTable  OBJECT-TYPE
            SYNTAX  SEQUENCE OF RS-SectionRelayEntry
            ACCESS  not-accessible
            STATUS  mandatory
            DESCRIPTION
                "RS-Section layer Alarm Mask Table"
            ::= { cRS-SectionTable 2 }

        rS-SectionRelayEntry  OBJECT-TYPE
            SYNTAX  RS-SectionRelayEntry
            ACCESS  not-accessible
            STATUS  mandatory
            DESCRIPTION
                "RS-Sectionsical Alarm entry"
            INDEX { cRS-SectionRelayXCUindex , cRS-SectionRelayPortindex }
            ::= { cRS-SectionRelayTable 1 }

        RS-SectionRelayEntry ::= SEQUENCE {
            cRS-SectionRelayXCUindex    XcSlot,
            cRS-SectionRelayPortindex   PortID,
            cRS-SectionRelayLOF         INTEGER,
            cRS-SectionRelayBIP         INTEGER,
            cRS-SectionRelayTIM         INTEGER
        }

        cRS-SectionRelayXCUindex  OBJECT-TYPE
            SYNTAX  XcSlot
            ACCESS  read-only
            STATUS  mandatory
            DESCRIPTION
                "XCU index"
            ::= { rS-SectionRelayEntry 1 }

        cRS-SectionRelayPortindex  OBJECT-TYPE
            SYNTAX  PortID
            ACCESS  read-only
            STATUS  mandatory
            DESCRIPTION
                "Alarm Port index"
            ::= { rS-SectionRelayEntry 2 }

        cRS-SectionRelayLOF  OBJECT-TYPE
            SYNTAX  INTEGER {
                    disable(1),
                    enable(2)
                }
            ACCESS  read-write
            STATUS  mandatory
            DESCRIPTION
                "LOF Alarm Relay Enable/Disable"
            ::= { rS-SectionRelayEntry 3 }

        cRS-SectionRelayBIP  OBJECT-TYPE
            SYNTAX  INTEGER {
                    disable(1),
                    enable(2)
                }
            ACCESS  read-write
            STATUS  mandatory
            DESCRIPTION
                "BIP Alarm Relay Enable/Disable"
            ::= { rS-SectionRelayEntry 4 }

        cRS-SectionRelayTIM  OBJECT-TYPE
            SYNTAX  INTEGER {
                    disable(1),
                    enable(2)
                }
            ACCESS  read-write
            STATUS  mandatory
            DESCRIPTION
                "TIM Alarm Relay Enable/Disable"
            ::= { rS-SectionRelayEntry 5 }

--
--  RS-Section Layer Alarm Severity Table
--
    cRS-SectionSvrityTable  OBJECT IDENTIFIER ::= { cRS-SectionTable 3 }

        cRS-SectionSvrityLOF  OBJECT-TYPE
            SYNTAX  Severity
            ACCESS  read-write
            STATUS  mandatory
            DESCRIPTION
                "LOF Alarm Severity Selection"
            ::= { cRS-SectionSvrityTable 1 }

        cRS-SectionSvrityBIP  OBJECT-TYPE
            SYNTAX  Severity
            ACCESS  read-write
            STATUS  mandatory
            DESCRIPTION
                "BIP Alarm Severity Selection"
            ::= { cRS-SectionSvrityTable 2 }

        cRS-SectionSvrityTIM  OBJECT-TYPE
            SYNTAX  Severity
            ACCESS  read-write
            STATUS  mandatory
            DESCRIPTION
                "TIM Alarm Severity Selection"
            ::= { cRS-SectionSvrityTable 3 }

--
--  MS-Line Layer Alarm Mask Table
--

    cMS-LineTable   OBJECT IDENTIFIER ::= { sdh-sonetAlarmTable 3 }

        cMS-LineMaskTable  OBJECT-TYPE
            SYNTAX  SEQUENCE OF MS-LineMaskEntry
            ACCESS  not-accessible
            STATUS  mandatory
            DESCRIPTION
                "MS-Line layer Alarm Mask Table"
            ::= { cMS-LineTable 1 }

        mS-LineMaskEntry  OBJECT-TYPE
            SYNTAX  MS-LineMaskEntry
            ACCESS  not-accessible
            STATUS  mandatory
            DESCRIPTION
                "MS-Linesical Alarm entry"
            INDEX { cMS-LineMaskXCUindex , cMS-LineMaskPortindex }
            ::= { cMS-LineMaskTable 1 }

        MS-LineMaskEntry ::= SEQUENCE {
            cMS-LineMaskXCUindex        XcuNum,
            cMS-LineMaskPortindex       PortNum,
            cMS-LineMaskAIS             INTEGER,
            cMS-LineMaskRDI             INTEGER,
            cMS-LineMaskBIP             INTEGER,
            cMS-LineMaskREI             INTEGER,
            cMS-LineMaskSD              INTEGER,
            cMS-LineMaskSF              INTEGER
        }

        cMS-LineMaskXCUindex  OBJECT-TYPE
            SYNTAX  XcuNum
            ACCESS  read-only
            STATUS  mandatory
            DESCRIPTION
                "XCU index"
            ::= { mS-LineMaskEntry 1 }

        cMS-LineMaskPortindex  OBJECT-TYPE
            SYNTAX  PortNum
            ACCESS  read-only
            STATUS  mandatory
            DESCRIPTION
                "Port index"
            ::= { mS-LineMaskEntry 2 }

        cMS-LineMaskAIS  OBJECT-TYPE
            SYNTAX  INTEGER {
                    disable(1),
                    enable(2)
                }
            ACCESS  read-write
            STATUS  mandatory
            DESCRIPTION
                "AIS Alarm Mask Enable/Disable"
            ::= { mS-LineMaskEntry 3 }

        cMS-LineMaskRDI  OBJECT-TYPE
            SYNTAX  INTEGER {
                    disable(1),
                    enable(2)
                }
            ACCESS  read-write
            STATUS  mandatory
            DESCRIPTION
                "RDI Alarm Mask Enable/Disable"
            ::= { mS-LineMaskEntry 4 }

        cMS-LineMaskBIP  OBJECT-TYPE
            SYNTAX  INTEGER {
                    disable(1),
                    enable(2)
                }
            ACCESS  read-write
            STATUS  mandatory
            DESCRIPTION
                "BIP Alarm Mask Enable/Disable"
            ::= { mS-LineMaskEntry 5 }

        cMS-LineMaskREI  OBJECT-TYPE
            SYNTAX  INTEGER {
                    disable(1),
                    enable(2)
                }
            ACCESS  read-write
            STATUS  mandatory
            DESCRIPTION
                "REI Alarm Mask Enable/Disable"
            ::= { mS-LineMaskEntry 6 }

        cMS-LineMaskSD  OBJECT-TYPE
            SYNTAX  INTEGER {
                    disable(1),
                    enable(2)
                }
            ACCESS  read-write
            STATUS  mandatory
            DESCRIPTION
                "SD Alarm Mask Enable/Disable"
            ::= { mS-LineMaskEntry 7 }

        cMS-LineMaskSF  OBJECT-TYPE
            SYNTAX  INTEGER {
                    disable(1),
                    enable(2)
                }
            ACCESS  read-write
            STATUS  mandatory
            DESCRIPTION
                "SF Alarm Mask Enable/Disable"
            ::= { mS-LineMaskEntry 8 }
--
--  MS-Line Layer Alarm Relay Table
--
        cMS-LineRelayTable  OBJECT-TYPE
            SYNTAX  SEQUENCE OF MS-LineRelayEntry
            ACCESS  not-accessible
            STATUS  mandatory
            DESCRIPTION
                "MS-Line layer Alarm Mask Table"
            ::= { cMS-LineTable 2 }

        mS-LineRelayEntry  OBJECT-TYPE
            SYNTAX  MS-LineRelayEntry
            ACCESS  not-accessible
            STATUS  mandatory
            DESCRIPTION
                "MS-Line Alarm entry"
            INDEX { cMS-LineRelayXCUindex , cMS-LineRelayPortindex }
            ::= { cMS-LineRelayTable 1 }

        MS-LineRelayEntry ::= SEQUENCE {
            cMS-LineRelayXCUindex       XcuNum,
            cMS-LineRelayPortindex      PortNum,
            cMS-LineRelayAIS            INTEGER,
            cMS-LineRelayRDI            INTEGER,
            cMS-LineRelayBIP            INTEGER,
            cMS-LineRelayREI            INTEGER,
            cMS-LineRelaySD             INTEGER,
            cMS-LineRelaySF             INTEGER
        }

        cMS-LineRelayXCUindex  OBJECT-TYPE
            SYNTAX  XcuNum
            ACCESS  read-only
            STATUS  mandatory
            DESCRIPTION
                "XCU index"
            ::= { mS-LineRelayEntry 1 }

        cMS-LineRelayPortindex  OBJECT-TYPE
            SYNTAX  PortNum
            ACCESS  read-only
            STATUS  mandatory
            DESCRIPTION
                "Port index"
            ::= { mS-LineRelayEntry 2 }

        cMS-LineRelayAIS  OBJECT-TYPE
            SYNTAX  INTEGER {
                    disable(1),
                    enable(2)
                }
            ACCESS  read-write
            STATUS  mandatory
            DESCRIPTION
                "AIS Alarm Relay Enable/Disable"
            ::= { mS-LineRelayEntry 3 }

        cMS-LineRelayRDI  OBJECT-TYPE
            SYNTAX  INTEGER {
                    disable(1),
                    enable(2)
                }
            ACCESS  read-write
            STATUS  mandatory
            DESCRIPTION
                "RDI Alarm Relay Enable/Disable"
            ::= { mS-LineRelayEntry 4 }

        cMS-LineRelayBIP  OBJECT-TYPE
            SYNTAX  INTEGER {
                    disable(1),
                    enable(2)
                }
            ACCESS  read-write
            STATUS  mandatory
            DESCRIPTION
                "BIP Alarm Relay Enable/Disable"
            ::= { mS-LineRelayEntry 5 }

        cMS-LineRelayREI  OBJECT-TYPE
            SYNTAX  INTEGER {
                    disable(1),
                    enable(2)
                }
            ACCESS  read-write
            STATUS  mandatory
            DESCRIPTION
                "REI Alarm Relay Enable/Disable"
            ::= { mS-LineRelayEntry 6 }

        cMS-LineRelaySD  OBJECT-TYPE
            SYNTAX  INTEGER {
                    disable(1),
                    enable(2)
                }
            ACCESS  read-write
            STATUS  mandatory
            DESCRIPTION
                "SD Alarm Relay Enable/Disable"
            ::= { mS-LineRelayEntry 7 }

        cMS-LineRelaySF  OBJECT-TYPE
            SYNTAX  INTEGER {
                    disable(1),
                    enable(2)
                }
            ACCESS  read-write
            STATUS  mandatory
            DESCRIPTION
                "SF Alarm Relay Enable/Disable"
            ::= { mS-LineRelayEntry 8 }

--
--  MS-Line Layer Alarm Severity Table
--
    cMS-LineSvrityTable  OBJECT IDENTIFIER ::= { cMS-LineTable 3 }

        cMS-LinerSvrityAIS  OBJECT-TYPE
            SYNTAX  Severity
            ACCESS  read-write
            STATUS  mandatory
            DESCRIPTION
                "AIS Alarm Severity Selection"
            ::= { cMS-LineSvrityTable 1 }

        cMS-LineSvrityRDI  OBJECT-TYPE
            SYNTAX  Severity
            ACCESS  read-write
            STATUS  mandatory
            DESCRIPTION
                "RDI Alarm Severity Selection"
            ::= { cMS-LineSvrityTable 2 }

        cMS-LineSvrityBIP  OBJECT-TYPE
            SYNTAX  Severity
            ACCESS  read-write
            STATUS  mandatory
            DESCRIPTION
                "BIP Alarm Severity Selection"
            ::= { cMS-LineSvrityTable 3 }

        cMS-LineSvrityREI  OBJECT-TYPE
            SYNTAX  Severity
            ACCESS  read-write
            STATUS  mandatory
            DESCRIPTION
                "REI Alarm Severity Selection"
            ::= { cMS-LineSvrityTable 4 }

        cMS-LineSvritySD  OBJECT-TYPE
            SYNTAX  Severity
            ACCESS  read-write
            STATUS  mandatory
            DESCRIPTION
                "SD Alarm Severity Selection"
            ::= { cMS-LineSvrityTable 5 }

        cMS-LineSvritySF  OBJECT-TYPE
            SYNTAX  Severity
            ACCESS  read-write
            STATUS  mandatory
            DESCRIPTION
                "SF Alarm Severity Selection"
            ::= { cMS-LineSvrityTable 6 }

--
--  HoPath-STSPath Layer Alarm Mask Table
--

    cHo-STSPathTable   OBJECT IDENTIFIER ::= { sdh-sonetAlarmTable 4 }

        cHo-STSMaskTable  OBJECT-TYPE
            SYNTAX  SEQUENCE OF HoPath-STSPathMaskEntry
            ACCESS  not-accessible
            STATUS  mandatory
            DESCRIPTION
                "HoPath-STSPathsical layer Alarm Mask Table"
            ::= { cHo-STSPathTable 1 }

        hoPath-STSPathMaskEntry  OBJECT-TYPE
            SYNTAX  HoPath-STSPathMaskEntry
            ACCESS  not-accessible
            STATUS  mandatory
            DESCRIPTION
                "HoPath-STSPathsical Alarm entry"
            INDEX { cHo-STSMaskXCUIndex , cHo-STSMaskPortIndex , cHo-STSMaskAUG1STS3Index , cHo-STSMaskVC3STS1Index }
            ::= { cHo-STSMaskTable 1 }

        HoPath-STSPathMaskEntry ::= SEQUENCE {
            cHo-STSMaskXCUIndex         XcuNum,
            cHo-STSMaskPortIndex        PortNum,
            cHo-STSMaskAUG1STS3Index    Aug1Sts3Num,
            cHo-STSMaskVC3STS1Index     Vc3Sts1Num,
            cHo-STSMaskLOP              INTEGER,
            cHo-STSMaskAIS              INTEGER,
            cHo-STSMaskTIM              INTEGER,
            cHo-STSMaskRDI-S            INTEGER,
            cHo-STSMaskRDI-C            INTEGER,
            cHo-STSMaskRDI-P            INTEGER,
            cHo-STSMaskBIP              INTEGER,
            cHo-STSMaskREI              INTEGER,
            cHo-STSMaskPLM              INTEGER,
            cHo-STSMaskUNEQ             INTEGER,
            cHo-STSMaskLOM              INTEGER,
            cHo-STSMaskSD               INTEGER,
            cHo-STSMaskSF               INTEGER
        }

        cHo-STSMaskXCUIndex  OBJECT-TYPE
            SYNTAX  XcuNum
            ACCESS  read-only
            STATUS  mandatory
            DESCRIPTION
                "XCU1 Port-1 Optical Line Alarm Mask index"
            ::= { hoPath-STSPathMaskEntry 1 }

        cHo-STSMaskPortIndex  OBJECT-TYPE
            SYNTAX  PortNum
            ACCESS  read-only
            STATUS  mandatory
            DESCRIPTION
                "Alarm Port index"
            ::= { hoPath-STSPathMaskEntry 2 }

        cHo-STSMaskAUG1STS3Index  OBJECT-TYPE
            SYNTAX  Aug1Sts3Num
            ACCESS  read-only
            STATUS  mandatory
            DESCRIPTION
                "AUG1/STS3 index"
            ::= { hoPath-STSPathMaskEntry 3 }

        cHo-STSMaskVC3STS1Index  OBJECT-TYPE
            SYNTAX  Vc3Sts1Num
            ACCESS  read-only
            STATUS  mandatory
            DESCRIPTION
                "VC3/STS1 index"
            ::= { hoPath-STSPathMaskEntry 4 }

        cHo-STSMaskLOP  OBJECT-TYPE
            SYNTAX  INTEGER {
                    disable(1),
                    enable(2)
                }
            ACCESS  read-write
            STATUS  mandatory
            DESCRIPTION
                "LOP Alarm Mask Enable/Disable"
            ::= { hoPath-STSPathMaskEntry 5 }

        cHo-STSMaskAIS  OBJECT-TYPE
            SYNTAX  INTEGER {
                    disable(1),
                    enable(2)
                }
            ACCESS  read-write
            STATUS  mandatory
            DESCRIPTION
                "AIS Alarm Mask Enable/Disable"
            ::= { hoPath-STSPathMaskEntry 6 }

        cHo-STSMaskTIM  OBJECT-TYPE
            SYNTAX  INTEGER {
                    disable(1),
                    enable(2)
                }
            ACCESS  read-write
            STATUS  mandatory
            DESCRIPTION
                "TIM Alarm Mask Enable/Disable"
            ::= { hoPath-STSPathMaskEntry 7 }

        cHo-STSMaskRDI-S  OBJECT-TYPE
            SYNTAX  INTEGER {
                    disable(1),
                    enable(2)
                }
            ACCESS  read-write
            STATUS  mandatory
            DESCRIPTION
                "RDI-S Alarm Mask Enable/Disable"
            ::= { hoPath-STSPathMaskEntry 8 }

        cHo-STSMaskRDI-C  OBJECT-TYPE
            SYNTAX  INTEGER {
                    disable(1),
                    enable(2)
                }
            ACCESS  read-write
            STATUS  mandatory
            DESCRIPTION
                "RDI-C Alarm Mask Enable/Disable"
            ::= { hoPath-STSPathMaskEntry 9 }

        cHo-STSMaskRDI-P  OBJECT-TYPE
            SYNTAX  INTEGER {
                    disable(1),
                    enable(2)
                }
            ACCESS  read-write
            STATUS  mandatory
            DESCRIPTION
                "RDI-P Alarm Mask Enable/Disable"
            ::= { hoPath-STSPathMaskEntry 10 }

        cHo-STSMaskBIP  OBJECT-TYPE
            SYNTAX  INTEGER {
                    disable(1),
                    enable(2)
                }
            ACCESS  read-write
            STATUS  mandatory
            DESCRIPTION
                "BIP Alarm Mask Enable/Disable"
            ::= { hoPath-STSPathMaskEntry 11 }

        cHo-STSMaskREI  OBJECT-TYPE
            SYNTAX  INTEGER {
                    disable(1),
                    enable(2)
                }
            ACCESS  read-write
            STATUS  mandatory
            DESCRIPTION
                "REI Alarm Mask Enable/Disable"
            ::= { hoPath-STSPathMaskEntry 12 }

        cHo-STSMaskPLM  OBJECT-TYPE
            SYNTAX  INTEGER {
                    disable(1),
                    enable(2)
                }
            ACCESS  read-write
            STATUS  mandatory
            DESCRIPTION
                "PLM Alarm Mask Enable/Disable"
            ::= { hoPath-STSPathMaskEntry 13 }

        cHo-STSMaskUNEQ  OBJECT-TYPE
            SYNTAX  INTEGER {
                    disable(1),
                    enable(2)
                }
            ACCESS  read-write
            STATUS  mandatory
            DESCRIPTION
                "UNEQ Alarm Mask Enable/Disable"
            ::= { hoPath-STSPathMaskEntry 14 }

        cHo-STSMaskLOM  OBJECT-TYPE
            SYNTAX  INTEGER {
                    disable(1),
                    enable(2)
                }
            ACCESS  read-write
            STATUS  mandatory
            DESCRIPTION
                "LOM Alarm Mask Enable/Disable"
            ::= { hoPath-STSPathMaskEntry 15 }

        cHo-STSMaskSD  OBJECT-TYPE
            SYNTAX  INTEGER {
                    disable(1),
                    enable(2)
                }
            ACCESS  read-write
            STATUS  mandatory
            DESCRIPTION
                "SD Alarm Mask Enable/Disable"
            ::= { hoPath-STSPathMaskEntry 16 }

        cHo-STSMaskSF  OBJECT-TYPE
            SYNTAX  INTEGER {
                    disable(1),
                    enable(2)
                }
            ACCESS  read-write
            STATUS  mandatory
            DESCRIPTION
                "SF Alarm Mask Enable/Disable"
            ::= { hoPath-STSPathMaskEntry 17 }
--
--  HoPath-STSPath Layer Alarm Relay Table
--
        cHo-STSRelayTable  OBJECT-TYPE
            SYNTAX  SEQUENCE OF Ho-STSRelayEntry
            ACCESS  not-accessible
            STATUS  mandatory
            DESCRIPTION
                "HoPath-STSPath layer Alarm Mask Table"
            ::= { cHo-STSPathTable 2 }

        ho-STSRelayEntry  OBJECT-TYPE
            SYNTAX  Ho-STSRelayEntry
            ACCESS  not-accessible
            STATUS  mandatory
            DESCRIPTION
                "HoPath-STSPathsical Alarm entry"
            INDEX { cHo-STSRelayXCUIdx , cHo-STSRelayPortIdx , cHo-STSRelayAUG1STS3Idx , cHo-STSRelayVC3STS1Idx }
            ::= { cHo-STSRelayTable 1 }

        Ho-STSRelayEntry ::= SEQUENCE {
            cHo-STSRelayXCUIdx          XcuNum,
            cHo-STSRelayPortIdx         PortNum,
            cHo-STSRelayAUG1STS3Idx     Aug1Sts3Num,
            cHo-STSRelayVC3STS1Idx      Vc3Sts1Num,
            cHo-STSRelayLOP             INTEGER,
            cHo-STSRelayAIS             INTEGER,
            cHo-STSRelayTIM             INTEGER,
            cHo-STSRelayRDI-S           INTEGER,
            ccHo-STSRelayRDI-C          INTEGER,
            cHo-STSRelayRDI-P           INTEGER,
            cHo-STSRelayBIP             INTEGER,
            cHo-STSRelayREI             INTEGER,
            cHo-STSRelayPLM             INTEGER,
            cHo-STSRelayUNEQ            INTEGER,
            cHo-STSRelayLOM             INTEGER,
            cHo-STSRelaySD              INTEGER,
            cHo-STSRelaySF              INTEGER
        }

        cHo-STSRelayXCUIdx  OBJECT-TYPE
            SYNTAX  XcuNum
            ACCESS  read-only
            STATUS  mandatory
            DESCRIPTION
                "XCU index"
            ::= { ho-STSRelayEntry 1 }

        cHo-STSRelayPortIdx  OBJECT-TYPE
            SYNTAX  PortNum
            ACCESS  read-only
            STATUS  mandatory
            DESCRIPTION
                "Port index"
            ::= { ho-STSRelayEntry 2 }

        cHo-STSRelayAUG1STS3Idx  OBJECT-TYPE
            SYNTAX  Aug1Sts3Num
            ACCESS  read-only
            STATUS  mandatory
            DESCRIPTION
                "AUG1/STS3 index"
            ::= { ho-STSRelayEntry 3 }

        cHo-STSRelayVC3STS1Idx  OBJECT-TYPE
            SYNTAX  Vc3Sts1Num
            ACCESS  read-only
            STATUS  mandatory
            DESCRIPTION
                "VC3/STS1 index"
            ::= { ho-STSRelayEntry 4 }

        cHo-STSRelayLOP  OBJECT-TYPE
            SYNTAX  INTEGER {
                    disable(1),
                    enable(2)
                }
            ACCESS  read-write
            STATUS  mandatory
            DESCRIPTION
                "LOP Alarm Relay Enable/Disable"
            ::= { ho-STSRelayEntry 5 }

        cHo-STSRelayAIS  OBJECT-TYPE
            SYNTAX  INTEGER {
                    disable(1),
                    enable(2)
                }
            ACCESS  read-write
            STATUS  mandatory
            DESCRIPTION
                "AIS Alarm Relay Enable/Disable"
            ::= { ho-STSRelayEntry 6 }

        cHo-STSRelayTIM  OBJECT-TYPE
            SYNTAX  INTEGER {
                    disable(1),
                    enable(2)
                }
            ACCESS  read-write
            STATUS  mandatory
            DESCRIPTION
                "TIM Alarm Relay Enable/Disable"
            ::= { ho-STSRelayEntry 7 }

        cHo-STSRelayRDI-S  OBJECT-TYPE
            SYNTAX  INTEGER {
                    disable(1),
                    enable(2)
                }
            ACCESS  read-write
            STATUS  mandatory
            DESCRIPTION
                "RDI-S Alarm Relay Enable/Disable"
            ::= { ho-STSRelayEntry 8 }

        ccHo-STSRelayRDI-C  OBJECT-TYPE
            SYNTAX  INTEGER {
                    disable(1),
                    enable(2)
                }
            ACCESS  read-write
            STATUS  mandatory
            DESCRIPTION
                "RDI-C Alarm Relay Enable/Disable"
            ::= { ho-STSRelayEntry 9 }

        cHo-STSRelayRDI-P  OBJECT-TYPE
            SYNTAX  INTEGER {
                    disable(1),
                    enable(2)
                }
            ACCESS  read-write
            STATUS  mandatory
            DESCRIPTION
                "RDI-P Alarm Relay Enable/Disable"
            ::= { ho-STSRelayEntry 10 }

        cHo-STSRelayBIP  OBJECT-TYPE
            SYNTAX  INTEGER {
                    disable(1),
                    enable(2)
                }
            ACCESS  read-write
            STATUS  mandatory
            DESCRIPTION
                "BIP Alarm Relay Enable/Disable"
            ::= { ho-STSRelayEntry 11 }

        cHo-STSRelayREI  OBJECT-TYPE
            SYNTAX  INTEGER {
                    disable(1),
                    enable(2)
                }
            ACCESS  read-write
            STATUS  mandatory
            DESCRIPTION
                "REI Alarm Relay Enable/Disable"
            ::= { ho-STSRelayEntry 12 }

        cHo-STSRelayPLM  OBJECT-TYPE
            SYNTAX  INTEGER {
                    disable(1),
                    enable(2)
                }
            ACCESS  read-write
            STATUS  mandatory
            DESCRIPTION
                "PLM Alarm Relay Enable/Disable"
            ::= { ho-STSRelayEntry 13 }

        cHo-STSRelayUNEQ  OBJECT-TYPE
            SYNTAX  INTEGER {
                    disable(1),
                    enable(2)
                }
            ACCESS  read-write
            STATUS  mandatory
            DESCRIPTION
                "UNEQ Alarm Relay Enable/Disable"
            ::= { ho-STSRelayEntry 14 }

        cHo-STSRelayLOM  OBJECT-TYPE
            SYNTAX  INTEGER {
                    disable(1),
                    enable(2)
                }
            ACCESS  read-write
            STATUS  mandatory
            DESCRIPTION
                "LOM Alarm Relay Enable/Disable"
            ::= { ho-STSRelayEntry 15 }

        cHo-STSRelaySD  OBJECT-TYPE
            SYNTAX  INTEGER {
                    disable(1),
                    enable(2)
                }
            ACCESS  read-write
            STATUS  mandatory
            DESCRIPTION
                "SD Alarm Relay Enable/Disable"
            ::= { ho-STSRelayEntry 16 }

        cHo-STSRelaySF  OBJECT-TYPE
            SYNTAX  INTEGER {
                    disable(1),
                    enable(2)
                }
            ACCESS  read-write
            STATUS  mandatory
            DESCRIPTION
                "SF Alarm Relay Enable/Disable"
            ::= { ho-STSRelayEntry 17 }
--
--  HoPath-STSPath Layer Alarm Severity Table
--
    cHo-STSSvrityTable  OBJECT IDENTIFIER ::= { cHo-STSPathTable 3 }

        cHo-STSSvrityLOP  OBJECT-TYPE
            SYNTAX  Severity
            ACCESS  read-write
            STATUS  mandatory
            DESCRIPTION
                "LOP Alarm Severity Selection"
            ::= { cHo-STSSvrityTable 1 }

        cHo-STSSvrityAIS  OBJECT-TYPE
            SYNTAX  Severity
            ACCESS  read-write
            STATUS  mandatory
            DESCRIPTION
                "AIS Alarm Severity Selection"
            ::= { cHo-STSSvrityTable 2 }

        cHo-STSSvrityTIM  OBJECT-TYPE
            SYNTAX  Severity
            ACCESS  read-write
            STATUS  mandatory
            DESCRIPTION
                "TIM Alarm Severity Selection"
            ::= { cHo-STSSvrityTable 3 }

        cHo-STSSvrityRDI-S  OBJECT-TYPE
            SYNTAX  Severity
            ACCESS  read-write
            STATUS  mandatory
            DESCRIPTION
                "RDI-S Alarm Severity Selection"
            ::= { cHo-STSSvrityTable 4 }

        cHo-STSSvrityRDI-C  OBJECT-TYPE
            SYNTAX  Severity
            ACCESS  read-write
            STATUS  mandatory
            DESCRIPTION
                "RDI-C Alarm Severity Selection"
            ::= { cHo-STSSvrityTable 5 }

        cHo-STSSvrityRDI-P  OBJECT-TYPE
            SYNTAX  Severity
            ACCESS  read-write
            STATUS  mandatory
            DESCRIPTION
                "RDI-P Alarm Severity Selection"
            ::= { cHo-STSSvrityTable 6 }

        cHo-STSSvrityBIP  OBJECT-TYPE
            SYNTAX  Severity
            ACCESS  read-write
            STATUS  mandatory
            DESCRIPTION
                "BIP Alarm Severity Selection"
            ::= { cHo-STSSvrityTable 7 }

        cHo-STSSvrityREI  OBJECT-TYPE
            SYNTAX  Severity
            ACCESS  read-write
            STATUS  mandatory
            DESCRIPTION
                "REI Alarm Severity Selection"
            ::= { cHo-STSSvrityTable 8 }

        cHo-STSSvrityPLM  OBJECT-TYPE
            SYNTAX  Severity
            ACCESS  read-write
            STATUS  mandatory
            DESCRIPTION
                "PLM Alarm Severity Selection"
            ::= { cHo-STSSvrityTable 9 }

        cHo-STSSvrityUNEQ  OBJECT-TYPE
            SYNTAX  Severity
            ACCESS  read-write
            STATUS  mandatory
            DESCRIPTION
                "UNEQ Alarm Severity Selection"
            ::= { cHo-STSSvrityTable 10 }

        cHo-STSSvrityLOM  OBJECT-TYPE
            SYNTAX  Severity
            ACCESS  read-write
            STATUS  mandatory
            DESCRIPTION
                "LOM Alarm Severity Selection"
            ::= { cHo-STSSvrityTable 11 }

        cHo-STSSvritySD  OBJECT-TYPE
            SYNTAX  Severity
            ACCESS  read-write
            STATUS  mandatory
            DESCRIPTION
                "SD Alarm Severity Selection"
            ::= { cHo-STSSvrityTable 12 }

        cHo-STSSvritySF  OBJECT-TYPE
            SYNTAX  Severity
            ACCESS  read-write
            STATUS  mandatory
            DESCRIPTION
                "SF Alarm Severity Selection"
            ::= { cHo-STSSvrityTable 13 }

--
--  LoPath-VTPath Layer Alarm Mask Table
--

    cLo-VTPathTable   OBJECT IDENTIFIER ::= { sdh-sonetAlarmTable 5 }

        cLo-VTMaskTable  OBJECT-TYPE
            SYNTAX  SEQUENCE OF Lo-VTMaskEntry
            ACCESS  not-accessible
            STATUS  mandatory
            DESCRIPTION
                "LoPath-VTPath layer Alarm Mask Table"
            ::= { cLo-VTPathTable 1 }

        lo-VTMaskEntry  OBJECT-TYPE
            SYNTAX  Lo-VTMaskEntry
            ACCESS  not-accessible
            STATUS  mandatory
            DESCRIPTION
                "LoPath-VTPath Alarm entry"
            INDEX { cLo-VTMaskXCUIdx , cLo-VTMaskPortIdx , cLo-VTMaskAUG1STS3Idx , cLo-VTMaskVC3STS1Idx , cLo-VTMaskTU1xVTxIdx }
            ::= { cLo-VTMaskTable 1 }

        Lo-VTMaskEntry ::= SEQUENCE {
            cLo-VTMaskXCUIdx            XcuNum,
            cLo-VTMaskPortIdx           PortNum,
            cLo-VTMaskAUG1STS3Idx       Aug1Sts3Num,
            cLo-VTMaskVC3STS1Idx        Vc3Sts1Num,
            cLo-VTMaskTU1xVTxIdx        TU1xVtxNum,
            cLo-VTMaskLOP               INTEGER,
            cLo-VTMaskAIS               INTEGER,
            cLo-VTMaskTIM               INTEGER,
            cLo-VTMaskRDI-S             INTEGER,
            cLo-VTMaskRDI-C             INTEGER,
            cLo-VTMaskRDI-P             INTEGER,
            cLo-VTMaskBIP               INTEGER,
            cLo-VTMaskREI               INTEGER,
            ccLo-VTMaskPLM              INTEGER,
            ccLo-VTMaskUNEQ             INTEGER,
            cLo-VTMaskSD                INTEGER,
            cLo-VTMaskSF                INTEGER
        }

        cLo-VTMaskXCUIdx  OBJECT-TYPE
            SYNTAX  XcuNum
            ACCESS  read-only
            STATUS  mandatory
            DESCRIPTION
                "XCU index"
            ::= { lo-VTMaskEntry 1 }

        cLo-VTMaskPortIdx  OBJECT-TYPE
            SYNTAX  PortNum
            ACCESS  read-only
            STATUS  mandatory
            DESCRIPTION
                "Port index"
            ::= { lo-VTMaskEntry 2 }

        cLo-VTMaskAUG1STS3Idx  OBJECT-TYPE
            SYNTAX  Aug1Sts3Num
            ACCESS  read-only
            STATUS  mandatory
            DESCRIPTION
                "AUG1/STS3 index"
            ::= { lo-VTMaskEntry 3 }

        cLo-VTMaskVC3STS1Idx  OBJECT-TYPE
            SYNTAX  Vc3Sts1Num
            ACCESS  read-only
            STATUS  mandatory
            DESCRIPTION
                "VC3/STS1 or Tug3 index"
            ::= { lo-VTMaskEntry 4 }

        cLo-VTMaskTU1xVTxIdx  OBJECT-TYPE
            SYNTAX  TU1xVtxNum
            ACCESS  read-only
            STATUS  mandatory
            DESCRIPTION
                "VC1x/VTx index"
            ::= { lo-VTMaskEntry 5 }

        cLo-VTMaskLOP  OBJECT-TYPE
            SYNTAX  INTEGER {
                    disable(1),
                    enable(2)
                }
            ACCESS  read-write
            STATUS  mandatory
            DESCRIPTION
                "LOP Alarm Mask Enable/Disable"
            ::= { lo-VTMaskEntry 6 }

        cLo-VTMaskAIS  OBJECT-TYPE
            SYNTAX  INTEGER {
                    disable(1),
                    enable(2)
                }
            ACCESS  read-write
            STATUS  mandatory
            DESCRIPTION
                "AIS Alarm Mask Enable/Disable"
            ::= { lo-VTMaskEntry 7 }

        cLo-VTMaskTIM  OBJECT-TYPE
            SYNTAX  INTEGER {
                    disable(1),
                    enable(2)
                }
            ACCESS  read-write
            STATUS  mandatory
            DESCRIPTION
                "TIM Alarm Mask Enable/Disable"
            ::= { lo-VTMaskEntry 8 }

        cLo-VTMaskRDI-S  OBJECT-TYPE
            SYNTAX  INTEGER {
                    disable(1),
                    enable(2)
                }
            ACCESS  read-write
            STATUS  mandatory
            DESCRIPTION
                "RDI-S Alarm Mask Enable/Disable"
            ::= { lo-VTMaskEntry 9 }

        cLo-VTMaskRDI-C  OBJECT-TYPE
            SYNTAX  INTEGER {
                    disable(1),
                    enable(2)
                }
            ACCESS  read-write
            STATUS  mandatory
            DESCRIPTION
                "RDI-C Alarm Mask Enable/Disable"
            ::= { lo-VTMaskEntry 10 }

        cLo-VTMaskRDI-P  OBJECT-TYPE
            SYNTAX  INTEGER {
                    disable(1),
                    enable(2)
                }
            ACCESS  read-write
            STATUS  mandatory
            DESCRIPTION
                "RDI-P Alarm Mask Enable/Disable"
            ::= { lo-VTMaskEntry 11 }

        cLo-VTMaskBIP  OBJECT-TYPE
            SYNTAX  INTEGER {
                    disable(1),
                    enable(2)
                }
            ACCESS  read-write
            STATUS  mandatory
            DESCRIPTION
                "BIP Alarm Mask Enable/Disable"
            ::= { lo-VTMaskEntry 12 }

        cLo-VTMaskREI  OBJECT-TYPE
            SYNTAX  INTEGER {
                    disable(1),
                    enable(2)
                }
            ACCESS  read-write
            STATUS  mandatory
            DESCRIPTION
                "REI Alarm Mask Enable/Disable"
            ::= { lo-VTMaskEntry 13 }

        ccLo-VTMaskPLM  OBJECT-TYPE
            SYNTAX  INTEGER {
                    disable(1),
                    enable(2)
                }
            ACCESS  read-write
            STATUS  mandatory
            DESCRIPTION
                "PLM Alarm Mask Enable/Disable"
            ::= { lo-VTMaskEntry 14 }

        ccLo-VTMaskUNEQ  OBJECT-TYPE
            SYNTAX  INTEGER {
                    disable(1),
                    enable(2)
                }
            ACCESS  read-write
            STATUS  mandatory
            DESCRIPTION
                "UNEQ Alarm Mask Enable/Disable"
            ::= { lo-VTMaskEntry 15 }

        cLo-VTMaskSD  OBJECT-TYPE
            SYNTAX  INTEGER {
                    disable(1),
                    enable(2)
                }
            ACCESS  read-write
            STATUS  mandatory
            DESCRIPTION
                "SD Alarm Mask Enable/Disable"
            ::= { lo-VTMaskEntry 16 }

        cLo-VTMaskSF  OBJECT-TYPE
            SYNTAX  INTEGER {
                    disable(1),
                    enable(2)
                }
            ACCESS  read-write
            STATUS  mandatory
            DESCRIPTION
                "SF Alarm Mask Enable/Disable"
            ::= { lo-VTMaskEntry 17 }
--
--  LoPath-VTPath Layer Alarm Relay Table
--
        cLo-VTRelayTable  OBJECT-TYPE
            SYNTAX  SEQUENCE OF LoPath-VTPathLayerRelayEntry
            ACCESS  not-accessible
            STATUS  mandatory
            DESCRIPTION
                "LoPath-VTPath layer Alarm Mask Table"
            ::= { cLo-VTPathTable 2 }

        lo-VTRelayEntry  OBJECT-TYPE
            SYNTAX  LoPath-VTPathLayerRelayEntry
            ACCESS  not-accessible
            STATUS  mandatory
            DESCRIPTION
                "LoPath-VTPath Alarm entry"
            INDEX { cLo-VTRelayXCUIndex , cLo-VTRelayPortIndex , cLo-VTRelayAUG1STS3Index , cLo-VTRelayVC3STS1Index , cLo-VTRelayTU1xVTxIndex }
            ::= { cLo-VTRelayTable 1 }

        LoPath-VTPathLayerRelayEntry ::= SEQUENCE {
            cLo-VTRelayXCUIndex         XcuNum,
            cLo-VTRelayPortIndex        PortNum,
            cLo-VTRelayAUG1STS3Index    Aug1Sts3Num,
            cLo-VTRelayVC3STS1Index     Vc3Sts1Num,
            cLo-VTRelayTU1xVTxIndex     TU1xVtxNum,
            cLo-VTRelayLOP              INTEGER,
            cLo-VTRelayAIS              INTEGER,
            cLo-VTRelayTIM              INTEGER,
            cLo-VTRelayRDI-S            INTEGER,
            cLo-VTRelayRDI-C            INTEGER,
            cLo-VTRelayRDI-P            INTEGER,
            cLo-VTRelayBIP              INTEGER,
            cLo-VTRelayREI              INTEGER,
            cLo-VTRelayPLM              INTEGER,
            cLo-VTRelayUNEQ             INTEGER,
            cLo-VTRelaySD               INTEGER,
            cLo-VTRelaySF               INTEGER
        }

        cLo-VTRelayXCUIndex  OBJECT-TYPE
            SYNTAX  XcuNum
            ACCESS  read-only
            STATUS  mandatory
            DESCRIPTION
                "XCU index"
            ::= { lo-VTRelayEntry 1 }

        cLo-VTRelayPortIndex  OBJECT-TYPE
            SYNTAX  PortNum
            ACCESS  read-only
            STATUS  mandatory
            DESCRIPTION
                "Port index"
            ::= { lo-VTRelayEntry 2 }

        cLo-VTRelayAUG1STS3Index  OBJECT-TYPE
            SYNTAX  Aug1Sts3Num
            ACCESS  read-only
            STATUS  mandatory
            DESCRIPTION
                "AUG1/STS3 index"
            ::= { lo-VTRelayEntry 3 }

        cLo-VTRelayVC3STS1Index  OBJECT-TYPE
            SYNTAX  Vc3Sts1Num
            ACCESS  read-only
            STATUS  mandatory
            DESCRIPTION
                "VC3/STS1 or Tug3 index"
            ::= { lo-VTRelayEntry 4 }

        cLo-VTRelayTU1xVTxIndex  OBJECT-TYPE
            SYNTAX  TU1xVtxNum
            ACCESS  read-only
            STATUS  mandatory
            DESCRIPTION
                "VC1x/VTx index"
            ::= { lo-VTRelayEntry 5 }

        cLo-VTRelayLOP  OBJECT-TYPE
            SYNTAX  INTEGER {
                    disable(1),
                    enable(2)
                }
            ACCESS  read-write
            STATUS  mandatory
            DESCRIPTION
                "LOP Alarm Relay Enable/Disable"
            ::= { lo-VTRelayEntry 6 }

        cLo-VTRelayAIS  OBJECT-TYPE
            SYNTAX  INTEGER {
                    disable(1),
                    enable(2)
                }
            ACCESS  read-write
            STATUS  mandatory
            DESCRIPTION
                "AIS Alarm Relay Enable/Disable"
            ::= { lo-VTRelayEntry 7 }

        cLo-VTRelayTIM  OBJECT-TYPE
            SYNTAX  INTEGER {
                    disable(1),
                    enable(2)
                }
            ACCESS  read-write
            STATUS  mandatory
            DESCRIPTION
                "TIM Alarm Relay Enable/Disable"
            ::= { lo-VTRelayEntry 8 }

        cLo-VTRelayRDI-S  OBJECT-TYPE
            SYNTAX  INTEGER {
                    disable(1),
                    enable(2)
                }
            ACCESS  read-write
            STATUS  mandatory
            DESCRIPTION
                "RDI-S Alarm Relay Enable/Disable"
            ::= { lo-VTRelayEntry 9 }

        cLo-VTRelayRDI-C  OBJECT-TYPE
            SYNTAX  INTEGER {
                    disable(1),
                    enable(2)
                }
            ACCESS  read-write
            STATUS  mandatory
            DESCRIPTION
                "RDI-C Alarm Relay Enable/Disable"
            ::= { lo-VTRelayEntry 10 }

        cLo-VTRelayRDI-P  OBJECT-TYPE
            SYNTAX  INTEGER {
                    disable(1),
                    enable(2)
                }
            ACCESS  read-write
            STATUS  mandatory
            DESCRIPTION
                "RDI-P Alarm Relay Enable/Disable"
            ::= { lo-VTRelayEntry 11 }

        cLo-VTRelayBIP  OBJECT-TYPE
            SYNTAX  INTEGER {
                    disable(1),
                    enable(2)
                }
            ACCESS  read-write
            STATUS  mandatory
            DESCRIPTION
                "BIP Alarm Relay Enable/Disable"
            ::= { lo-VTRelayEntry 12 }

        cLo-VTRelayREI  OBJECT-TYPE
            SYNTAX  INTEGER {
                    disable(1),
                    enable(2)
                }
            ACCESS  read-write
            STATUS  mandatory
            DESCRIPTION
                "REI Alarm Relay Enable/Disable"
            ::= { lo-VTRelayEntry 13 }

        cLo-VTRelayPLM  OBJECT-TYPE
            SYNTAX  INTEGER {
                    disable(1),
                    enable(2)
                }
            ACCESS  read-write
            STATUS  mandatory
            DESCRIPTION
                "PLM Alarm Relay Enable/Disable"
            ::= { lo-VTRelayEntry 14 }

        cLo-VTRelayUNEQ  OBJECT-TYPE
            SYNTAX  INTEGER {
                    disable(1),
                    enable(2)
                }
            ACCESS  read-write
            STATUS  mandatory
            DESCRIPTION
                "UNEQ Alarm Relay Enable/Disable"
            ::= { lo-VTRelayEntry 15 }

        cLo-VTRelaySD  OBJECT-TYPE
            SYNTAX  INTEGER {
                    disable(1),
                    enable(2)
                }
            ACCESS  read-write
            STATUS  mandatory
            DESCRIPTION
                "SD Alarm Relay Enable/Disable"
            ::= { lo-VTRelayEntry 16 }

        cLo-VTRelaySF  OBJECT-TYPE
            SYNTAX  INTEGER {
                    disable(1),
                    enable(2)
                }
            ACCESS  read-write
            STATUS  mandatory
            DESCRIPTION
                "SF Alarm Relay Enable/Disable"
            ::= { lo-VTRelayEntry 17 }
--
--  LoPath-VTPath Layer Alarm Severity Table
--
    cLo-VTSvrityTable  OBJECT IDENTIFIER ::= { cLo-VTPathTable 3 }


        cLo-VTSvrityLOP  OBJECT-TYPE
            SYNTAX  Severity
            ACCESS  read-write
            STATUS  mandatory
            DESCRIPTION
                "LOP Alarm Severity Selection"
            ::= { cLo-VTSvrityTable 1 }

        cLo-VTSvrityAIS  OBJECT-TYPE
            SYNTAX  Severity
            ACCESS  read-write
            STATUS  mandatory
            DESCRIPTION
                "AIS Alarm Severity Selection"
            ::= { cLo-VTSvrityTable 2 }

        cLo-VTSvrityTIM  OBJECT-TYPE
            SYNTAX  Severity
            ACCESS  read-write
            STATUS  mandatory
            DESCRIPTION
                "TIM Alarm Severity Selection"
            ::= { cLo-VTSvrityTable 3 }

        cLo-VTSvrityRDI-S  OBJECT-TYPE
            SYNTAX  Severity
            ACCESS  read-write
            STATUS  mandatory
            DESCRIPTION
                "RDI-S Alarm Severity Selection"
            ::= { cLo-VTSvrityTable 4 }

        cLo-VTSvrityRDI-C  OBJECT-TYPE
            SYNTAX  Severity
            ACCESS  read-write
            STATUS  mandatory
            DESCRIPTION
                "RDI-C Alarm Severity Selection"
            ::= { cLo-VTSvrityTable 5 }

        cLo-VTSvrityRDI-P  OBJECT-TYPE
            SYNTAX  Severity
            ACCESS  read-write
            STATUS  mandatory
            DESCRIPTION
                "RDI-P Alarm Severity Selection"
            ::= { cLo-VTSvrityTable 6 }

        cLo-VTSvrityBIP  OBJECT-TYPE
            SYNTAX  Severity
            ACCESS  read-write
            STATUS  mandatory
            DESCRIPTION
                "BIP Alarm Severity Selection"
            ::= { cLo-VTSvrityTable 7 }

        cLo-VTSvrityREI  OBJECT-TYPE
            SYNTAX  Severity
            ACCESS  read-write
            STATUS  mandatory
            DESCRIPTION
                "REI Alarm Severity Selection"
            ::= { cLo-VTSvrityTable 8 }

        cLo-VTSvrityPLM  OBJECT-TYPE
            SYNTAX  Severity
            ACCESS  read-write
            STATUS  mandatory
            DESCRIPTION
                "PLM Alarm Severity Selection"
            ::= { cLo-VTSvrityTable 9 }

        cLo-VTSvrityUNEQ  OBJECT-TYPE
            SYNTAX  Severity
            ACCESS  read-write
            STATUS  mandatory
            DESCRIPTION
                "UNEQ Alarm Severity Selection"
            ::= { cLo-VTSvrityTable 10 }


        cLo-VTSvritySD  OBJECT-TYPE
            SYNTAX  Severity
            ACCESS  read-write
            STATUS  mandatory
            DESCRIPTION
                "SD Alarm Severity Selection"
            ::= { cLo-VTSvrityTable 11 }

        cLo-VTSvritySF  OBJECT-TYPE
            SYNTAX  Severity
            ACCESS  read-write
            STATUS  mandatory
            DESCRIPTION
                "SF Alarm Severity Selection"
            ::= { cLo-VTSvrityTable 12 }



--
--  External Alarm Setup Table
--
        externalSetupTable  OBJECT-TYPE
            SYNTAX  SEQUENCE OF ExternalSetupEntry
            ACCESS  not-accessible
            STATUS  mandatory
            DESCRIPTION
                "External alarm setup table"
            ::= { alarmSetupTable 3 }

        externalSetupEntry  OBJECT-TYPE
            SYNTAX  ExternalSetupEntry
            ACCESS  not-accessible
            STATUS  mandatory
            DESCRIPTION
                "External alarm setup entry"
            INDEX { ccExternalMaskIndex }
            ::= { externalSetupTable 1 }

        ExternalSetupEntry ::= SEQUENCE {
            ccExternalMaskIndex         INTEGER (1..4),
            ccExternalMessage           DisplayString (SIZE(0..30)),
            ccExternalMaskEnable        INTEGER,
            ccExternalRelayEnable       INTEGER,
            ccExternalSeverity          Severity
        }

        ccExternalMaskIndex  OBJECT-TYPE
            SYNTAX  INTEGER (1..4)
            ACCESS  read-only
            STATUS  mandatory
            DESCRIPTION
                "External alarm setup index"
            ::= { externalSetupEntry 1 }

        ccExternalMessage  OBJECT-TYPE
            SYNTAX  DisplayString (SIZE(0..30))
            ACCESS  read-write
            STATUS  mandatory
            DESCRIPTION
                "External alarm message"
            ::= { externalSetupEntry 2 }

        ccExternalMaskEnable  OBJECT-TYPE
            SYNTAX  INTEGER {
                    disable(1),
                    enable(2)
                }
            ACCESS  read-write
            STATUS  mandatory
            DESCRIPTION
                "External alarm mask enable/disable"
            ::= { externalSetupEntry 3 }

        ccExternalRelayEnable  OBJECT-TYPE
            SYNTAX  INTEGER {
                    disable(1),
                    enable(2)
                }
            ACCESS  read-write
            STATUS  mandatory
            DESCRIPTION
                "External alarm relay enable/disable"
            ::= { externalSetupEntry 4 }

        ccExternalSeverity  OBJECT-TYPE
            SYNTAX  Severity
            ACCESS  read-write
            STATUS  mandatory
            DESCRIPTION
                "External alarm severity"
            ::= { externalSetupEntry 5 }


--
--  Alarm Setup Hex Table
--
    alarmSetupHexTable  OBJECT IDENTIFIER ::= { alarmSetupTable 4 }

        systemAlarmMaskHex  OBJECT-TYPE
            SYNTAX  OCTET STRING(SIZE(8))
            ACCESS  read-only
            STATUS  mandatory
            DESCRIPTION
                "system alarm mask in Hex"
            ::= { alarmSetupHexTable 1 }

        systemAlarmRelayHex  OBJECT-TYPE
            SYNTAX  OCTET STRING(SIZE(8))
            ACCESS  read-only
            STATUS  mandatory
            DESCRIPTION
                "system alarm relay in Hex"
            ::= { alarmSetupHexTable 2 }

        systemAlarmSeverityHex  OBJECT-TYPE
            SYNTAX  OCTET STRING(SIZE(32))
            ACCESS  read-only
            STATUS  mandatory
            DESCRIPTION
                "system alarm Severity in Hex"
            ::= { alarmSetupHexTable 3 }

        lineAlarmMaskHex  OBJECT-TYPE
            SYNTAX  OCTET STRING(SIZE(17))
            ACCESS  read-only
            STATUS  mandatory
            DESCRIPTION
                "Line alarm mask in Hex"
            ::= { alarmSetupHexTable 4 }

        lineAlarmRelayHex  OBJECT-TYPE
            SYNTAX  OCTET STRING(SIZE(17))
            ACCESS  read-only
            STATUS  mandatory
            DESCRIPTION
                "Line alarm Relay in Hex"
            ::= { alarmSetupHexTable 5 }

        lineAlarmSeverityHex  OBJECT-TYPE
            SYNTAX  OCTET STRING(SIZE(24))
            ACCESS  read-only
            STATUS  mandatory
            DESCRIPTION
                "Line alarm Relay in Hex"
            ::= { alarmSetupHexTable 6 }

        hpAlarmMaskHex  OBJECT-TYPE
            SYNTAX  OCTET STRING(SIZE(97))
            ACCESS  read-only
            STATUS  mandatory
            DESCRIPTION
                "hp alarm mask in Hex"
            ::= { alarmSetupHexTable 7 }

        hpAlarmRelayHex  OBJECT-TYPE
            SYNTAX  OCTET STRING(SIZE(97))
            ACCESS  read-only
            STATUS  mandatory
            DESCRIPTION
                "hp alarm Relay in Hex"
            ::= { alarmSetupHexTable 8 }

        hpAlarmSeverityHex  OBJECT-TYPE
            SYNTAX  OCTET STRING(SIZE(24))
            ACCESS  read-only
            STATUS  mandatory
            DESCRIPTION
                "hp alarm Severity in Hex"
            ::= { alarmSetupHexTable 9 }

        lpXCU1Port1AlarmMaskHex  OBJECT-TYPE
            SYNTAX  OCTET STRING(SIZE(673))
            ACCESS  read-only
            STATUS  mandatory
            DESCRIPTION
                "XCU#1 Port#1 lp alarm mask in Hex"
            ::= { alarmSetupHexTable 10 }

        lpXCU1Port2AlarmMaskHex  OBJECT-TYPE
            SYNTAX  OCTET STRING(SIZE(673))
            ACCESS  read-only
            STATUS  mandatory
            DESCRIPTION
                "XCU#1 Port#2 lp alarm mask in Hex"
            ::= { alarmSetupHexTable 11 }

        lpXCU2Port1AlarmMaskHex  OBJECT-TYPE
            SYNTAX  OCTET STRING(SIZE(673))
            ACCESS  read-only
            STATUS  mandatory
            DESCRIPTION
                "XCU#2 Port#1 lp alarm mask in Hex"
            ::= { alarmSetupHexTable 12 }

        lpXCU2Port2AlarmMaskHex  OBJECT-TYPE
            SYNTAX  OCTET STRING(SIZE(673))
            ACCESS  read-only
            STATUS  mandatory
            DESCRIPTION
                "XCU#2 Port#1 lp alarm mask in Hex"
            ::= { alarmSetupHexTable 13 }

        lpXCU1Port1AlarmRelayHex  OBJECT-TYPE
            SYNTAX  OCTET STRING(SIZE(673))
            ACCESS  read-only
            STATUS  mandatory
            DESCRIPTION
                "XCU#1 Port#1 lp alarm Relay in Hex"
            ::= { alarmSetupHexTable 14 }

        lpXCU1Port2AlarmRelayHex  OBJECT-TYPE
            SYNTAX  OCTET STRING(SIZE(673))
            ACCESS  read-only
            STATUS  mandatory
            DESCRIPTION
                "XCU#1 Port#2 lp alarm Relay in Hex"
            ::= { alarmSetupHexTable 15 }

        lpXCU2Port1AlarmRelayHex  OBJECT-TYPE
            SYNTAX  OCTET STRING(SIZE(673))
            ACCESS  read-only
            STATUS  mandatory
            DESCRIPTION
                "XCU#2 Port#1 lp alarm Relay in Hex"
            ::= { alarmSetupHexTable 16 }

        lpXCU2Port2AlarmRelayHex  OBJECT-TYPE
            SYNTAX  OCTET STRING(SIZE(673))
            ACCESS  read-only
            STATUS  mandatory
            DESCRIPTION
                "XCU#2 Port#1 lp alarm Relay in Hex"
            ::= { alarmSetupHexTable 17 }

        lpAlarmSeverityHex  OBJECT-TYPE
            SYNTAX  OCTET STRING(SIZE(24))
            ACCESS  read-only
            STATUS  mandatory
            DESCRIPTION
                "lp alarm Severity in Hex"
            ::= { alarmSetupHexTable 18 }

        externalAlarmMaskHex  OBJECT-TYPE
            SYNTAX  OCTET STRING(SIZE(2))
            ACCESS  read-only
            STATUS  mandatory
            DESCRIPTION
                "external alarm mask in Hex"
            ::= { alarmSetupHexTable 19 }

        externalAlarmRelayHex  OBJECT-TYPE
            SYNTAX  OCTET STRING(SIZE(2))
            ACCESS  read-only
            STATUS  mandatory
            DESCRIPTION
                "external alarm relay in Hex"
            ::= { alarmSetupHexTable 20 }

        externalAlarmSeverityHex  OBJECT-TYPE
            SYNTAX  OCTET STRING(SIZE(16))
            ACCESS  read-only
            STATUS  mandatory
            DESCRIPTION
                "external alarm Severity in Hex"
            ::= { alarmSetupHexTable 21 }



--
--   alarmOutputTable
--
    alarmOutputTable         OBJECT IDENTIFIER  ::= { alarmSetupTable 5 }

        alarmOutputControl  OBJECT-TYPE
            SYNTAX  INTEGER {
                    by-system(1),
                    by-user(2)
                }
            ACCESS  read-write
            STATUS  mandatory
            DESCRIPTION
                "Alarm output control setup"
            ::= { alarmOutputTable 1 }

        alarmOutputP1State  OBJECT-TYPE
            SYNTAX  INTEGER {
--                  off(1),
--            on(2)
                    open(1),
                    close(2)
                }
            ACCESS  read-write
            STATUS  mandatory
            DESCRIPTION
                "P1 alarm output state. Only take effect when alarm output is controlled by user"
            ::= { alarmOutputTable 2 }

        alarmOutputP2State  OBJECT-TYPE
            SYNTAX  INTEGER {
--                  off(1),
--            on(2)
                    open(1),
                    close(2)
                }
            ACCESS  read-write
            STATUS  mandatory
            DESCRIPTION
                "P2 alarm output state. Only take effect when alarm output is controlled by user"
            ::= { alarmOutputTable 3 }

        alarmOutputP3State  OBJECT-TYPE
            SYNTAX  INTEGER {
--                  off(1),
--            on(2)
                    open(1),
                    close(2)
                }
            ACCESS  read-write
            STATUS  mandatory
            DESCRIPTION
                "P3 alarm output state. Only take effect when alarm output is controlled by user"
            ::= { alarmOutputTable 4 }

        alarmOutputP4State  OBJECT-TYPE
            SYNTAX  INTEGER {
--                  off(1),
--            on(2)
                    open(1),
                    close(2)
                }
            ACCESS  read-write
            STATUS  mandatory
            DESCRIPTION
                "P4 alarm output state. Only take effect when alarm output is controlled by user"
            ::= { alarmOutputTable 5 }

        alarmOutputP1Info  OBJECT-TYPE
            SYNTAX  DisplayString (SIZE (0..63))
            ACCESS  read-write
            STATUS  mandatory
            DESCRIPTION
                "P1 alarm output information string"
            ::= { alarmOutputTable 6 }

        alarmOutputP2Info  OBJECT-TYPE
            SYNTAX  DisplayString (SIZE (0..63))
            ACCESS  read-write
            STATUS  mandatory
            DESCRIPTION
                "P2 alarm output information string"
            ::= { alarmOutputTable 7 }

        alarmOutputP3Info  OBJECT-TYPE
            SYNTAX  DisplayString (SIZE (0..63))
            ACCESS  read-write
            STATUS  mandatory
            DESCRIPTION
                "P3 alarm output information string"
            ::= { alarmOutputTable 8 }

        alarmOutputP4Info  OBJECT-TYPE
            SYNTAX  DisplayString (SIZE (0..63))
            ACCESS  read-write
            STATUS  mandatory
            DESCRIPTION
                "P4 alarm output information string"
            ::= { alarmOutputTable 9 }

-- 2016-07-22 add below by Sue
--
--  Inhibit Port Alarm Table
--

        inhibitPortAlarmTable  OBJECT-TYPE
            SYNTAX  SEQUENCE OF InhibitPortAlarmEntry
            ACCESS  not-accessible
            STATUS  mandatory
            DESCRIPTION
                "Inhibit port alarm table"
            ::= { alarmSetupTable 6 }

        inhibitPortAlarmEntry  OBJECT-TYPE
            SYNTAX  InhibitPortAlarmEntry
            ACCESS  not-accessible
            STATUS  mandatory
            DESCRIPTION
                "inhibit port alarm entry"
            INDEX { cCardIndex }
            ::= { inhibitPortAlarmTable 1 }

        InhibitPortAlarmEntry ::= SEQUENCE {
            cCardIndex                  CardID,
            cPort1AlarmInhibit          INTEGER,
            cPort2AlarmInhibit          INTEGER
        }

        cCardIndex  OBJECT-TYPE
            SYNTAX  CardID
            ACCESS  read-only
            STATUS  mandatory
            DESCRIPTION
                "2 XCUs and tributary card 1 to 8, total 10 cards."
            ::= { inhibitPortAlarmEntry 1 }

        cPort1AlarmInhibit  OBJECT-TYPE
            SYNTAX  INTEGER {
                    disable(1),
                    enable(2)
                }
            ACCESS  read-write
            STATUS  mandatory
            DESCRIPTION
                "Port 1 Alarm Inhibit Enable/Disable"
            ::= { inhibitPortAlarmEntry 2 }

        cPort2AlarmInhibit  OBJECT-TYPE
            SYNTAX  INTEGER {
                    disable(1),
                    enable(2)
                }
            ACCESS  read-write
            STATUS  mandatory
            DESCRIPTION
                "Port 2 Alarm Inhibit Enable/Disable"
            ::= { inhibitPortAlarmEntry 3 }
-- 2016-07-22 add above by Sue


--
--  Current Alarm Status Table
--

    currentAlarmStatusTable     OBJECT IDENTIFIER ::= { system 6 }

--
--  Physical Layer Alarm Status Table
--

    cPHYCurrStTable             OBJECT IDENTIFIER ::= { currentAlarmStatusTable 1 }


        cPHYStatusTable  OBJECT-TYPE
        SYNTAX  SEQUENCE OF PHYStatusEntry
            ACCESS  not-accessible
            STATUS  mandatory
            DESCRIPTION
                "Physical layer Alarm Status Table"
            ::= { cPHYCurrStTable 1 }

        pHYStatusEntry  OBJECT-TYPE
            SYNTAX  PHYStatusEntry
            ACCESS  not-accessible
            STATUS  mandatory
            DESCRIPTION
                "Physical Alarm entry"
            INDEX { cPHYStatusXCUIndex , cPHYStatusPortIndex }
            ::= { cPHYStatusTable 1 }

        PHYStatusEntry ::= SEQUENCE {
            cPHYStatusXCUIndex          XcuNum,
            cPHYStatusPortIndex         PortNum,
            cPHYStatusLOS               AlmStatus
        }

        cPHYStatusXCUIndex  OBJECT-TYPE
            SYNTAX  XcuNum
            ACCESS  read-only
            STATUS  mandatory
            DESCRIPTION
                "XCU index"
            ::= { pHYStatusEntry 1 }

        cPHYStatusPortIndex  OBJECT-TYPE
            SYNTAX  PortNum
            ACCESS  read-only
            STATUS  mandatory
            DESCRIPTION
                "Port index"
            ::= { pHYStatusEntry 2 }

        cPHYStatusLOS  OBJECT-TYPE
            SYNTAX  AlmStatus
            ACCESS  read-only
            STATUS  mandatory
            DESCRIPTION
                "Alarm Status"
            ::= { pHYStatusEntry 3 }

--  Count Table


        cPHYCountTable  OBJECT-TYPE
            SYNTAX  SEQUENCE OF PHYCountEntry
            ACCESS  not-accessible
            STATUS  mandatory
            DESCRIPTION
                "Physical layer Alarm Count Table"
            ::= { cPHYCurrStTable 2 }

        pHYCountEntry  OBJECT-TYPE
            SYNTAX  PHYCountEntry
            ACCESS  not-accessible
            STATUS  mandatory
            DESCRIPTION
                "Physical Alarm entry"
            INDEX { cPHYCountXCUIndex , cPHYCountPortIndex }
            ::= { cPHYCountTable 1 }

        PHYCountEntry ::= SEQUENCE {
            cPHYCountXCUIndex           XcuNum,
            cPHYCountPortIndex          PortNum,
            cPHYCountLOS                INTEGER
        }

        cPHYCountXCUIndex  OBJECT-TYPE
            SYNTAX  XcuNum
            ACCESS  read-only
            STATUS  mandatory
            DESCRIPTION
                "XCU index"
            ::= { pHYCountEntry 1 }

        cPHYCountPortIndex  OBJECT-TYPE
            SYNTAX  PortNum
            ACCESS  read-only
            STATUS  mandatory
            DESCRIPTION
                "Port index"
            ::= { pHYCountEntry 2 }

        cPHYCountLOS  OBJECT-TYPE
            SYNTAX  INTEGER
            ACCESS  read-only
            STATUS  mandatory
            DESCRIPTION
                "Alarm  Count"
            ::= { pHYCountEntry 3 }


--
--  RS-Section Layer Alarm Status Table
--

    cRS-SectionCurrStTable        OBJECT IDENTIFIER ::= { currentAlarmStatusTable 2 }

        cRS-SectionStatusTable  OBJECT-TYPE
            SYNTAX  SEQUENCE OF RS-SectionStatusEntry
            ACCESS  not-accessible
            STATUS  mandatory
            DESCRIPTION
                "RS-Section layer Alarm Status Table"
            ::= { cRS-SectionCurrStTable 1 }

        rS-SectionStatusEntry  OBJECT-TYPE
            SYNTAX  RS-SectionStatusEntry
            ACCESS  not-accessible
            STATUS  mandatory
            DESCRIPTION
                "RS-Section layer Alarm entry"
            INDEX { cRS-SectionStatusXCUIdx , cRS-SectionStatusPortIdx }
            ::= { cRS-SectionStatusTable 1 }

        RS-SectionStatusEntry ::= SEQUENCE {
            cRS-SectionStatusXCUIdx     XcuNum,
            cRS-SectionStatusPortIdx    PortNum,
            cRS-SectionStatusLOF        AlmStatus,
            cRS-SectionStatusBIP        AlmStatus,
            cRS-SectionStatusTIM        AlmStatus
        }

        cRS-SectionStatusXCUIdx  OBJECT-TYPE
            SYNTAX  XcuNum
            ACCESS  read-only
            STATUS  mandatory
            DESCRIPTION
                "Alarm XCU index"
            ::= { rS-SectionStatusEntry 1 }

        cRS-SectionStatusPortIdx  OBJECT-TYPE
            SYNTAX  PortNum
            ACCESS  read-only
            STATUS  mandatory
            DESCRIPTION
                "Alarm Port index"
            ::= { rS-SectionStatusEntry 2 }

        cRS-SectionStatusLOF  OBJECT-TYPE
            SYNTAX  AlmStatus
            ACCESS  read-only
            STATUS  mandatory
            DESCRIPTION
                "Alarm Status"
            ::= { rS-SectionStatusEntry 3 }

        cRS-SectionStatusTIM  OBJECT-TYPE
            SYNTAX  AlmStatus
            ACCESS  read-only
            STATUS  mandatory
            DESCRIPTION
                "Alarm Status"
            ::= { rS-SectionStatusEntry 4 }

        cRS-SectionStatusBIP  OBJECT-TYPE
            SYNTAX  AlmStatus
            ACCESS  read-only
            STATUS  mandatory
            DESCRIPTION
                "Alarm Status"
            ::= { rS-SectionStatusEntry 5 }

-- Count Table

        cRS-SectionCountTable  OBJECT-TYPE
            SYNTAX  SEQUENCE OF RS-SectionCountEntry
            ACCESS  not-accessible
            STATUS  mandatory
            DESCRIPTION
                "RS-Section layer Alarm Count Table"
            ::= { cRS-SectionCurrStTable 2 }

        rS-SectionCountEntry  OBJECT-TYPE
            SYNTAX  RS-SectionCountEntry
            ACCESS  not-accessible
            STATUS  mandatory
            DESCRIPTION
                "RS-Section layer Alarm entry"
            INDEX { cRS-SectionCountXCUIdx , cRS-SectionCountPortIdx }
            ::= { cRS-SectionCountTable 1 }

        RS-SectionCountEntry ::= SEQUENCE {
            cRS-SectionCountXCUIdx      XcuNum,
            cRS-SectionCountPortIdx     PortNum,
            cRS-SectionCountLOF         INTEGER,
            cRS-SectionCountBIP         INTEGER,
            cRS-SectionCountTIM         INTEGER
        }

        cRS-SectionCountXCUIdx  OBJECT-TYPE
            SYNTAX  XcuNum
            ACCESS  read-only
            STATUS  mandatory
            DESCRIPTION
                "Alarm XCU index"
            ::= { rS-SectionCountEntry 1 }

        cRS-SectionCountPortIdx  OBJECT-TYPE
            SYNTAX  PortNum
            ACCESS  read-only
            STATUS  mandatory
            DESCRIPTION
                "Alarm Port index"
            ::= { rS-SectionCountEntry 2 }

        cRS-SectionCountLOF  OBJECT-TYPE
            SYNTAX  INTEGER
            ACCESS  read-only
            STATUS  mandatory
            DESCRIPTION
                "Alarm Count"
            ::= { rS-SectionCountEntry 3 }

        cRS-SectionCountTIM  OBJECT-TYPE
            SYNTAX  INTEGER
            ACCESS  read-only
            STATUS  mandatory
            DESCRIPTION
                "Alarm Count "
            ::= { rS-SectionCountEntry 4 }

        cRS-SectionCountBIP  OBJECT-TYPE
            SYNTAX  INTEGER
            ACCESS  read-only
            STATUS  mandatory
            DESCRIPTION
                "Alarm Count"
            ::= { rS-SectionCountEntry 5 }

--
--  MS-Line Layer Alarm Status Table
--


    cMS-LineCurrStTable        OBJECT IDENTIFIER ::= { currentAlarmStatusTable 3 }

        cMS-LineStatusTable  OBJECT-TYPE
            SYNTAX  SEQUENCE OF MS-LineStatusEntry
            ACCESS  not-accessible
            STATUS  mandatory
            DESCRIPTION
                "MS-Linesical layer Alarm Status Table"
            ::= { cMS-LineCurrStTable 1 }

        mS-LineStatusEntry  OBJECT-TYPE
            SYNTAX  MS-LineStatusEntry
            ACCESS  not-accessible
            STATUS  mandatory
            DESCRIPTION
                "MS-Linesical Alarm entry"
            INDEX { cMS-LineStatusXCUIndex , cMS-LineStatusPortIndex }
            ::= { cMS-LineStatusTable 1 }

        MS-LineStatusEntry ::= SEQUENCE {
            cMS-LineStatusXCUIndex      XcuNum,
            cMS-LineStatusPortIndex     PortNum,
            cMS-LineStatusSD            AlmStatus,
            cMS-LineStatusSF            AlmStatus,
            cMS-LineStatusAIS           AlmStatus,
            cMS-LineStatusRDI           AlmStatus,
            cMS-LineStatusBIP           AlmStatus,
            cMS-LineStatusREI           AlmStatus
        }

        cMS-LineStatusXCUIndex  OBJECT-TYPE
            SYNTAX  XcuNum
            ACCESS  read-only
            STATUS  mandatory
            DESCRIPTION
                "Alarm XCU Index"
            ::= { mS-LineStatusEntry 1 }

        cMS-LineStatusPortIndex  OBJECT-TYPE
            SYNTAX  PortNum
            ACCESS  read-only
            STATUS  mandatory
            DESCRIPTION
                "Alarm Port Index"
            ::= { mS-LineStatusEntry 2 }

        cMS-LineStatusSD  OBJECT-TYPE
            SYNTAX  AlmStatus
            ACCESS  read-only
            STATUS  mandatory
            DESCRIPTION
                "Alarm Status"
            ::= { mS-LineStatusEntry 3 }

        cMS-LineStatusSF  OBJECT-TYPE
            SYNTAX  AlmStatus
            ACCESS  read-only
            STATUS  mandatory
            DESCRIPTION
                "Alarm Status"
            ::= { mS-LineStatusEntry 4 }

        cMS-LineStatusAIS  OBJECT-TYPE
            SYNTAX  AlmStatus
            ACCESS  read-only
            STATUS  mandatory
            DESCRIPTION
                "Alarm Status"
            ::= { mS-LineStatusEntry 5 }

        cMS-LineStatusRDI  OBJECT-TYPE
            SYNTAX  AlmStatus
            ACCESS  read-only
            STATUS  mandatory
            DESCRIPTION
                "Alarm Status"
            ::= { mS-LineStatusEntry 6 }

        cMS-LineStatusBIP  OBJECT-TYPE
            SYNTAX  AlmStatus
            ACCESS  read-only
            STATUS  mandatory
            DESCRIPTION
                "Alarm Status"
            ::= { mS-LineStatusEntry 7 }

        cMS-LineStatusREI  OBJECT-TYPE
            SYNTAX  AlmStatus
            ACCESS  read-only
            STATUS  mandatory
            DESCRIPTION
                "Alarm Status"
            ::= { mS-LineStatusEntry 8 }

-- Count Table

        cMS-LineCountTable  OBJECT-TYPE
            SYNTAX  SEQUENCE OF MS-LineCountEntry
            ACCESS  not-accessible
            STATUS  mandatory
            DESCRIPTION
                "MS-Line layer Alarm Count Table"
            ::= { cMS-LineCurrStTable 2 }

        mS-LineCountEntry  OBJECT-TYPE
            SYNTAX  MS-LineCountEntry
            ACCESS  not-accessible
            STATUS  mandatory
            DESCRIPTION
                "MS-Line Alarm entry"
            INDEX { cMS-LineCountXCUIndex , cMS-LineCountPortIndex }
            ::= { cMS-LineCountTable 1 }

        MS-LineCountEntry ::= SEQUENCE {
            cMS-LineCountXCUIndex       XcuNum,
            cMS-LineCountPortIndex      PortNum,
            cMS-LineCountSD             INTEGER,
            cMS-LineCountSF             INTEGER,
            cMS-LineCountAIS            INTEGER,
            cMS-LineCountRDI            INTEGER,
            cMS-LineCountBIP            INTEGER,
            cMS-LineCountREI            INTEGER
        }

        cMS-LineCountXCUIndex  OBJECT-TYPE
            SYNTAX  XcuNum
            ACCESS  read-only
            STATUS  mandatory
            DESCRIPTION
                "Alarm XCU Index"
            ::= { mS-LineCountEntry 1 }

        cMS-LineCountPortIndex  OBJECT-TYPE
            SYNTAX  PortNum
            ACCESS  read-only
            STATUS  mandatory
            DESCRIPTION
                "Alarm Port Index"
            ::= { mS-LineCountEntry 2 }

        cMS-LineCountSD  OBJECT-TYPE
            SYNTAX  INTEGER
            ACCESS  read-only
            STATUS  mandatory
            DESCRIPTION
                "Alarm Count"
            ::= { mS-LineCountEntry 3 }

        cMS-LineCountSF  OBJECT-TYPE
            SYNTAX  INTEGER
            ACCESS  read-only
            STATUS  mandatory
            DESCRIPTION
                "Alarm Count"
            ::= { mS-LineCountEntry 4 }

        cMS-LineCountAIS  OBJECT-TYPE
            SYNTAX  INTEGER
            ACCESS  read-only
            STATUS  mandatory
            DESCRIPTION
                "Alarm Count"
            ::= { mS-LineCountEntry 5 }

        cMS-LineCountRDI  OBJECT-TYPE
            SYNTAX  INTEGER
            ACCESS  read-only
            STATUS  mandatory
            DESCRIPTION
                "Alarm Count"
            ::= { mS-LineCountEntry 6 }

        cMS-LineCountBIP  OBJECT-TYPE
            SYNTAX  INTEGER
            ACCESS  read-only
            STATUS  mandatory
            DESCRIPTION
                "Alarm Count"
            ::= { mS-LineCountEntry 7 }

        cMS-LineCountREI  OBJECT-TYPE
            SYNTAX  INTEGER
            ACCESS  read-only
            STATUS  mandatory
            DESCRIPTION
                "Alarm Count"
            ::= { mS-LineCountEntry 8 }

--
--  HoPath-STSPath Layer Alarm Status Table
--

    cHo-STSPathCurrStTable  OBJECT IDENTIFIER ::= { currentAlarmStatusTable 4 }

        cHo-STSPathStatusTable  OBJECT-TYPE
            SYNTAX  SEQUENCE OF Ho-STSPathStatusEntry
            ACCESS  not-accessible
            STATUS  mandatory
            DESCRIPTION
                "HoPath-STSPath layer Alarm Status Table"
            ::= { cHo-STSPathCurrStTable 1 }

        ho-STSPathStatusEntry  OBJECT-TYPE
            SYNTAX  Ho-STSPathStatusEntry
            ACCESS  not-accessible
            STATUS  mandatory
            DESCRIPTION
                "HoPath-STSPath Alarm entry"
            INDEX { cHo-STSStatusXCUIdx , cHo-STSStatusPortIdx ,
                    cHo-STSStatusAug1Sts3Idx , cHo-STSStatusVc3Sts1Idx }
            ::= { cHo-STSPathStatusTable 1 }

        Ho-STSPathStatusEntry ::= SEQUENCE {
            cHo-STSStatusXCUIdx         XcuNum,
            cHo-STSStatusPortIdx        PortNum,
            cHo-STSStatusAug1Sts3Idx    Aug1Sts3Num,
            cHo-STSStatusVc3Sts1Idx     Vc3Sts1Num,
            cHo-STSStatusMappingType    HoMappingType,
            cHo-STSStatusLOP            AlmStatus,
            cHo-STSStatusAIS            AlmStatus,
            cHo-STSStatusSD             AlmStatus,
            cHo-STSStatusSF             AlmStatus,
            cHo-STSStatusTIM            AlmStatus,
            cHo-STSStatusUNEQ           AlmStatus,
            cHo-STSStatusPLM            AlmStatus,
            cHo-STSStatusRDI-S          AlmStatus,
            cHo-STSStatusRDI-C          AlmStatus,
            cHo-STSStatusRDI-P          AlmStatus,
            cHo-STSStatusBIP            AlmStatus,
            cHo-STSStatusREI            AlmStatus,
            cHo-STSStatusLOM            AlmStatus,
            cHo-STSStatusPJ             INTEGER,
            cHo-STSStatusNJ             INTEGER
        }

        cHo-STSStatusXCUIdx  OBJECT-TYPE
            SYNTAX  XcuNum
            ACCESS  read-only
            STATUS  mandatory
            DESCRIPTION
                "Alarm XCU index"
            ::= { ho-STSPathStatusEntry 1 }

        cHo-STSStatusPortIdx  OBJECT-TYPE
            SYNTAX  PortNum
            ACCESS  read-only
            STATUS  mandatory
            DESCRIPTION
                "Alarm Port index"
            ::= { ho-STSPathStatusEntry 2 }

        cHo-STSStatusAug1Sts3Idx  OBJECT-TYPE
            SYNTAX  Aug1Sts3Num
            ACCESS  read-only
            STATUS  mandatory
            DESCRIPTION
                "line stm1/sts3 index"
            ::= { ho-STSPathStatusEntry 3 }

        cHo-STSStatusVc3Sts1Idx  OBJECT-TYPE
            SYNTAX  Vc3Sts1Num
            ACCESS  read-only
            STATUS  mandatory
            DESCRIPTION
                "line au3/sts1/tug3 index"
            ::= { ho-STSPathStatusEntry 4 }

        cHo-STSStatusMappingType  OBJECT-TYPE
            SYNTAX  HoMappingType
            ACCESS  read-only
            STATUS  mandatory
            DESCRIPTION
                "Alarm Status Mapping Type"
            ::= { ho-STSPathStatusEntry 5 }

        cHo-STSStatusLOP  OBJECT-TYPE
            SYNTAX  AlmStatus
            ACCESS  read-only
            STATUS  mandatory
            DESCRIPTION
                "Alarm Status"
            ::= { ho-STSPathStatusEntry 6 }

        cHo-STSStatusAIS  OBJECT-TYPE
            SYNTAX  AlmStatus
            ACCESS  read-only
            STATUS  mandatory
            DESCRIPTION
                "Alarm Status"
            ::= { ho-STSPathStatusEntry 7 }

        cHo-STSStatusSD  OBJECT-TYPE
            SYNTAX  AlmStatus
            ACCESS  read-only
            STATUS  mandatory
            DESCRIPTION
                "Alarm Status"
            ::= { ho-STSPathStatusEntry 8 }

        cHo-STSStatusSF  OBJECT-TYPE
            SYNTAX  AlmStatus
            ACCESS  read-only
            STATUS  mandatory
            DESCRIPTION
                "Alarm Status"
            ::= { ho-STSPathStatusEntry 9 }

        cHo-STSStatusTIM  OBJECT-TYPE
            SYNTAX  AlmStatus
            ACCESS  read-only
            STATUS  mandatory
            DESCRIPTION
                "Alarm Status"
            ::= { ho-STSPathStatusEntry 10 }

        cHo-STSStatusUNEQ  OBJECT-TYPE
            SYNTAX  AlmStatus
            ACCESS  read-only
            STATUS  mandatory
            DESCRIPTION
                "Alarm Status"
            ::= { ho-STSPathStatusEntry 11 }

        cHo-STSStatusPLM  OBJECT-TYPE
            SYNTAX  AlmStatus
            ACCESS  read-only
            STATUS  mandatory
            DESCRIPTION
                "Alarm Status"
            ::= { ho-STSPathStatusEntry 12 }

        cHo-STSStatusRDI-S  OBJECT-TYPE
            SYNTAX  AlmStatus
            ACCESS  read-only
            STATUS  mandatory
            DESCRIPTION
                "Alarm Status"
            ::= { ho-STSPathStatusEntry 13 }

        cHo-STSStatusRDI-C  OBJECT-TYPE
            SYNTAX  AlmStatus
            ACCESS  read-only
            STATUS  mandatory
            DESCRIPTION
                "Alarm Status"
            ::= { ho-STSPathStatusEntry 14 }

        cHo-STSStatusRDI-P  OBJECT-TYPE
            SYNTAX  AlmStatus
            ACCESS  read-only
            STATUS  mandatory
            DESCRIPTION
                "Alarm Status"
            ::= { ho-STSPathStatusEntry 15 }

        cHo-STSStatusBIP  OBJECT-TYPE
            SYNTAX  AlmStatus
            ACCESS  read-only
            STATUS  mandatory
            DESCRIPTION
                "Alarm Status"
            ::= { ho-STSPathStatusEntry 16 }

        cHo-STSStatusREI  OBJECT-TYPE
            SYNTAX  AlmStatus
            ACCESS  read-only
            STATUS  mandatory
            DESCRIPTION
                "Alarm Status"
            ::= { ho-STSPathStatusEntry 17 }

        cHo-STSStatusLOM  OBJECT-TYPE
            SYNTAX  AlmStatus
            ACCESS  read-only
            STATUS  mandatory
            DESCRIPTION
                "Alarm Status Enable/Disable"
            ::= { ho-STSPathStatusEntry 18 }

        cHo-STSStatusPJ  OBJECT-TYPE
            SYNTAX  INTEGER
            ACCESS  read-only
            STATUS  mandatory
            DESCRIPTION
                "Alarm Status"
            ::= { ho-STSPathStatusEntry 19 }

        cHo-STSStatusNJ  OBJECT-TYPE
            SYNTAX  INTEGER
            ACCESS  read-only
            STATUS  mandatory
            DESCRIPTION
                "Alarm Status"
            ::= { ho-STSPathStatusEntry 20 }

-- Count Table

        cHo-STSPathCountTable  OBJECT-TYPE
            SYNTAX  SEQUENCE OF Ho-STSPathCountEntry
            ACCESS  not-accessible
            STATUS  mandatory
            DESCRIPTION
                "HoPath-STSPath layer Alarm Count Table"
            ::= { cHo-STSPathCurrStTable 2 }

        ho-STSPathCountEntry  OBJECT-TYPE
            SYNTAX  Ho-STSPathCountEntry
            ACCESS  not-accessible
            STATUS  mandatory
            DESCRIPTION
                "HoPath-STSPath Alarm entry"
            INDEX { cHo-STSCountXCUIdx , cHo-STSCountPortIdx ,
                    cHo-STSCountAug1Sts3Idx , cHo-STSCountVc3Sts1Idx }
            ::= { cHo-STSPathCountTable 1 }

        Ho-STSPathCountEntry ::= SEQUENCE {
            cHo-STSCountXCUIdx          XcuNum,
            cHo-STSCountPortIdx         PortNum,
            cHo-STSCountAug1Sts3Idx     Aug1Sts3Num,
            cHo-STSCountVc3Sts1Idx      Vc3Sts1Num,
            cHo-STSCountMappingType     HoMappingType,
            cHo-STSCountLOP             INTEGER,
            cHo-STSCountAIS             INTEGER,
            cHo-STSCountSD              INTEGER,
            cHo-STSCountSF              INTEGER,
            cHo-STSCountTIM             INTEGER,
            cHo-STSCountUNEQ            INTEGER,
            cHo-STSCountPLM             INTEGER,
            cHo-STSCountRDI-S           INTEGER,
            cHo-STSCountRDI-C           INTEGER,
            cHo-STSCountRDI-P           INTEGER,
            cHo-STSCountBIP             INTEGER,
            cHo-STSCountREI             INTEGER,
            cHo-STSCountLOM             INTEGER
        }

        cHo-STSCountXCUIdx  OBJECT-TYPE
            SYNTAX  XcuNum
            ACCESS  read-only
            STATUS  mandatory
            DESCRIPTION
                "Alarm XCU index"
            ::= { ho-STSPathCountEntry 1 }

        cHo-STSCountPortIdx  OBJECT-TYPE
            SYNTAX  PortNum
            ACCESS  read-only
            STATUS  mandatory
            DESCRIPTION
                "Alarm Port index"
            ::= { ho-STSPathCountEntry 2 }

        cHo-STSCountAug1Sts3Idx  OBJECT-TYPE
            SYNTAX  Aug1Sts3Num
            ACCESS  read-only
            STATUS  mandatory
            DESCRIPTION
                "line stm1/sts3 index"
            ::= { ho-STSPathCountEntry 3 }

        cHo-STSCountVc3Sts1Idx  OBJECT-TYPE
            SYNTAX  Vc3Sts1Num
            ACCESS  read-only
            STATUS  mandatory
            DESCRIPTION
                "line au3/sts1/tug3 index"
            ::= { ho-STSPathCountEntry 4 }

        cHo-STSCountMappingType  OBJECT-TYPE
            SYNTAX  HoMappingType
            ACCESS  read-only
            STATUS  mandatory
            DESCRIPTION
                "Alarm Count Mapping Type"
            ::= { ho-STSPathCountEntry 5 }

        cHo-STSCountLOP  OBJECT-TYPE
            SYNTAX  INTEGER
            ACCESS  read-only
            STATUS  mandatory
            DESCRIPTION
                "Alarm Count"
            ::= { ho-STSPathCountEntry 6 }

        cHo-STSCountAIS  OBJECT-TYPE
            SYNTAX  INTEGER
            ACCESS  read-only
            STATUS  mandatory
            DESCRIPTION
                "Alarm Count"
            ::= { ho-STSPathCountEntry 7 }

        cHo-STSCountSD  OBJECT-TYPE
            SYNTAX  INTEGER
            ACCESS  read-only
            STATUS  mandatory
            DESCRIPTION
                "Alarm Count"
            ::= { ho-STSPathCountEntry 8 }

        cHo-STSCountSF  OBJECT-TYPE
            SYNTAX  INTEGER
            ACCESS  read-only
            STATUS  mandatory
            DESCRIPTION
                "Alarm Count"
            ::= { ho-STSPathCountEntry 9 }

        cHo-STSCountTIM  OBJECT-TYPE
            SYNTAX  INTEGER
            ACCESS  read-only
            STATUS  mandatory
            DESCRIPTION
                "Alarm Count"
            ::= { ho-STSPathCountEntry 10 }

        cHo-STSCountUNEQ  OBJECT-TYPE
            SYNTAX  INTEGER
            ACCESS  read-only
            STATUS  mandatory
            DESCRIPTION
                "Alarm Count"
            ::= { ho-STSPathCountEntry 11 }

        cHo-STSCountPLM  OBJECT-TYPE
            SYNTAX  INTEGER
            ACCESS  read-only
            STATUS  mandatory
            DESCRIPTION
                "Alarm Count"
            ::= { ho-STSPathCountEntry 12 }

        cHo-STSCountRDI-S  OBJECT-TYPE
            SYNTAX  INTEGER
            ACCESS  read-only
            STATUS  mandatory
            DESCRIPTION
                "Alarm Count"
            ::= { ho-STSPathCountEntry 13 }

        cHo-STSCountRDI-C  OBJECT-TYPE
            SYNTAX  INTEGER
            ACCESS  read-only
            STATUS  mandatory
            DESCRIPTION
                "Alarm Count"
            ::= { ho-STSPathCountEntry 14 }

        cHo-STSCountRDI-P  OBJECT-TYPE
            SYNTAX  INTEGER
            ACCESS  read-only
            STATUS  mandatory
            DESCRIPTION
                "Alarm Count"
            ::= { ho-STSPathCountEntry 15 }

        cHo-STSCountBIP  OBJECT-TYPE
            SYNTAX  INTEGER
            ACCESS  read-only
            STATUS  mandatory
            DESCRIPTION
                "Alarm Count"
            ::= { ho-STSPathCountEntry 16 }

        cHo-STSCountREI  OBJECT-TYPE
            SYNTAX  INTEGER
            ACCESS  read-only
            STATUS  mandatory
            DESCRIPTION
                "Alarm Count"
            ::= { ho-STSPathCountEntry 17 }

        cHo-STSCountLOM  OBJECT-TYPE
            SYNTAX  INTEGER
            ACCESS  read-only
            STATUS  mandatory
            DESCRIPTION
                "Alarm Count"
            ::= { ho-STSPathCountEntry 18 }

--
--  LoPath-VTPath Layer Alarm Status Table
--

    cLo-VTPathCurrStTable   OBJECT IDENTIFIER ::= { currentAlarmStatusTable 5 }

        cLo-VTPathStatusTable  OBJECT-TYPE
            SYNTAX  SEQUENCE OF Lo-VTPathStatusEntry
            ACCESS  not-accessible
            STATUS  mandatory
            DESCRIPTION
                "LoPath-VTPath layer Alarm Status Table"
            ::= { cLo-VTPathCurrStTable 1 }

        lo-VTPathStatusEntry  OBJECT-TYPE
            SYNTAX  Lo-VTPathStatusEntry
            ACCESS  not-accessible
            STATUS  mandatory
            DESCRIPTION
                "LoPath-VTPath Alarm entry"
            INDEX { cLo-VTStatusXCUIdx , cLo-VTStatusPortIdx ,
                    cLo-VTStatusAug1Sts3Index , cLo-VTStatusVc3Sts1Index ,
                    cLo-VTStatusTU1xVTxIdx }
            ::= { cLo-VTPathStatusTable 1 }

        Lo-VTPathStatusEntry ::= SEQUENCE {
            cLo-VTStatusXCUIdx          XcuNum,
            cLo-VTStatusPortIdx         PortNum,
            cLo-VTStatusAug1Sts3Index   Aug1Sts3Num,
            cLo-VTStatusVc3Sts1Index    Vc3Sts1Num,
            cLo-VTStatusTU1xVTxIdx      TU1xVtxNum,
            cLo-VTStatusMappingType     LoMappingType,
            cLo-VTStatusLOP             AlmStatus,
            cLo-VTStatusAIS             AlmStatus,
            cLo-VTStatusSD              AlmStatus,
            cLo-VTStatusSF              AlmStatus,
            cLo-VTStatusTIM             AlmStatus,
            cLo-VTStatusUNEQ            AlmStatus,
            cLo-VTStatusPLM             AlmStatus,
            cLo-VTStatusRDI-S           AlmStatus,
            cLo-VTStatusRDI-C           AlmStatus,
            cLo-VTStatusRDI-P           AlmStatus,
            cLo-VTStatusBIP             AlmStatus,
            cLo-VTStatusREI             AlmStatus,
            cLo-VTStatusPJ              INTEGER,
            cLo-VTStatusNJ              INTEGER
        }

        cLo-VTStatusXCUIdx  OBJECT-TYPE
            SYNTAX  XcuNum
            ACCESS  read-only
            STATUS  mandatory
            DESCRIPTION
                "Alarm XCU Index"
            ::= { lo-VTPathStatusEntry 1 }

        cLo-VTStatusPortIdx  OBJECT-TYPE
            SYNTAX  PortNum
            ACCESS  read-only
            STATUS  mandatory
            DESCRIPTION
                "Alarm Port Index"
            ::= { lo-VTPathStatusEntry 2 }

        cLo-VTStatusAug1Sts3Index  OBJECT-TYPE
            SYNTAX  Aug1Sts3Num
            ACCESS  read-only
            STATUS  mandatory
            DESCRIPTION
                "line stm1/sts3 index"
            ::= { lo-VTPathStatusEntry 3 }

        cLo-VTStatusVc3Sts1Index  OBJECT-TYPE
            SYNTAX  Vc3Sts1Num
            ACCESS  read-only
            STATUS  mandatory
            DESCRIPTION
                "line au3/sts1/tug3 index"
            ::= { lo-VTPathStatusEntry 4 }

        cLo-VTStatusTU1xVTxIdx  OBJECT-TYPE
            SYNTAX  TU1xVtxNum
            ACCESS  read-only
            STATUS  mandatory
            DESCRIPTION
                "line au3/sts1/tug3 index"
            ::= { lo-VTPathStatusEntry 5 }

        cLo-VTStatusMappingType  OBJECT-TYPE
            SYNTAX  LoMappingType
            ACCESS  read-only
            STATUS  mandatory
            DESCRIPTION
                "Alarm Status mapping type"
            ::= { lo-VTPathStatusEntry 6 }

        cLo-VTStatusLOP  OBJECT-TYPE
            SYNTAX  AlmStatus
            ACCESS  read-only
            STATUS  mandatory
            DESCRIPTION
                "Alarm Status "
            ::= { lo-VTPathStatusEntry 7 }

        cLo-VTStatusAIS  OBJECT-TYPE
            SYNTAX  AlmStatus
            ACCESS  read-only
            STATUS  mandatory
            DESCRIPTION
                "Alarm Status"
            ::= { lo-VTPathStatusEntry 8 }

        cLo-VTStatusSD  OBJECT-TYPE
            SYNTAX  AlmStatus
            ACCESS  read-only
            STATUS  mandatory
            DESCRIPTION
                "Alarm Status "
            ::= { lo-VTPathStatusEntry 9 }

        cLo-VTStatusSF  OBJECT-TYPE
            SYNTAX  AlmStatus
            ACCESS  read-only
            STATUS  mandatory
            DESCRIPTION
                "Alarm Status "
            ::= { lo-VTPathStatusEntry 10 }

        cLo-VTStatusTIM  OBJECT-TYPE
            SYNTAX  AlmStatus
            ACCESS  read-only
            STATUS  mandatory
            DESCRIPTION
                "Alarm Status "
            ::= { lo-VTPathStatusEntry 11 }

        cLo-VTStatusUNEQ  OBJECT-TYPE
            SYNTAX  AlmStatus
            ACCESS  read-only
            STATUS  mandatory
            DESCRIPTION
                "Alarm Status"
            ::= { lo-VTPathStatusEntry 12 }

        cLo-VTStatusPLM  OBJECT-TYPE
            SYNTAX  AlmStatus
            ACCESS  read-only
            STATUS  mandatory
            DESCRIPTION
                "Alarm Status "
            ::= { lo-VTPathStatusEntry 13 }

        cLo-VTStatusRDI-S  OBJECT-TYPE
            SYNTAX  AlmStatus
            ACCESS  read-only
            STATUS  mandatory
            DESCRIPTION
                "Alarm Status "
            ::= { lo-VTPathStatusEntry 14 }

        cLo-VTStatusRDI-C  OBJECT-TYPE
            SYNTAX  AlmStatus
            ACCESS  read-only
            STATUS  mandatory
            DESCRIPTION
                "Alarm Status "
            ::= { lo-VTPathStatusEntry 15 }

        cLo-VTStatusRDI-P  OBJECT-TYPE
            SYNTAX  AlmStatus
            ACCESS  read-only
            STATUS  mandatory
            DESCRIPTION
                "Alarm Status "
            ::= { lo-VTPathStatusEntry 16 }

        cLo-VTStatusBIP  OBJECT-TYPE
            SYNTAX  AlmStatus
            ACCESS  read-only
            STATUS  mandatory
            DESCRIPTION
                "Alarm Status "
            ::= { lo-VTPathStatusEntry 17 }

        cLo-VTStatusREI  OBJECT-TYPE
            SYNTAX  AlmStatus
            ACCESS  read-only
            STATUS  mandatory
            DESCRIPTION
                "Alarm Status "
            ::= { lo-VTPathStatusEntry 18 }

        cLo-VTStatusPJ  OBJECT-TYPE
            SYNTAX  INTEGER
            ACCESS  read-only
            STATUS  mandatory
            DESCRIPTION
                "Alarm Status "
            ::= { lo-VTPathStatusEntry 19 }

        cLo-VTStatusNJ  OBJECT-TYPE
            SYNTAX  INTEGER
            ACCESS  read-only
            STATUS  mandatory
            DESCRIPTION
                "Alarm Status "
            ::= { lo-VTPathStatusEntry 20 }

-- Count Table

        cLo-VTPathCountTable  OBJECT-TYPE
            SYNTAX  SEQUENCE OF Lo-VTPathCountEntry
            ACCESS  not-accessible
            STATUS  mandatory
            DESCRIPTION
                "LoPath-VTPath layer Alarm Count Table"
            ::= { cLo-VTPathCurrStTable 2 }

        lo-VTPathCountEntry  OBJECT-TYPE
            SYNTAX  Lo-VTPathCountEntry
            ACCESS  not-accessible
            STATUS  mandatory
            DESCRIPTION
                "LoPath-VTPath Alarm entry"
            INDEX { cLo-VTCountXCUIdx , cLo-VTCountPortIdx ,
                    cLo-VTCountAug1Sts3Idx , cLo-VTCountVc3Sts1Idx ,
                    cLo-VTCountTU1xVTxIdx }
            ::= { cLo-VTPathCountTable 1 }

        Lo-VTPathCountEntry ::= SEQUENCE {
            cLo-VTCountXCUIdx           XcuNum,
            cLo-VTCountPortIdx          PortNum,
            cLo-VTCountAug1Sts3Idx      Aug1Sts3Num,
            cLo-VTCountVc3Sts1Idx       Vc3Sts1Num,
            cLo-VTCountTU1xVTxIdx       TU1xVtxNum,
            cLo-VTCountMappingType      LoMappingType,
            cLo-VTCountLOP              INTEGER,
            cLo-VTCountAIS              INTEGER,
            cLo-VTCountSD               INTEGER,
            cLo-VTCountSF               INTEGER,
            cLo-VTCountTIM              INTEGER,
            cLo-VTCountUNEQ             INTEGER,
            cLo-VTCountPLM              INTEGER,
            cLo-VTCountRDI-S            INTEGER,
            cLo-VTCountRDI-C            INTEGER,
            cLo-VTCountRDI-P            INTEGER,
            cLo-VTCountBIP              INTEGER,
            cLo-VTCountREI              INTEGER
        }

        cLo-VTCountXCUIdx  OBJECT-TYPE
            SYNTAX  XcuNum
            ACCESS  read-only
            STATUS  mandatory
            DESCRIPTION
                "Alarm Port Index"
            ::= { lo-VTPathCountEntry 1 }

        cLo-VTCountPortIdx  OBJECT-TYPE
            SYNTAX  PortNum
            ACCESS  read-only
            STATUS  mandatory
            DESCRIPTION
                "Alarm Port Index"
            ::= { lo-VTPathCountEntry 2 }

        cLo-VTCountAug1Sts3Idx  OBJECT-TYPE
            SYNTAX  Aug1Sts3Num
            ACCESS  read-only
            STATUS  mandatory
            DESCRIPTION
                "line stm1/sts3 index"
            ::= { lo-VTPathCountEntry 3 }

        cLo-VTCountVc3Sts1Idx  OBJECT-TYPE
            SYNTAX  Vc3Sts1Num
            ACCESS  read-only
            STATUS  mandatory
            DESCRIPTION
                "line au3/sts1/tug3 index"
            ::= { lo-VTPathCountEntry 4 }

        cLo-VTCountTU1xVTxIdx  OBJECT-TYPE
            SYNTAX  TU1xVtxNum
            ACCESS  read-only
            STATUS  mandatory
            DESCRIPTION
                "line au3/sts1/tug3 index"
            ::= { lo-VTPathCountEntry 5 }

        cLo-VTCountMappingType  OBJECT-TYPE
            SYNTAX  LoMappingType
            ACCESS  read-only
            STATUS  mandatory
            DESCRIPTION
                "Alarm Count mapping type"
            ::= { lo-VTPathCountEntry 6 }

        cLo-VTCountLOP  OBJECT-TYPE
            SYNTAX  INTEGER
            ACCESS  read-only
            STATUS  mandatory
            DESCRIPTION
                "Alarm Count"
            ::= { lo-VTPathCountEntry 7 }

        cLo-VTCountAIS  OBJECT-TYPE
            SYNTAX  INTEGER
            ACCESS  read-only
            STATUS  mandatory
            DESCRIPTION
                "Alarm Count"
            ::= { lo-VTPathCountEntry 8 }

        cLo-VTCountSD  OBJECT-TYPE
            SYNTAX  INTEGER
            ACCESS  read-only
            STATUS  mandatory
            DESCRIPTION
                "Alarm Count"
            ::= { lo-VTPathCountEntry 9 }

        cLo-VTCountSF  OBJECT-TYPE
            SYNTAX  INTEGER
            ACCESS  read-only
            STATUS  mandatory
            DESCRIPTION
                "Alarm Count"
            ::= { lo-VTPathCountEntry 10 }

        cLo-VTCountTIM  OBJECT-TYPE
            SYNTAX  INTEGER
            ACCESS  read-only
            STATUS  mandatory
            DESCRIPTION
                "Alarm Count"
            ::= { lo-VTPathCountEntry 11 }

        cLo-VTCountUNEQ  OBJECT-TYPE
            SYNTAX  INTEGER
            ACCESS  read-only
            STATUS  mandatory
            DESCRIPTION
                "Alarm Count"
            ::= { lo-VTPathCountEntry 12 }

        cLo-VTCountPLM  OBJECT-TYPE
            SYNTAX  INTEGER
            ACCESS  read-only
            STATUS  mandatory
            DESCRIPTION
                "Alarm Count"
            ::= { lo-VTPathCountEntry 13 }

        cLo-VTCountRDI-S  OBJECT-TYPE
            SYNTAX  INTEGER
            ACCESS  read-only
            STATUS  mandatory
            DESCRIPTION
                "Alarm Count"
            ::= { lo-VTPathCountEntry 14 }

        cLo-VTCountRDI-C  OBJECT-TYPE
            SYNTAX  INTEGER
            ACCESS  read-only
            STATUS  mandatory
            DESCRIPTION
                "Alarm Count"
            ::= { lo-VTPathCountEntry 15 }

        cLo-VTCountRDI-P  OBJECT-TYPE
            SYNTAX  INTEGER
            ACCESS  read-only
            STATUS  mandatory
            DESCRIPTION
                "Alarm Count"
            ::= { lo-VTPathCountEntry 16 }

        cLo-VTCountBIP  OBJECT-TYPE
            SYNTAX  INTEGER
            ACCESS  read-only
            STATUS  mandatory
            DESCRIPTION
                "Alarm Count"
            ::= { lo-VTPathCountEntry 17 }

        cLo-VTCountREI  OBJECT-TYPE
            SYNTAX  INTEGER
            ACCESS  read-only
            STATUS  mandatory
            DESCRIPTION
                "Alarm Count"
            ::= { lo-VTPathCountEntry 18 }

--
--  Alarm Status Hex Table
--
    alarmStatusHexTable  OBJECT IDENTIFIER ::= { currentAlarmStatusTable 6 }

        systemAlarmStatusHex  OBJECT-TYPE
            SYNTAX  OCTET STRING(SIZE(8))
            ACCESS  read-only
            STATUS  mandatory
            DESCRIPTION
                "system alarm status in Hex"
            ::= { alarmStatusHexTable 1 }


        lineAlarmStatusHex  OBJECT-TYPE
            SYNTAX  OCTET STRING(SIZE(17))
            ACCESS  read-only
            STATUS  mandatory
            DESCRIPTION
                "Line alarm status in Hex"
            ::= { alarmStatusHexTable 2 }

        hpAlarmStatusHex  OBJECT-TYPE
            SYNTAX  OCTET STRING(SIZE(97))
            ACCESS  read-only
            STATUS  mandatory
            DESCRIPTION
                "hp alarm mask in Hex"
            ::= { alarmStatusHexTable 3 }

        lpXCU1Port1AlarmStatusHex  OBJECT-TYPE
            SYNTAX  OCTET STRING(SIZE(673))
            ACCESS  read-only
            STATUS  mandatory
            DESCRIPTION
                "XCU#1 Port#1 lp alarm status in Hex"
            ::= { alarmStatusHexTable 4 }

        lpXCU1Port2AlarmStatusHex  OBJECT-TYPE
            SYNTAX  OCTET STRING(SIZE(673))
            ACCESS  read-only
            STATUS  mandatory
            DESCRIPTION
                "XCU#1 Port#2 lp alarm status in Hex"
            ::= { alarmStatusHexTable 5 }

        lpXCU2Port1AlarmStatusHex  OBJECT-TYPE
            SYNTAX  OCTET STRING(SIZE(673))
            ACCESS  read-only
            STATUS  mandatory
            DESCRIPTION
                "XCU#2 Port#1 lp alarm status in Hex"
            ::= { alarmStatusHexTable 6 }

        lpXCU2Port2AlarmStatusHex  OBJECT-TYPE
            SYNTAX  OCTET STRING(SIZE(673))
            ACCESS  read-only
            STATUS  mandatory
            DESCRIPTION
                "XCU#2 Port#1 lp alarm status in Hex"
            ::= { alarmStatusHexTable 7 }

        externalAlarmStatusHex  OBJECT-TYPE
            SYNTAX  OCTET STRING(SIZE(2))
            ACCESS  read-only
            STATUS  mandatory
            DESCRIPTION
                "external alarm status in Hex"
            ::= { alarmStatusHexTable 8 }


--
--  Alarm Queue Table
--
        alarmQueueTable  OBJECT-TYPE
            SYNTAX  SEQUENCE OF AlarmQueueEntry
            ACCESS  not-accessible
            STATUS  mandatory
            DESCRIPTION
                "Alarm Queue Table."
            ::= { system 7 }

        alarmQueueEntry  OBJECT-TYPE
            SYNTAX  AlarmQueueEntry
            ACCESS  not-accessible
            STATUS  mandatory
            DESCRIPTION
                "alarm Queue entry"
            INDEX { alarmQueueIndex }
            ::= { alarmQueueTable 1 }

        AlarmQueueEntry ::= SEQUENCE {
            alarmQueueIndex             INTEGER (1..300),
            alarmQueueString            DisplayString (SIZE(0..255)),
            alarmQueueTimeStamp         DisplayString (SIZE(0..255)),
            alarmQueueSubrack           INTEGER,
            alarmQueueUnit              CardID,
            alarmQueueCardModel         CardModel,
            alarmQueueRegModel          RegModel,
            alarmQueuePortNum           PortID,
            alarmQueueVcChan            INTEGER,
            alarmQueueAlmNum            AlarmNum,
            alarmQueueVC43STS31Type     Au4Au3Type,
            alarmQueueTU1xVTxType       Tu1xVtxType,
            alarmQueueVC4STS3           Aug1Sts3Num,
            alarmQueueVC3TUG3           INTEGER,
            alarmQueueTUG2VTG           INTEGER,
            alarmQueueTU1xVTx           INTEGER,
            alarmQueueStatus            AlmStatus,
            alarmQueueSeverity          Severity
        }

        alarmQueueIndex  OBJECT-TYPE
            SYNTAX  INTEGER (1..300)
            ACCESS  read-only
            STATUS  mandatory
            DESCRIPTION
                "Select Alarm Queue Index(1-200)"
            ::= { alarmQueueEntry 1 }

        alarmQueueString  OBJECT-TYPE
            SYNTAX  DisplayString (SIZE (0..255))
            ACCESS  read-only
            STATUS  mandatory
            DESCRIPTION
                "Alarm Queue String"
            ::= { alarmQueueEntry 2 }

        alarmQueueTimeStamp  OBJECT-TYPE
            SYNTAX  DisplayString (SIZE (0..255))
            ACCESS  read-only
            STATUS  mandatory
            DESCRIPTION
                "Alarm Time Stamp"
            ::= { alarmQueueEntry 3 }

        alarmQueueSubrack  OBJECT-TYPE
            SYNTAX  INTEGER
            ACCESS  read-only
            STATUS  mandatory
            DESCRIPTION
                "Alarm Subrack"
            ::= { alarmQueueEntry 4 }

        alarmQueueUnit  OBJECT-TYPE
            SYNTAX  CardID
            ACCESS  read-only
            STATUS  mandatory
            DESCRIPTION
            "Xcu or Unit 1~4,11~16"
            ::= { alarmQueueEntry 5 }

        alarmQueueCardModel  OBJECT-TYPE
            SYNTAX  CardModel
            ACCESS  read-only
            STATUS  mandatory
            DESCRIPTION
                "Card Model"
            ::= { alarmQueueEntry 6 }

        alarmQueueRegModel  OBJECT-TYPE
            SYNTAX  RegModel
            ACCESS  read-only
            STATUS  mandatory
            DESCRIPTION
                "Registered Model"
            ::= { alarmQueueEntry 7 }

        alarmQueuePortNum  OBJECT-TYPE
            SYNTAX  PortID
            ACCESS  read-only
            STATUS  mandatory
            DESCRIPTION
                "Port number(1..64)"
            ::= { alarmQueueEntry 8 }

        alarmQueueVcChan  OBJECT-TYPE
            SYNTAX  INTEGER
            ACCESS  read-only
            STATUS  mandatory
            DESCRIPTION
                "VC Channel"
            ::= { alarmQueueEntry 9 }

        alarmQueueAlmNum  OBJECT-TYPE
            SYNTAX  AlarmNum
            ACCESS  read-only
            STATUS  mandatory
            DESCRIPTION
                "Alarm Num"
            ::= { alarmQueueEntry 10 }

        alarmQueueVC43STS31Type  OBJECT-TYPE
            SYNTAX  Au4Au3Type
            ACCESS  read-only
            STATUS  mandatory
            DESCRIPTION
                "AU4 or AU3 type in SDH, STS-3c or STS-1 type in SONET"
            ::= { alarmQueueEntry 11 }

        alarmQueueTU1xVTxType  OBJECT-TYPE
            SYNTAX  Tu1xVtxType
            ACCESS  read-only
            STATUS  mandatory
            DESCRIPTION
                "Tu1x type"
            ::= { alarmQueueEntry 12 }

        alarmQueueVC4STS3  OBJECT-TYPE
            SYNTAX  Aug1Sts3Num
            ACCESS  read-only
            STATUS  mandatory
            DESCRIPTION
                "The number of STM1"
            ::= { alarmQueueEntry 13 }

        alarmQueueVC3TUG3  OBJECT-TYPE
            SYNTAX  INTEGER(1..3)
            ACCESS  read-only
            STATUS  mandatory
            DESCRIPTION
                "The number of Tug3"
            ::= { alarmQueueEntry 14 }

        alarmQueueTUG2VTG  OBJECT-TYPE
            SYNTAX  INTEGER(1..7)
            ACCESS  read-only
            STATUS  mandatory
            DESCRIPTION
                "The number of Tug2"
            ::= { alarmQueueEntry 15 }

        alarmQueueTU1xVTx  OBJECT-TYPE
            SYNTAX  INTEGER(1..4)
            ACCESS  read-only
            STATUS  mandatory
            DESCRIPTION
                "The number of Tu1x"
            ::= { alarmQueueEntry 16 }

        alarmQueueStatus  OBJECT-TYPE
            SYNTAX  AlmStatus
            ACCESS  read-only
            STATUS  mandatory
            DESCRIPTION
                "The Status of Alarm"
            ::= { alarmQueueEntry 17 }

        alarmQueueSeverity  OBJECT-TYPE
            SYNTAX  Severity
            ACCESS  read-only
            STATUS  mandatory
            DESCRIPTION
                "Alarm Severity"
            ::= { alarmQueueEntry 18 }

--
--  Current Active Alarm Summary Table
--
        currentActiveAlarmTable  OBJECT-TYPE
            SYNTAX  SEQUENCE OF CurrentActiveAlarmEntry
            ACCESS  not-accessible
            STATUS  mandatory
            DESCRIPTION
                "Current Active Alarm Summary(CAAS) Table"
            ::= { system 8 }

        currentActiveAlarmEntry  OBJECT-TYPE
            SYNTAX  CurrentActiveAlarmEntry
            ACCESS  not-accessible
            STATUS  mandatory
            DESCRIPTION
                "alarm Queue entry"
            INDEX { activeAlarmIndex }
            ::= { currentActiveAlarmTable 1 }

        CurrentActiveAlarmEntry ::= SEQUENCE {
            activeAlarmIndex            INTEGER (1..10000),
            activeAlarmString           DisplayString (SIZE(0..255)),
            activeAlarmUnit             CardID,
            activeAlarmCardModel        CardModel,
            activeAlarmRegModel         RegModel,
            activeAlarmPortNum          PortID,
            activeAlarmVcChan           INTEGER,
            activeAlarmAlmNum           AlarmNum,
            activeAlarmVC43STS31Type    Au4Au3Type,
            activeAlarmTU1xVTxType      Tu1xVtxType,
            activeAlarmAUG1STS3         Aug1Sts3Num,
            activeAlarmTUG3             INTEGER,
            activeAlarmTUG2VTG          INTEGER,
            activeAlarmTU1xVTx          INTEGER,
            activeAlarmStatus           AlmStatus,
            activeAlarmSeverity         Severity
        }

        activeAlarmIndex  OBJECT-TYPE
            SYNTAX  INTEGER (1..10000)
            ACCESS  read-only
            STATUS  mandatory
            DESCRIPTION
                "Current Active Alarm Summary(CAAS) Index"
            ::= { currentActiveAlarmEntry 1 }

        activeAlarmString  OBJECT-TYPE
            SYNTAX  DisplayString (SIZE (0..255))
            ACCESS  read-only
            STATUS  mandatory
            DESCRIPTION
                "Current Active Alarm Summary String"
            ::= { currentActiveAlarmEntry 2 }

        activeAlarmUnit  OBJECT-TYPE
            SYNTAX  CardID
            ACCESS  read-only
            STATUS  mandatory
            DESCRIPTION
            "Xcu or Unit 1~4,11~16"
            ::= { currentActiveAlarmEntry 3 }

        activeAlarmCardModel  OBJECT-TYPE
            SYNTAX  CardModel
            ACCESS  read-only
            STATUS  mandatory
            DESCRIPTION
                "Card Model"
            ::= { currentActiveAlarmEntry 4 }

        activeAlarmRegModel  OBJECT-TYPE
            SYNTAX  RegModel
            ACCESS  read-only
            STATUS  mandatory
            DESCRIPTION
                "Registered Model"
            ::= { currentActiveAlarmEntry 5 }

        activeAlarmPortNum  OBJECT-TYPE
            SYNTAX  PortID
            ACCESS  read-only
            STATUS  mandatory
            DESCRIPTION
                "Port number(1..64)"
            ::= { currentActiveAlarmEntry 6 }

        activeAlarmVcChan  OBJECT-TYPE
            SYNTAX  INTEGER
            ACCESS  read-only
            STATUS  mandatory
            DESCRIPTION
                "VC Channel"
            ::= { currentActiveAlarmEntry 7 }

        activeAlarmAlmNum  OBJECT-TYPE
            SYNTAX  AlarmNum
            ACCESS  read-only
            STATUS  mandatory
            DESCRIPTION
                "Alarm Num"
            ::= { currentActiveAlarmEntry 8 }

        activeAlarmVC43STS31Type  OBJECT-TYPE
            SYNTAX  Au4Au3Type
            ACCESS  read-only
            STATUS  mandatory
            DESCRIPTION
                "AU4 or AU3 type"
            ::= { currentActiveAlarmEntry 9 }

        activeAlarmTU1xVTxType  OBJECT-TYPE
            SYNTAX  Tu1xVtxType
            ACCESS  read-only
            STATUS  mandatory
            DESCRIPTION
                "Tu1x type"
            ::= { currentActiveAlarmEntry 10 }

        activeAlarmAUG1STS3  OBJECT-TYPE
            SYNTAX  Aug1Sts3Num
            ACCESS  read-only
            STATUS  mandatory
            DESCRIPTION
                "The number of AU4"
            ::= { currentActiveAlarmEntry 11 }

        activeAlarmTUG3  OBJECT-TYPE
            SYNTAX  INTEGER
            ACCESS  read-only
            STATUS  mandatory
            DESCRIPTION
                "The number of Tug3"
            ::= { currentActiveAlarmEntry 12 }

        activeAlarmTUG2VTG  OBJECT-TYPE
            SYNTAX  INTEGER
            ACCESS  read-only
            STATUS  mandatory
            DESCRIPTION
                "The number of Tug2"
            ::= { currentActiveAlarmEntry 13 }

        activeAlarmTU1xVTx  OBJECT-TYPE
            SYNTAX  INTEGER
            ACCESS  read-only
            STATUS  mandatory
            DESCRIPTION
                "The number of Tu1x"
            ::= { currentActiveAlarmEntry 14 }

        activeAlarmStatus  OBJECT-TYPE
            SYNTAX  AlmStatus
            ACCESS  read-only
            STATUS  mandatory
            DESCRIPTION
                "The Status of Alarm"
            ::= { currentActiveAlarmEntry 15 }

        activeAlarmSeverity  OBJECT-TYPE
            SYNTAX  Severity
            ACCESS  read-only
            STATUS  mandatory
            DESCRIPTION
                "Alarm Severity"
            ::= { currentActiveAlarmEntry 16 }

--
--  SYSTEM XC Table
--
    systemXcTable      OBJECT IDENTIFIER ::= { system 9 }

--
--  SYSTEM XC Create Table
--
    systemXcCreateTable      OBJECT IDENTIFIER ::= { systemXcTable 1 }

        xcCreateGranularityType  OBJECT-TYPE
            SYNTAX  INTEGER {
                    tu3(2),
                    au3-sts1(3),
                    tu11-vt15(4),
                    tu12-vt2(5),
                    vc4-sts3c(6),
                    none(100)
                }
            ACCESS  read-write
            STATUS  mandatory
            DESCRIPTION
                "Xc Ts mapping type"
            ::= { systemXcCreateTable 1 }

        xcCreateMapIndex  OBJECT-TYPE
            SYNTAX  XcMap
            ACCESS  read-write
            STATUS  mandatory
            DESCRIPTION
                "Xc Map1/Map2"
            ::= { systemXcCreateTable 2 }

        xcCreateSrcSlot  OBJECT-TYPE
            SYNTAX  XcSlot
            ACCESS  read-write
            STATUS  mandatory
            DESCRIPTION
                "Xc source unit"
            ::= { systemXcCreateTable  3}

        xcCreateSrcPort  OBJECT-TYPE
            SYNTAX  PortID
            ACCESS  read-write
            STATUS  mandatory
            DESCRIPTION
                "Xc source Port"
            ::= { systemXcCreateTable 4 }

        xcCreateSrcChannel  OBJECT-TYPE
            SYNTAX  ChannelNum
            ACCESS  read-write
            STATUS  mandatory
            DESCRIPTION
                "Xc source channel number"
            ::= { systemXcCreateTable 5 }

        xcCreateSrcAug1Sts3Path  OBJECT-TYPE
            SYNTAX  Aug1Sts3Num
            ACCESS  read-write
            STATUS  mandatory
            DESCRIPTION
                "Xc source Aug1 path"
            ::= { systemXcCreateTable 6 }

        xcCreateSrcVc3Sts1Path  OBJECT-TYPE
            SYNTAX  Vc3Sts1Num
            ACCESS  read-write
            STATUS  mandatory
            DESCRIPTION
                "Xc source VC3/STS1 path"
            ::= { systemXcCreateTable 7 }

        xcCreateSrcVc1xVtxPath  OBJECT-TYPE
            SYNTAX  Vc1xVtxNum
            ACCESS  read-write
            STATUS  mandatory
            DESCRIPTION
                "Xc source Vc1x/vtx path"
            ::= { systemXcCreateTable 8 }

        xcCreateDesSlot  OBJECT-TYPE
            SYNTAX  XcSlot
            ACCESS  read-write
            STATUS  mandatory
            DESCRIPTION
                "Xc Des unit"
            ::= { systemXcCreateTable 9 }

        xcCreateDesPort  OBJECT-TYPE
            SYNTAX  PortID
            ACCESS  read-write
            STATUS  mandatory
            DESCRIPTION
                "Xc Des Port"
            ::= { systemXcCreateTable 10 }

        xcCreateDesChannel  OBJECT-TYPE
            SYNTAX  ChannelNum
            ACCESS  read-write
            STATUS  mandatory
            DESCRIPTION
                "Xc destination channel number"
            ::= { systemXcCreateTable 11 }

        xcCreateDesAug1Sts3Path  OBJECT-TYPE
            SYNTAX  Aug1Sts3Num
            ACCESS  read-write
            STATUS  mandatory
            DESCRIPTION
                "Xc destination Aug1 path"
            ::= { systemXcCreateTable 12 }

        xcCreateDesVc3Sts1Path  OBJECT-TYPE
            SYNTAX  Vc3Sts1Num
            ACCESS  read-write
            STATUS  mandatory
            DESCRIPTION
                "Xc Des VC3/STS1 path"
            ::= { systemXcCreateTable 13 }

        xcCreateDesVc1xVtxPath  OBJECT-TYPE
            SYNTAX  Vc1xVtxNum
            ACCESS  read-write
            STATUS  mandatory
            DESCRIPTION
                "Xc Des Vc1x/vtx path"
            ::= { systemXcCreateTable 14 }

        xcCreateXcType  OBJECT-TYPE
            -- SYNTAX  XcType elvis comment
            SYNTAX  INTEGER {
                    uni-xc(1),
                    bi-xc(2),
                    not-available(100)
                }
            ACCESS  read-write
            STATUS  mandatory
            DESCRIPTION
                "Xc type"
            ::= { systemXcCreateTable 15 }

        xcCreateXcCount  OBJECT-TYPE
            SYNTAX  INTEGER(1..84)
            ACCESS  read-write
            STATUS  mandatory
            DESCRIPTION
                "Xc count"
            ::= { systemXcCreateTable 16 }

        xcCreateCommand  OBJECT-TYPE
            SYNTAX  INTEGER {
                    none(1),
                    set-only(2),
                    clear-and-set(3)
                }
            ACCESS  read-write
            STATUS  mandatory
            DESCRIPTION
                "Xc command"
            ::= { systemXcCreateTable 17 }

        xcCreateErrorCode  OBJECT-TYPE
            SYNTAX  XcSetErrCode
            ACCESS  read-only
            STATUS  mandatory
            DESCRIPTION
                "Xc setup error code"
            ::= { systemXcCreateTable 18 }

--
--  SYSTEM XC Delete Table
--
    systemXcDeleteTable      OBJECT IDENTIFIER ::= { systemXcTable 2 }

        xcDeleteMapIndex  OBJECT-TYPE
            SYNTAX  XcMap
            ACCESS  read-write
            STATUS  mandatory
            DESCRIPTION
                "Xc Map1/Map2"
            ::= { systemXcDeleteTable 1 }

        xcDeleteDesSlot  OBJECT-TYPE
            SYNTAX  XcSlot
            ACCESS  read-write
            STATUS  mandatory
            DESCRIPTION
                "Xc Des unit"
            ::= { systemXcDeleteTable 2 }

        xcDeleteDesPort  OBJECT-TYPE
            SYNTAX  PortID
            ACCESS  read-write
            STATUS  mandatory
            DESCRIPTION
                "Xc Des Port"
            ::= { systemXcDeleteTable 3 }

        xcDeleteDesChannel  OBJECT-TYPE
            SYNTAX  ChannelNum
            ACCESS  read-write
            STATUS  mandatory
            DESCRIPTION
                "Xc Des Channel"
            ::= { systemXcDeleteTable 4 }

        xcDeleteDesAug1Sts3Path  OBJECT-TYPE
            SYNTAX  Aug1Sts3Num
            ACCESS  read-write
            STATUS  mandatory
            DESCRIPTION
                "Xc desinitaion Aug1 path"
            ::= { systemXcDeleteTable 5 }

        xcDeleteDesVc3Sts1Path  OBJECT-TYPE
            SYNTAX  Vc3Sts1Num
            ACCESS  read-write
            STATUS  mandatory
            DESCRIPTION
                "Xc Des VC3/STS1 path"
            ::= { systemXcDeleteTable 6 }

        xcDeleteDesVc1xVtxPath  OBJECT-TYPE
            SYNTAX  Vc1xVtxNum
            ACCESS  read-write
            STATUS  mandatory
            DESCRIPTION
                "Xc Des Vc1x/vtx path"
            ::= { systemXcDeleteTable 7 }

        xcDeleteDesXcCount  OBJECT-TYPE
            SYNTAX  INTEGER(1..84)
            ACCESS  read-write
            STATUS  mandatory
            DESCRIPTION
                "Xc count"
            ::= { systemXcDeleteTable 8 }

        xcDeleteCommand  OBJECT-TYPE
            SYNTAX  INTEGER {
                    none(1),
                    clear-source(2),
                    clear-sncp-primary(3),
                    clear-sncp-secondary(4)
                }
            ACCESS  read-write
            STATUS  mandatory
            DESCRIPTION
                "Xc command"
            ::= { systemXcDeleteTable 9 }

        xcDeleteErrorCode  OBJECT-TYPE
            SYNTAX  XcDelErrCode
            ACCESS  read-only
            STATUS  mandatory
            DESCRIPTION
                "Xc Del error code"
            ::= { systemXcDeleteTable 10 }

--
--  SYSTEM XC Display Table
--
        systemXcDisplayTable  OBJECT-TYPE
            SYNTAX  SEQUENCE OF  SystemXcDisplayEntry
            ACCESS  not-accessible
            STATUS  mandatory
            DESCRIPTION
                "sdh-sonetXcDisplayTable "
            ::= { systemXcTable 3 }

        systemXcDisplayEntry OBJECT-TYPE
            SYNTAX  SystemXcDisplayEntry
            ACCESS  not-accessible
            STATUS  mandatory
            DESCRIPTION
                "An entry in the sdh xc display table."
            INDEX { xcDisplayMapIndex , xcDisplaySlotIndex ,
                    xcDisplayPortIndex , xcDisplayAug1Sts3Index ,
                    xcDisplayVc3Sts1Index , xcDisplayVc1xVtxIndex }
            ::= { systemXcDisplayTable 1 }

        SystemXcDisplayEntry ::= SEQUENCE  {
            xcDisplayMapIndex           XcMap,
            xcDisplaySlotIndex          XcuNum,
            xcDisplayPortIndex          PortID,
            xcDisplayAug1Sts3Index      Aug1Sts3Num,
            xcDisplayVc3Sts1Index       Vc3Sts1Num,
            xcDisplayVc1xVtxIndex       Vc1xVtxNum,
            xcDisplaySrcSlotType        NewXcModel,
            xcDisplaySrcSlot            XcSlot,
            xcDisplaySrcPort            PortID,
            xcDisplaySrcChannel         ChannelNum,
            xcDisplaySrcAug1Sts3Path    Aug1Sts3Num,
            xcDisplaySrcVc3Sts1Path     Vc3Sts1Num,
            xcDisplaySrcVc1xVtxPath     Vc1xVtxNum,
            xcDisplayXcGranularity      INTEGER,
            xcDisplayXcType             XcType
        }

        xcDisplayMapIndex  OBJECT-TYPE
            SYNTAX  XcMap
            ACCESS  read-only
            STATUS  mandatory
            DESCRIPTION
                "xc map index"
            ::= { systemXcDisplayEntry  1 }

        xcDisplaySlotIndex  OBJECT-TYPE
            SYNTAX  XcuNum
            ACCESS  read-only
            STATUS  mandatory
            DESCRIPTION
                "Optical unit"
            ::= { systemXcDisplayEntry  2 }

        xcDisplayPortIndex  OBJECT-TYPE
            SYNTAX  PortID
            ACCESS  read-only
            STATUS  mandatory
            DESCRIPTION
                "Optical port index"
            ::= { systemXcDisplayEntry  3 }

        xcDisplayAug1Sts3Index  OBJECT-TYPE
            SYNTAX  Aug1Sts3Num
            ACCESS  read-only
            STATUS  mandatory
            DESCRIPTION
                "Optical Aug1/sts3 path index"
            ::= { systemXcDisplayEntry  4 }

        xcDisplayVc3Sts1Index  OBJECT-TYPE
            SYNTAX  Vc3Sts1Num
            ACCESS  read-only
            STATUS  mandatory
            DESCRIPTION
                "Optical vc3/sts1 path index"
            ::= { systemXcDisplayEntry  5 }

        xcDisplayVc1xVtxIndex  OBJECT-TYPE
            SYNTAX  Vc1xVtxNum
            ACCESS  read-only
            STATUS  mandatory
            DESCRIPTION
                "Optical Vc1x/Vtx path index"
            ::= { systemXcDisplayEntry  6 }

        xcDisplaySrcSlotType  OBJECT-TYPE
            SYNTAX  NewXcModel
            ACCESS  read-only
            STATUS  mandatory
            DESCRIPTION
                " Xc src Unit Type"
            ::= { systemXcDisplayEntry  7 }

        xcDisplaySrcSlot  OBJECT-TYPE
            SYNTAX  XcSlot
            ACCESS  read-only
            STATUS  mandatory
            DESCRIPTION
                "Xc src Unit "
            ::= { systemXcDisplayEntry  8 }

        xcDisplaySrcPort  OBJECT-TYPE
            SYNTAX  PortID
            ACCESS  read-only
            STATUS  mandatory
            DESCRIPTION
                "Xc src port "
            ::= { systemXcDisplayEntry  9 }

        xcDisplaySrcChannel  OBJECT-TYPE
            SYNTAX  ChannelNum
            ACCESS  read-only
            STATUS  mandatory
            DESCRIPTION
                "Xc src channel "
            ::= { systemXcDisplayEntry  10 }

        xcDisplaySrcAug1Sts3Path  OBJECT-TYPE
            SYNTAX  Aug1Sts3Num
            ACCESS  read-only
            STATUS  mandatory
            DESCRIPTION
                "Xc src port "
            ::= { systemXcDisplayEntry  11 }

        xcDisplaySrcVc3Sts1Path  OBJECT-TYPE
            SYNTAX  Vc3Sts1Num
            ACCESS  read-only
            STATUS  mandatory
            DESCRIPTION
                " Xc src port "
            ::= { systemXcDisplayEntry  12 }

        xcDisplaySrcVc1xVtxPath  OBJECT-TYPE
            SYNTAX  Vc1xVtxNum
            ACCESS  read-only
            STATUS  mandatory
            DESCRIPTION
                " src port "
            ::= { systemXcDisplayEntry  13 }

        xcDisplayXcGranularity  OBJECT-TYPE
            SYNTAX  INTEGER {
                    tu3(2),
                    au3-sts1(3),
                    tu11-vt15(4),
                    tu12-vt2(5),
                    vc4-sts3c(6),
                    none(100)
                }
            ACCESS  read-only
            STATUS  mandatory
            DESCRIPTION
                " Xc granularity "
            ::= { systemXcDisplayEntry  14 }

        xcDisplayXcType  OBJECT-TYPE
            SYNTAX  XcType
            ACCESS  read-only
            STATUS  mandatory
            DESCRIPTION
                "Xc type "
            ::= { systemXcDisplayEntry  15 }

--
--  SYSTEM XC MAP Modify Table
--
    systemXcMapModifyTable  OBJECT IDENTIFIER ::= { systemXcTable 4 }

        xcMapActiveSetting  OBJECT-TYPE
            SYNTAX  INTEGER {
                    map1(1),
                    map2(2)
                }
            ACCESS  read-write
            STATUS  mandatory
            DESCRIPTION
                "Command:Change active TSA map"
            ::= { systemXcMapModifyTable 1 }

        xcMapDeleteSetting  OBJECT-TYPE
            SYNTAX  INTEGER {
                    map1(1),
                    map2(2)
                }
            ACCESS  read-write
            STATUS  mandatory
            DESCRIPTION
                "Command:Delete the TSA map"
            ::= { systemXcMapModifyTable 2 }

        xcMapCopySettng  OBJECT-TYPE
            SYNTAX  INTEGER {
                    none(1),
                    copy-active-to-the-other(2)
                }
            ACCESS  read-write
            STATUS  mandatory
            DESCRIPTION
                "Command:Copy active TSA map to other map"
            ::= { systemXcMapModifyTable 3 }

--
--  SYSTEM XC Summary Hex Table
--
        systemXcSummaryHexTab  OBJECT-TYPE
            SYNTAX  SEQUENCE OF  SystemXcSummaryHexEty
            ACCESS  not-accessible
            STATUS  mandatory
            DESCRIPTION
                "System XC Summary HEX Table "
            ::= { systemXcTable 5 }

        systemXcSummaryHexEty OBJECT-TYPE
            SYNTAX  SystemXcSummaryHexEty
            ACCESS  not-accessible
            STATUS  mandatory
            DESCRIPTION
                "An entry in the sdh xc summary hex table."
            INDEX { xcSummMapIndex , xcSummSlotIndex , xcSummPortIndex ,
                    xcSummAug1Sts3Index }
            ::= { systemXcSummaryHexTab 1 }

        SystemXcSummaryHexEty ::= SEQUENCE  {
            xcSummMapIndex              XcMap,
            xcSummSlotIndex             XcuNum,
            xcSummPortIndex             PortID,
            xcSummAug1Sts3Index         Aug1Sts3Num,
            xcSummSummary               OCTET STRING
        }

        xcSummMapIndex  OBJECT-TYPE
            SYNTAX  XcMap
            ACCESS  read-only
            STATUS  mandatory
            DESCRIPTION
                "xc map index"
            ::= { systemXcSummaryHexEty  1 }

        xcSummSlotIndex  OBJECT-TYPE
            SYNTAX  XcuNum
            ACCESS  read-only
            STATUS  mandatory
            DESCRIPTION
                "Optical unit"
            ::= { systemXcSummaryHexEty  2 }

        xcSummPortIndex  OBJECT-TYPE
            SYNTAX  PortID
            ACCESS  read-only
            STATUS  mandatory
            DESCRIPTION
                "Optical port index"
            ::= { systemXcSummaryHexEty  3 }

        xcSummAug1Sts3Index  OBJECT-TYPE
            SYNTAX  Aug1Sts3Num
            ACCESS  read-only
            STATUS  mandatory
            DESCRIPTION
                "Optical Aug1/sts3 path index"
            ::= { systemXcSummaryHexEty  4 }

        xcSummSummary  OBJECT-TYPE
            SYNTAX  OCTET STRING(SIZE(15))
            ACCESS  read-only
            STATUS  mandatory
            DESCRIPTION
                "XCU XC Summary"
            ::= { systemXcSummaryHexEty  5 }
--  2011-3-14 elvis add below
--
--  SYSTEM XC Sncp Tsa Table
--
    new-systemXcSncpTsaTable      OBJECT IDENTIFIER ::= { systemXcTable 6 }

        xcSncpTsaGranularityType  OBJECT-TYPE
            SYNTAX  INTEGER {
                    tu3(2),
                    au3-sts1(3),
                    tu11-vt15(4),
                    tu12-vt2(5),
                    vc4-sts3c(6),
                    none(100)
                }
            ACCESS  read-write
            STATUS  mandatory
            DESCRIPTION
                "Xc Sncp Tsa mapping type"
            ::= { new-systemXcSncpTsaTable 1 }

        xcSncpTsaMapIndex  OBJECT-TYPE
            SYNTAX  XcMap
            ACCESS  read-write
            STATUS  mandatory
            DESCRIPTION
                "Xc Sncp Tsa Map1/Map2"
            ::= { new-systemXcSncpTsaTable 2 }

        xcSncpTsaPriSlot  OBJECT-TYPE
            SYNTAX  XcSlot
            ACCESS  read-write
            STATUS  mandatory
            DESCRIPTION
                "Xc Sncp Tsa Primary unit"
            ::= { new-systemXcSncpTsaTable  3}

        xcSncpTsaPriPort  OBJECT-TYPE
            SYNTAX  PortID
            ACCESS  read-write
            STATUS  mandatory
            DESCRIPTION
                "Xc Sncp Tsa Primary Port"
            ::= { new-systemXcSncpTsaTable 4 }

        xcSncpTsaPriChannel  OBJECT-TYPE
            SYNTAX  ChannelNum
            ACCESS  read-write
            STATUS  mandatory
            DESCRIPTION
                "Xc Sncp Tsa Primary channel number"
            ::= { new-systemXcSncpTsaTable 5 }

        xcSncpTsaPriAug1Sts3  OBJECT-TYPE
            SYNTAX  Aug1Sts3Num
            ACCESS  read-write
            STATUS  mandatory
            DESCRIPTION
                "Xc Sncp Tsa Primary Aug1 path"
            ::= { new-systemXcSncpTsaTable 6 }

        xcSncpTsaPriVc3Sts1  OBJECT-TYPE
            SYNTAX  Vc3Sts1Num
            ACCESS  read-write
            STATUS  mandatory
            DESCRIPTION
                "Xc Sncp Tsa Primary VC3/STS1 path"
            ::= { new-systemXcSncpTsaTable 7 }

        xcSncpTsaPriVc1xVtx  OBJECT-TYPE
            SYNTAX  Vc1xVtxNum
            ACCESS  read-write
            STATUS  mandatory
            DESCRIPTION
                "Xc Sncp Tsa Primary Vc1x/vtx path"
            ::= { new-systemXcSncpTsaTable 8 }

        xcSncpTsaSecSlot  OBJECT-TYPE
            SYNTAX  XcSlot
            ACCESS  read-write
            STATUS  mandatory
            DESCRIPTION
                "Xc Sncp Tsa Second unit"
            ::= { new-systemXcSncpTsaTable  9}

        xcSncpTsaSecPort  OBJECT-TYPE
            SYNTAX  PortID
            ACCESS  read-write
            STATUS  mandatory
            DESCRIPTION
                "Xc Sncp Tsa Second Port"
            ::= { new-systemXcSncpTsaTable 10 }

        xcSncpTsaSecChannel  OBJECT-TYPE
            SYNTAX  ChannelNum
            ACCESS  read-write
            STATUS  mandatory
            DESCRIPTION
                "Xc Sncp Tsa Second channel number"
            ::= { new-systemXcSncpTsaTable 11 }

        xcSncpTsaSecAug1Sts3  OBJECT-TYPE
            SYNTAX  Aug1Sts3Num
            ACCESS  read-write
            STATUS  mandatory
            DESCRIPTION
                "Xc Sncp Tsa Second Aug1 path"
            ::= { new-systemXcSncpTsaTable 12 }

        xcSncpTsaSecVc3Sts1  OBJECT-TYPE
            SYNTAX  Vc3Sts1Num
            ACCESS  read-write
            STATUS  mandatory
            DESCRIPTION
                "Xc Sncp Tsa Second VC3/STS1 path"
            ::= { new-systemXcSncpTsaTable 13 }

        xcSncpTsaSecVc1xVtx  OBJECT-TYPE
            SYNTAX  Vc1xVtxNum
            ACCESS  read-write
            STATUS  mandatory
            DESCRIPTION
                "Xc Sncp Tsa Second Vc1x/vtx path"
            ::= { new-systemXcSncpTsaTable 14 }

        xcSncpTsaPrtdSlot  OBJECT-TYPE
            SYNTAX  XcSlot
            ACCESS  read-write
            STATUS  mandatory
            DESCRIPTION
                "Xc Sncp Tsa Protected unit"
            ::= { new-systemXcSncpTsaTable  15}

        xcSncpTsaPrtdPort  OBJECT-TYPE
            SYNTAX  PortID
            ACCESS  read-write
            STATUS  mandatory
            DESCRIPTION
                "Xc Sncp Tsa Protected Port"
            ::= { new-systemXcSncpTsaTable 16 }

        xcSncpTsaPrtdChannel  OBJECT-TYPE
            SYNTAX  ChannelNum
            ACCESS  read-write
            STATUS  mandatory
            DESCRIPTION
                "Xc Sncp Tsa Protected channel number"
            ::= { new-systemXcSncpTsaTable 17 }

        xcSncpTsaPrtdAug1Sts3  OBJECT-TYPE
            SYNTAX  Aug1Sts3Num
            ACCESS  read-write
            STATUS  mandatory
            DESCRIPTION
                "Xc Sncp Tsa Protected Aug1 path"
            ::= { new-systemXcSncpTsaTable 18 }

        xcSncpTsaPrtdVc3Sts1  OBJECT-TYPE
            SYNTAX  Vc3Sts1Num
            ACCESS  read-write
            STATUS  mandatory
            DESCRIPTION
                "Xc Sncp Tsa Protected VC3/STS1 path"
            ::= { new-systemXcSncpTsaTable 19 }

        xcSncpTsaPrtdVc1xVtx  OBJECT-TYPE
            SYNTAX  Vc1xVtxNum
            ACCESS  read-write
            STATUS  mandatory
            DESCRIPTION
                "Xc Sncp Tsa Protected Vc1x/vtx path"
            ::= { new-systemXcSncpTsaTable 20 }

        xcSncpTsaXcType  OBJECT-TYPE
            SYNTAX  INTEGER {
                    pp-add-drop(1),
                    not-available(100)
                }
            ACCESS  read-write
            STATUS  mandatory
            DESCRIPTION
                "Xc type"
            ::= { new-systemXcSncpTsaTable 21 }

        xcSncpTsaXcCount  OBJECT-TYPE
            SYNTAX  INTEGER(1..84)
            ACCESS  read-write
            STATUS  mandatory
            DESCRIPTION
                "Xc count"
            ::= { new-systemXcSncpTsaTable 22 }

        xcSncpTsaCommand  OBJECT-TYPE
            SYNTAX  INTEGER {
                    none(1),
                    set-only(2),
                    clear-and-set(3)
                }
            ACCESS  read-write
            STATUS  mandatory
            DESCRIPTION
                "Xc command"
            ::= { new-systemXcSncpTsaTable 23 }

        xcSncpTsaErrorCode  OBJECT-TYPE
            SYNTAX  XcSetErrCode
            ACCESS  read-only
            STATUS  mandatory
            DESCRIPTION
                "Xc setup error code"
            ::= { new-systemXcSncpTsaTable 24 }

--
--  SYSTEM XC Clear XCU Port Table
--
    new-sysXcClrXcuPortTable      OBJECT IDENTIFIER ::= { systemXcTable 7 }

        xcClrXcuPortDes  OBJECT-TYPE
            SYNTAX  INTEGER {
                    xcu1-port1(1),
                    xcu1-port2(2),
                    xcu2-port1(3),
                    xcu2-port2(4),
                    not-available(100)
                }
            ACCESS  read-write
            STATUS  mandatory
            DESCRIPTION
                "Xc Clear XCU Port Des"
            ::= { new-sysXcClrXcuPortTable 1 }

--
--  SYSTEM XC Display Table
--
        new-systemXcDisplayTable  OBJECT-TYPE
            SYNTAX  SEQUENCE OF  NewSystemXcDisplayEntry
            ACCESS  not-accessible
            STATUS  mandatory
            DESCRIPTION
                "sdh-sonetXcDisplayTable "
            ::= { systemXcTable 8 }

        newsystemXcDisplayEntry OBJECT-TYPE
            SYNTAX  NewSystemXcDisplayEntry
            ACCESS  not-accessible
            STATUS  mandatory
            DESCRIPTION
                "An entry in the sdh xc display table."
            INDEX { new-xcDisplayMapIndex , new-xcDisplaySlotIndex , new-xcDisplayPortIndex ,
                    new-xcDisplayAug1Sts3Index , new-xcDisplayVc3Sts1Index , new-xcDisplayVc1xVtxIndex }
            ::= { new-systemXcDisplayTable 1 }

        NewSystemXcDisplayEntry ::= SEQUENCE  {
            new-xcDisplayMapIndex       XcMap,
            new-xcDisplaySlotIndex      XcuNum,
            new-xcDisplayPortIndex      PortID,
            new-xcDisplayAug1Sts3Index  Aug1Sts3Num,
            new-xcDisplayVc3Sts1Index   Vc3Sts1Num,
            new-xcDisplayVc1xVtxIndex   Vc1xVtxNum,
            new-xcDisplayPriSlotType    NewXcModel,
            new-xcDisplayPriSlot        XcSlot,
            new-xcDisplayPriPort        PortID,
            new-xcDisplayPriChannel     ChannelNum,
            new-xcDisplayPriAug1Sts3Path    Aug1Sts3Num,
            new-xcDisplayPriVc3Sts1Path     Vc3Sts1Num,
            new-xcDisplayPriVc1xVtxPath     Vc1xVtxNum,
            new-xcDisplaySecSlotType        NewXcModel,
            new-xcDisplaySecSlot            XcSlot,
            new-xcDisplaySecPort            PortID,
            new-xcDisplaySecChannel         ChannelNum,
            new-xcDisplaySecAug1Sts3Path    Aug1Sts3Num,
            new-xcDisplaySecVc3Sts1Path     Vc3Sts1Num,
            new-xcDisplaySecVc1xVtxPath     Vc1xVtxNum,
            new-xcDisplayXcGranularity      INTEGER,
            new-xcDisplayXcType             XcType
        }

        new-xcDisplayMapIndex  OBJECT-TYPE
            SYNTAX  XcMap
            ACCESS  read-only
            STATUS  mandatory
            DESCRIPTION
                "xc map index"
            ::= { newsystemXcDisplayEntry  1 }

        new-xcDisplaySlotIndex  OBJECT-TYPE
            SYNTAX  XcuNum
            ACCESS  read-only
            STATUS  mandatory
            DESCRIPTION
                "Optical unit"
            ::= { newsystemXcDisplayEntry  2 }

        new-xcDisplayPortIndex  OBJECT-TYPE
            SYNTAX  PortID
            ACCESS  read-only
            STATUS  mandatory
            DESCRIPTION
                "Optical port index"
            ::= { newsystemXcDisplayEntry  3 }

        new-xcDisplayAug1Sts3Index  OBJECT-TYPE
            SYNTAX  Aug1Sts3Num
            ACCESS  read-only
            STATUS  mandatory
            DESCRIPTION
                "Optical Aug1/sts3 path index"
            ::= { newsystemXcDisplayEntry  4 }

        new-xcDisplayVc3Sts1Index  OBJECT-TYPE
            SYNTAX  Vc3Sts1Num
            ACCESS  read-only
            STATUS  mandatory
            DESCRIPTION
                "Optical vc3/sts1 path index"
            ::= { newsystemXcDisplayEntry  5 }

        new-xcDisplayVc1xVtxIndex  OBJECT-TYPE
            SYNTAX  Vc1xVtxNum
            ACCESS  read-only
            STATUS  mandatory
            DESCRIPTION
                "Optical Vc1x/Vtx path index"
            ::= { newsystemXcDisplayEntry  6 }

        new-xcDisplayPriSlotType  OBJECT-TYPE
            SYNTAX  NewXcModel
            ACCESS  read-only
            STATUS  mandatory
            DESCRIPTION
                " Xc Primary Unit Type"
            ::= { newsystemXcDisplayEntry  7 }

        new-xcDisplayPriSlot  OBJECT-TYPE
            SYNTAX  XcSlot
            ACCESS  read-only
            STATUS  mandatory
            DESCRIPTION
                "Xc Primary Unit "
            ::= { newsystemXcDisplayEntry  8 }

        new-xcDisplayPriPort  OBJECT-TYPE
            SYNTAX  PortID
            ACCESS  read-only
            STATUS  mandatory
            DESCRIPTION
                "Xc Primary port "
            ::= { newsystemXcDisplayEntry  9 }

        new-xcDisplayPriChannel  OBJECT-TYPE
            SYNTAX  ChannelNum
            ACCESS  read-only
            STATUS  mandatory
            DESCRIPTION
                "Xc Primary channel "
            ::= { newsystemXcDisplayEntry  10 }

        new-xcDisplayPriAug1Sts3Path  OBJECT-TYPE
            SYNTAX  Aug1Sts3Num
            ACCESS  read-only
            STATUS  mandatory
            DESCRIPTION
                "Xc Primary Aug1/Sts3 "
            ::= { newsystemXcDisplayEntry  11 }

        new-xcDisplayPriVc3Sts1Path  OBJECT-TYPE
            SYNTAX  Vc3Sts1Num
            ACCESS  read-only
            STATUS  mandatory
            DESCRIPTION
                " Xc Primary Vc3/Sts1 "
            ::= { newsystemXcDisplayEntry  12 }

        new-xcDisplayPriVc1xVtxPath  OBJECT-TYPE
            SYNTAX  Vc1xVtxNum
            ACCESS  read-only
            STATUS  mandatory
            DESCRIPTION
                " Xc Primary Vc1x/Vtx "
            ::= { newsystemXcDisplayEntry  13 }

        new-xcDisplaySecSlotType  OBJECT-TYPE
            SYNTAX  NewXcModel
            ACCESS  read-only
            STATUS  mandatory
            DESCRIPTION
                " Xc Secondary Unit Type"
            ::= { newsystemXcDisplayEntry  14 }

        new-xcDisplaySecSlot  OBJECT-TYPE
            SYNTAX  XcSlot
            ACCESS  read-only
            STATUS  mandatory
            DESCRIPTION
                "Xc Secondary Unit "
            ::= { newsystemXcDisplayEntry  15 }

        new-xcDisplaySecPort  OBJECT-TYPE
            SYNTAX  PortID
            ACCESS  read-only
            STATUS  mandatory
            DESCRIPTION
                "Xc Secondary port "
            ::= { newsystemXcDisplayEntry  16 }

        new-xcDisplaySecChannel  OBJECT-TYPE
            SYNTAX  ChannelNum
            ACCESS  read-only
            STATUS  mandatory
            DESCRIPTION
                "Xc Secondary channel "
            ::= { newsystemXcDisplayEntry  17 }

        new-xcDisplaySecAug1Sts3Path  OBJECT-TYPE
            SYNTAX  Aug1Sts3Num
            ACCESS  read-only
            STATUS  mandatory
            DESCRIPTION
                "Xc Secondary Aug1/Sts3 "
            ::= { newsystemXcDisplayEntry  18 }

        new-xcDisplaySecVc3Sts1Path  OBJECT-TYPE
            SYNTAX  Vc3Sts1Num
            ACCESS  read-only
            STATUS  mandatory
            DESCRIPTION
                " Xc Secondary Vc3/Sts1 "
            ::= { newsystemXcDisplayEntry  19 }

        new-xcDisplaySecVc1xVtxPath  OBJECT-TYPE
            SYNTAX  Vc1xVtxNum
            ACCESS  read-only
            STATUS  mandatory
            DESCRIPTION
                " XC Secondary Vc1x/Vtx "
            ::= { newsystemXcDisplayEntry  20 }

        new-xcDisplayXcGranularity  OBJECT-TYPE
            SYNTAX  INTEGER {
                    tu3(2),
                    au3-sts1(3),
                    tu11-vt15(4),
                    tu12-vt2(5),
                    vc4-sts3c(6),
                    none(100)
                }
            ACCESS  read-only
            STATUS  mandatory
            DESCRIPTION
                " Xc granularity "
            ::= { newsystemXcDisplayEntry  21 }

        new-xcDisplayXcType  OBJECT-TYPE
            SYNTAX  XcType
            ACCESS  read-only
            STATUS  mandatory
            DESCRIPTION
                "Xc type "
            ::= { newsystemXcDisplayEntry  22 }



--  2011-3-14 elvis add above

--
--  Command Control Table
--
    commandControlTable     OBJECT IDENTIFIER ::= { system 10 }

        ccStoreConfiguration   OBJECT-TYPE
            SYNTAX  INTEGER {
                    store(1),
                    retrieve(2),
                    no(3),
                    -- 2012-09-20 add below by Rukka
                    in-storing(11),
                    in-retrieving(12)
                    -- 2012-09-20 add above by Rukka
                }
            ACCESS  read-write
            STATUS  mandatory
            DESCRIPTION
                " Command:Store/Retrieve Backup Configuration"
            ::= { commandControlTable 1 }

        ccAlarmQueueClear    OBJECT-TYPE
            SYNTAX  INTEGER {
                    unit-1(1),
                    unit-2(2),
                    unit-3(3),
                    unit-4(4),
                    all(9),
                    no(10),
                    unit-11(11),
                    unit-12(12),
                    unit-13(13),
                    unit-14(14),
                    unit-15(15),
                    unit-16(16)
                }
            ACCESS  read-write
            STATUS  mandatory
            DESCRIPTION
                "Command:Clear Alarm History"
            ::= { commandControlTable 2 }

        ccSystemReset  OBJECT-TYPE
            SYNTAX  INTEGER {
                    system-cold-reset(1),
                    system-warm-reset(2),
                    working-xcu-cold-reset(3),
                    working-xcu-warm-reset(4),
                    standby-xcu-cold-reset(5),
                    standby-xcu-warm-reset(6),
                    no(7)
                }
            ACCESS  read-write
            STATUS  mandatory
            DESCRIPTION
                "System and XCU Reset"
            ::= { commandControlTable 3 }

        ccClearACO  OBJECT-TYPE
            SYNTAX  INTEGER {
                    yes(1),
                    no(2)
                }
            ACCESS  read-write
            STATUS  mandatory
            DESCRIPTION
                "Command:Clear ACO"
            ::= { commandControlTable 4 }

        ccLoadDefault  OBJECT-TYPE
            SYNTAX  INTEGER {
                    unit-1(1),
                    unit-2(2),
                    unit-3(3),
                    unit-4(4),
                    all(9),
                    no(10)
                }
            ACCESS  read-write
            STATUS  mandatory
            DESCRIPTION
                "Command:load default"
            ::= { commandControlTable 5 }

        ccSysFec  OBJECT-TYPE
            SYNTAX  INTEGER {
                    enable(1),
                    disable(2)
                }
            ACCESS  read-write
            STATUS  mandatory
            DESCRIPTION
                "Command:enable/disable xcu fec port"
            ::= { commandControlTable 6 }

        ccConsoleLockout  OBJECT-TYPE
            SYNTAX  OCTET STRING(SIZE(28))
            ACCESS  read-write
            STATUS  mandatory
            DESCRIPTION
                "console unlock/lockout"
            ::= { commandControlTable 7 }

        ccTelnetLockout  OBJECT-TYPE
            SYNTAX  OCTET STRING(SIZE(28))
            ACCESS  read-write
            STATUS  mandatory
            DESCRIPTION
                "telnet unlock/lockout"
            ::= { commandControlTable 8 }

        ccPasswordChecking  OBJECT-TYPE
            SYNTAX  OCTET STRING(SIZE(28))
            ACCESS  read-write
            STATUS  mandatory
            DESCRIPTION
                "change setting of password checking"
            ::= { commandControlTable 9 }

        ccSSHserver  OBJECT-TYPE
            SYNTAX  INTEGER {
                    off(1),
                    on(2)
                }
            ACCESS  read-write
            STATUS  mandatory
            DESCRIPTION
                "SSH server on/off"
            ::= { commandControlTable 10 }

        ccTelnetTimeout  OBJECT-TYPE
            SYNTAX  INTEGER (300..3600)
            ACCESS  read-write
            STATUS  mandatory
            DESCRIPTION
                "Telnet Timeout"
            ::= { commandControlTable 11 }

        ccConsoleTimeout  OBJECT-TYPE
            SYNTAX  INTEGER (300..3600)
            ACCESS  read-write
            STATUS  mandatory
            DESCRIPTION
                "Console Timeout"
            ::= { commandControlTable 12 }

-- 2012-08-29 add below entry ccClearQandIssueCAASAlm by Rukka
        ccClearQAndIssueCAASAlm  OBJECT-TYPE
            SYNTAX  INTEGER{
                    no(1),
                    apply(2)
                }
            ACCESS  read-write
            STATUS  mandatory
            DESCRIPTION
                "Command:Clear alarm queue and issue all CAAS alarm again"
            ::= { commandControlTable 13 }

-- These is a field: 'sysSncpAISInsert' do exactly the same job with this one here. In IPv4 branch, user can see this field.
--        ccSncpUpsrAisInsertion  OBJECT-TYPE
--            SYNTAX  INTEGER {
--                    disable(1),
--                    enable(2)
--                }
--            ACCESS  read-write
--            STATUS  mandatory
--            DESCRIPTION
--                "Command: SNCP/UPSR AIS Insert Setup"
--            ::= { commandControlTable 14 }



--
--  Network interface Table
--

    sysNetIfTable                   OBJECT IDENTIFIER ::= { system 11 }

        sysIpAddress  OBJECT-TYPE
            SYNTAX  DisplayString (SIZE (0..19) )
            ACCESS  read-write
            STATUS  mandatory
            DESCRIPTION
                "system IP Address"
            ::= { sysNetIfTable 1 }

        sysIpMask     OBJECT-TYPE
            SYNTAX  DisplayString (SIZE (0..19) )
            ACCESS  read-write
            STATUS  mandatory
            DESCRIPTION
                "system IP Mask"
            ::= { sysNetIfTable 2 }

        sysGatewayIp    OBJECT-TYPE
            SYNTAX  DisplayString (SIZE (0..19) )
            ACCESS  read-write
            STATUS  mandatory
            DESCRIPTION
                "system Gateway IP"
            ::= { sysNetIfTable 3 }

        sysTrap1Ip    OBJECT-TYPE
            SYNTAX  DisplayString (SIZE (0..19) )
            ACCESS  read-write
            STATUS  mandatory
            DESCRIPTION
                "system trap1 IP"
            ::= { sysNetIfTable 4 }

        sysTrap2Ip    OBJECT-TYPE
            SYNTAX  DisplayString (SIZE (0..19) )
            ACCESS  read-write
            STATUS  mandatory
            DESCRIPTION
                "system trap2 IP"
            ::= { sysNetIfTable 5 }

        sysTrap3Ip    OBJECT-TYPE
            SYNTAX  DisplayString (SIZE (0..19) )
            ACCESS  read-write
            STATUS  mandatory
            DESCRIPTION
                "system trap3 IP"
            ::= { sysNetIfTable 6 }

        sysTrap4Ip    OBJECT-TYPE
            SYNTAX  DisplayString (SIZE (0..19) )
            ACCESS  read-write
            STATUS  mandatory
            DESCRIPTION
                "system trap4 IP"
            ::= { sysNetIfTable 7 }

        sysTrap1Community   OBJECT-TYPE
            SYNTAX  DisplayString (SIZE (0..19) )
            ACCESS  read-write
            STATUS  mandatory
            DESCRIPTION
                "system trap1 Community name"
            ::= { sysNetIfTable 8 }

        sysTrap2Community   OBJECT-TYPE
            SYNTAX  DisplayString (SIZE (0..19) )
            ACCESS  read-write
            STATUS  mandatory
            DESCRIPTION
                "system trap2 Community name"
            ::= { sysNetIfTable 9 }

        sysTrap3Community   OBJECT-TYPE
            SYNTAX  DisplayString (SIZE (0..19) )
            ACCESS  read-write
            STATUS  mandatory
            DESCRIPTION
                "system trap3 Community name"
            ::= { sysNetIfTable 10 }

        sysTrap4Community   OBJECT-TYPE
            SYNTAX  DisplayString (SIZE (0..19) )
            ACCESS  read-write
            STATUS  mandatory
            DESCRIPTION
                "system trap4 Community name"
            ::= { sysNetIfTable 11 }

-- 2012-08-03 modify below by Rukka
--        sysRouteProtocol  OBJECT-TYPE
--            SYNTAX  INTEGER {
--                    off(1),
--                    rip1(2),
--                    rip2(3)
--                }
--            ACCESS  read-write
--            STATUS  mandatory
--            DESCRIPTION
--                "system routing protocol"
--            ::= { sysNetIfTable  12 }
-- 2012-08-03 modify above by Rukka

--IPv6
        sysIpMode  OBJECT-TYPE
            SYNTAX  INTEGER {
                    v4-mode(1),
                    v6-mode(2)
                }
            ACCESS  read-write
            STATUS  mandatory
            DESCRIPTION
                "current IP mode"
            ::= { sysNetIfTable 13 }

        sysV6IpAddress  OBJECT-TYPE
            SYNTAX  DisplayString (SIZE(2..40))
            ACCESS  read-write
            STATUS  mandatory
            DESCRIPTION
                "IP V6 mode address"
            ::= { sysNetIfTable 14 }

        sysV6Ip-Prefix  OBJECT-TYPE
            SYNTAX  INTEGER (0..128)
            ACCESS  read-write
            STATUS  mandatory
            DESCRIPTION
                "IP V6 mode address prefix"
            ::= { sysNetIfTable 15 }

        sysV6IpGateway   OBJECT-TYPE
            SYNTAX  DisplayString (SIZE(2..40))
            ACCESS  read-write
            STATUS  mandatory
            DESCRIPTION
                "IP V6 mode Gateway"
            ::= { sysNetIfTable 16 }

        sysV6Trap1Ip   OBJECT-TYPE
            SYNTAX  DisplayString (SIZE(2..40))
            ACCESS  read-write
            STATUS  mandatory
            DESCRIPTION
                "system trap1 IP for IP V6 mode"
            ::= { sysNetIfTable 17 }

        sysV6Trap2Ip   OBJECT-TYPE
            SYNTAX  DisplayString (SIZE(2..40))
            ACCESS  read-write
            STATUS  mandatory
            DESCRIPTION
                "system trap2 IP for IP V6 mode"
            ::= { sysNetIfTable 18 }

        sysV6Trap3Ip   OBJECT-TYPE
            SYNTAX  DisplayString (SIZE(2..40))
            ACCESS  read-write
            STATUS  mandatory
            DESCRIPTION
                "system trap3 IP for IP V6 mode"
            ::= { sysNetIfTable 19 }

        sysV6Trap4Ip   OBJECT-TYPE
            SYNTAX  DisplayString (SIZE(2..40))
            ACCESS  read-write
            STATUS  mandatory
            DESCRIPTION
                "system trap4 IP for IP V6 mode"
            ::= { sysNetIfTable 20 }
--IPv6

        sysEthPortBpdu  OBJECT-TYPE
            SYNTAX  INTEGER {
                    disable(1),
                    enable(2)
                }
            ACCESS  read-write
            STATUS  mandatory
            DESCRIPTION
                "Ethernet port BPDU enable/disable"
            ::= { sysNetIfTable 21 }


--
--  Timing Source Table
--
    timingSourceTable               OBJECT IDENTIFIER ::= { system 12 }

--
--  Clock Mode Table
--
    clockModeTable                  OBJECT IDENTIFIER ::= { timingSourceTable 1 }

        ccClockMode     OBJECT-TYPE
            SYNTAX  INTEGER {
                    non-revertive(1),
                    revertive(2),
                    ssm(3)
                }
            ACCESS  read-write
            STATUS  mandatory
            DESCRIPTION
                "Clock Mode Setup"
            ::= { clockModeTable 1 }

        ccCurrentClock  OBJECT-TYPE
            SYNTAX  INTEGER {
                    priority-1(1),
                    priority-2(2),
                    priority-3(3),
                    priority-4(4),
                    hold-over(5)
                }
            ACCESS  read-only
            STATUS  mandatory
            DESCRIPTION
                "Current clock"
            ::= { clockModeTable 2 }

        ccOperationState        OBJECT-TYPE
            SYNTAX  INTEGER {
                    sync(1),
                    free-Run(2),
                    hold-over(3)
                }
            ACCESS  read-only
            STATUS  mandatory
            DESCRIPTION
                "Operation state"
            ::= { clockModeTable 3 }

        ccSSMHoldTime  OBJECT-TYPE
            SYNTAX  INTEGER (0..99)
            ACCESS  read-write
            STATUS  mandatory
            DESCRIPTION
                "SSM hold time"
            ::= { clockModeTable 4 }


--
--  Clock Source Table
--
        clockSourceTable  OBJECT-TYPE
            SYNTAX  SEQUENCE OF ClockSourceEntry
            ACCESS  not-accessible
            STATUS  mandatory
            DESCRIPTION
                "Clock source table."
            ::= { timingSourceTable 2 }

        clockSourceEntry        OBJECT-TYPE
            SYNTAX  ClockSourceEntry
            ACCESS  not-accessible
            STATUS  mandatory
            DESCRIPTION
                "clock source entry"
            INDEX { clkSourcePriorityIndex }
            ::= { clockSourceTable 1 }

        ClockSourceEntry ::= SEQUENCE {
            clkSourcePriorityIndex      INTEGER,
            clkSourceSlot               INTEGER,
            clkSourcePort               INTEGER,
            clkSourceQuality            INTEGER,
--            clkSourceSSMControl         INTEGER,
            clkSourceValid              INTEGER,
--            clkSourceRxS1               INTEGER,
--            clkSourceTxS1               INTEGER,
            clkSourceQualityLevel       INTEGER,
            clkSourceRxLevel            INTEGER,
            clkSourceTxLevel            INTEGER
        }

        clkSourcePriorityIndex  OBJECT-TYPE
            SYNTAX  INTEGER {
                    priority-1(1),
                    priority-2(2),
                    priority-3(3),
                    priority-4(4)
                }
            ACCESS  read-only
            STATUS  mandatory
            DESCRIPTION
                "Clock source priority"
            ::= { clockSourceEntry 1 }

        clkSourceSlot   OBJECT-TYPE
            SYNTAX  INTEGER {
                    null(1),
                    xcu1-w(2),
-- 2012-09-11 modify below by Rukka
                    xcu2-e(3),
                    --xcu2-w(3),
                    external-1(4),
                    external-2(5),
                    unit-1(6),
                    unit-2(7),
                    unit-3(8),
                    unit-4(9),
                    internal(14)
                }
            ACCESS  read-write
            STATUS  mandatory
            DESCRIPTION
                "clock source slot"
            ::= { clockSourceEntry 2 }

        clkSourcePort   OBJECT-TYPE
            SYNTAX  INTEGER {
                    null(1),
                    port-1(2),
                    port-2(3),
                    port-3(4),
                    port-4(5),
                    port-5(6),
                    port-6(7),
                    port-7(8),
                    port-8(9),
                    port-9(10),
                    port-10(11),
                    port-11(12),
                    port-12(13),
                    port-13(14),
                    port-14(15),
                    port-15(16),
                    port-16(17),
                    port-17(18),
                    port-18(19),
                    port-19(20),
                    port-20(21),
                    port-21(22),
                    port-22(23),
                    port-23(24),
                    port-24(25),
                    port-25(26),
                    port-26(27),
                    port-27(28),
                    port-28(29),
                    port-29(30),
                    port-30(31),
                    port-31(32),
                    port-32(33),
                    port-33(34),
                    port-34(35),
                    port-35(36),
                    port-36(37),
                    port-37(38),
                    port-38(39),
                    port-39(40),
                    port-40(41),
                    port-41(42),
                    port-42(43),
                    port-43(44),
                    port-44(45),
                    port-45(46),
                    port-46(47),
                    port-47(48),
                    port-48(49),
                    port-49(50),
                    port-50(51),
                    port-51(52),
                    port-52(53),
                    port-53(54),
                    port-54(55),
                    port-55(56),
                    port-56(57),
                    port-57(58),
                    port-58(59),
                    port-59(60),
                    port-60(61),
                    port-61(62),
                    port-62(63),
                    port-63(64),
                    port-64(65)
                }
            ACCESS  read-write
            STATUS  mandatory
            DESCRIPTION
                "Clock source port"
            ::= { clockSourceEntry 3 }

        clkSourceQuality        OBJECT-TYPE
            SYNTAX  INTEGER {
                    null(1),
                    auto(2),
                    static(3)
                }
            ACCESS  read-write
            STATUS  mandatory
            DESCRIPTION
                "clock quality entry"
            ::= { clockSourceEntry 4 }

--        clkSourceSSMControl     OBJECT-TYPE
--            SYNTAX  INTEGER (0..15)
--            ACCESS  read-write
--            STATUS  mandatory
--            DESCRIPTION
--                "do not use"
--            ::= { clockSourceEntry 5 }

        clkSourceValid  OBJECT-TYPE
            SYNTAX  INTEGER {
                    invalid(1),
                    valid(2)
                }
            ACCESS  read-only
            STATUS  mandatory
            DESCRIPTION
                "clock valid entry"
            ::= { clockSourceEntry 6 }

--        clkSourceRxS1   OBJECT-TYPE
--            SYNTAX  INTEGER (0..15)
--            ACCESS  read-only
--            STATUS  mandatory
--            DESCRIPTION
--                "do not use"
--            ::= { clockSourceEntry 7 }

--        clkSourceTxS1   OBJECT-TYPE
--            SYNTAX  INTEGER (0..15)
--            ACCESS  read-only
--            STATUS  mandatory
--            DESCRIPTION
--                "do not use"
--            ::= { clockSourceEntry 8 }

        clkSourceQualityLevel OBJECT-TYPE
            SYNTAX  INTEGER {
                    null(0),
                    level1(1),
                    level2(2),
                    level3(3),
                    level4(4),
                    level5(5),
                    level6(6),
                    level7(7),
                    level8(8),
                    level9(9)
                }
            ACCESS  read-write
            STATUS  mandatory
            DESCRIPTION
                "clock source entry"
            ::= { clockSourceEntry 9 }

        clkSourceRxLevel   OBJECT-TYPE
            SYNTAX  INTEGER {
                    notAvailable(0),
                    level1(1),
                    level2(2),
                    level3(3),
                    level4(4),
                    level5(5),
                    level6(6),
                    level7(7),
                    level8(8),
                    level9(9)
                }
            ACCESS  read-only
            STATUS  mandatory
            DESCRIPTION
                "Rx SSM level"
            ::= { clockSourceEntry 10 }

        clkSourceTxLevel   OBJECT-TYPE
            SYNTAX  INTEGER {
                    notAvailable(0),
                    level1(1),
                    level2(2),
                    level3(3),
                    level4(4),
                    level5(5),
                    level6(6),
                    level7(7),
                    level8(8),
                    level9(9)
                }
            ACCESS  read-only
            STATUS  mandatory
            DESCRIPTION
                "Tx SSM level"
            ::= { clockSourceEntry 11 }

--
--  External Clock Table
--
        externalClockTable  OBJECT-TYPE
            SYNTAX  SEQUENCE OF ExternalClockEntry
            ACCESS  not-accessible
            STATUS  mandatory
            DESCRIPTION
                "External clock table."
            ::= { timingSourceTable 3 }

        externalClockEntry      OBJECT-TYPE
            SYNTAX  ExternalClockEntry
            ACCESS  not-accessible
            STATUS  mandatory
            DESCRIPTION
                "External clock entry"
            INDEX { exteClockIndex }
            ::= { externalClockTable 1 }

        ExternalClockEntry ::= SEQUENCE {
            exteClockIndex              INTEGER,
            exteClockInterface          INTEGER,
            exteClockCarryBit           INTEGER,
            exteClockImpedance          INTEGER
        }

        exteClockIndex  OBJECT-TYPE
            SYNTAX  INTEGER {
                    external-1(1),
                    external-2(2)
                }
            ACCESS  read-only
            STATUS  mandatory
            DESCRIPTION
                "External clock index"
            ::= { externalClockEntry 1 }

        exteClockInterface      OBJECT-TYPE
            SYNTAX  INTEGER {
                    e1-crc(1),
                    e1-fas(2),
                    t1-esf(3),
                    t1-d4(4),
                    two-MHz(5)
                }
            ACCESS  read-write
            STATUS  mandatory
            DESCRIPTION
                "External clock interface"
            ::= { externalClockEntry 2 }

        exteClockCarryBit       OBJECT-TYPE
            SYNTAX  INTEGER {
                    null(1),
                    sa4(2),
                    sa5(3),
                    sa6(4),
                    sa7(5),
                    sa8(6)
                }
            ACCESS  read-write
            STATUS  mandatory
            DESCRIPTION
                "External clock carry bit"
            ::= { externalClockEntry 3 }

        exteClockImpedance      OBJECT-TYPE
            SYNTAX  INTEGER {
                    null(1),
                    e1-75ohm(2),
                    e1-120ohm(3)
                }
            ACCESS  read-write
            STATUS  mandatory
            DESCRIPTION
                "External clock Impedance"
            ::= { externalClockEntry 4 }


--
--  SSM conversion Table
--
        ssmConversionTable  OBJECT-TYPE
            SYNTAX  SEQUENCE OF SsmConvTableEntry
            ACCESS  not-accessible
            STATUS  mandatory
            DESCRIPTION
                "SSM conversion table"
            ::= { timingSourceTable 4 }

        ssmConvTableEntry OBJECT-TYPE
            SYNTAX  SsmConvTableEntry
            ACCESS  not-accessible
            STATUS  mandatory
            DESCRIPTION
                "SSM conversion table entry"
            INDEX { ssmQualityLevel }
            ::= { ssmConversionTable 1 }

        SsmConvTableEntry ::= SEQUENCE {
            ssmQualityLevel INTEGER,
            ssmSdhE1Ssm     SsmABCD,
            ssmSonetSsm     SsmABCD,
            ssmDs1Ssm       INTEGER
        }

        ssmQualityLevel OBJECT-TYPE
            SYNTAX  INTEGER {
                    level1Prs(1),
                    level2Stu(2),
                    level3St2(3),
                    level4TncG812t(4),
                    level5St3eG812l(5),
                    level6St3(6),
                    level7SmcSets(7),
                    level8St4(8),
                    level9Dus(9)
                }
            ACCESS  read-only
            STATUS  mandatory
            DESCRIPTION
                "Quality Level"
            ::= { ssmConvTableEntry 1 }

        ssmSdhE1Ssm OBJECT-TYPE
            SYNTAX  SsmABCD
            ACCESS  read-only
            STATUS  mandatory
            DESCRIPTION
                "SDH and E1 SSM value"
            ::= { ssmConvTableEntry 2 }

        ssmSonetSsm OBJECT-TYPE
            SYNTAX  SsmABCD
            ACCESS  read-only
            STATUS  mandatory
            DESCRIPTION
                "SONET SSM value"
            ::= { ssmConvTableEntry 3 }

        ssmDs1Ssm OBJECT-TYPE
            SYNTAX  INTEGER {
                    ssm00000100(1),
                    ssm00001000(2),
                    ssm00001100(3),
                    ssm01111000(4),
                    ssm01111100(5),
                    ssm00010000(6),
                    ssm00100010(7),
                    ssm00101000(8),
                    ssm00110000(9)
                }
            ACCESS  read-only
            STATUS  mandatory
            DESCRIPTION
                "DS1 SSM value"
            ::= { ssmConvTableEntry 4 }

--
--  SSM Conversion Setup Table
--
    ssmConvSetupTable     OBJECT IDENTIFIER ::= { timingSourceTable 5 }

        level3SdhE1Ssm  OBJECT-TYPE
            SYNTAX  SsmABCD
            ACCESS  read-write
            STATUS  mandatory
            DESCRIPTION
                "level 3 SDH/E1 SSM setup"
            ::= { ssmConvSetupTable 1 }

        level6SdhE1Ssm  OBJECT-TYPE
            SYNTAX  SsmABCD
            ACCESS  read-write
            STATUS  mandatory
            DESCRIPTION
                "level 6 SDH/E1 SSM setup"
            ::= { ssmConvSetupTable 2 }

        level8SdhE1Ssm  OBJECT-TYPE
            SYNTAX  SsmABCD
            ACCESS  read-write
            STATUS  mandatory
            DESCRIPTION
                "level 8 SDH/E1 SSM setup"
            ::= { ssmConvSetupTable 3 }

        level8SonetSsm  OBJECT-TYPE
            SYNTAX  SsmABCD
            ACCESS  read-write
            STATUS  mandatory
            DESCRIPTION
                "level 8 SONET SSM setup"
            ::= { ssmConvSetupTable 4 }


--
--  Path Granularity Table
--


        pathGranularityTable  OBJECT-TYPE
        SYNTAX  SEQUENCE OF  GranularityEntry
            ACCESS  not-accessible
            STATUS  mandatory
            DESCRIPTION
                "sdh/sonet ho/lo mapping mode table"
            ::= { system 13 }

        granularityEntry  OBJECT-TYPE
            SYNTAX  GranularityEntry
            ACCESS  not-accessible
            STATUS  mandatory
            DESCRIPTION
                "An entry in the sdh/sonet ho/lo mapping mode table."
            INDEX { granularityXCUIndex , granularityPortIndex , granularityAug1Sts3Index }
            ::= { pathGranularityTable 1 }


        GranularityEntry ::= SEQUENCE  {
            granularityXCUIndex         XcuNum,
            granularityPortIndex        PortNum,
            granularityAug1Sts3Index    Aug1Sts3Num,
            granularityHo-Sts3Path      HoMappingType,
            granularityLo-Sts1Path-1    LoMappingType,
            granularityLo-Sts1Path-2    LoMappingType,
            granularityLo-Sts1Path-3    LoMappingType

    }

        granularityXCUIndex  OBJECT-TYPE
            SYNTAX  XcuNum
            ACCESS  read-only
            STATUS  mandatory
            DESCRIPTION
                "XCU #1~#2"
            ::= { granularityEntry  1 }

        granularityPortIndex  OBJECT-TYPE
            SYNTAX  PortNum
            ACCESS  read-only
            STATUS  mandatory
            DESCRIPTION
                "PORT #1~#2"
            ::= { granularityEntry  2 }

        granularityAug1Sts3Index  OBJECT-TYPE
            SYNTAX  Aug1Sts3Num
            ACCESS  read-only
            STATUS  mandatory
            DESCRIPTION
                "Stm1/Sts3 Path selection"
            ::= { granularityEntry  3 }

        granularityHo-Sts3Path  OBJECT-TYPE
            SYNTAX  HoMappingType
            ACCESS  read-write
            STATUS  mandatory
            DESCRIPTION
                "Ho-order mapping type selection"
            ::= { granularityEntry  4 }

        granularityLo-Sts1Path-1  OBJECT-TYPE
            SYNTAX  LoMappingType
            ACCESS  read-write
            STATUS  mandatory
            DESCRIPTION
                "Lo-order mapping type selection"
            ::= { granularityEntry  5 }

        granularityLo-Sts1Path-2  OBJECT-TYPE
            SYNTAX  LoMappingType
            ACCESS  read-write
            STATUS  mandatory
            DESCRIPTION
                "Lo-order mapping type selection"
            ::= { granularityEntry  6 }

        granularityLo-Sts1Path-3  OBJECT-TYPE
            SYNTAX  LoMappingType
            ACCESS  read-write
            STATUS  mandatory
            DESCRIPTION
                "Lo-order mapping type selection"
            ::= { granularityEntry  7 }

--
--  System Mode Table
--
    systemModeTable         OBJECT IDENTIFIER ::= { system 14 }

        sysSdhSonetMode         OBJECT-TYPE
            SYNTAX  INTEGER {
                    sdh(1),
                    sonet(2)
                }
            ACCESS  read-write
            STATUS  mandatory
            DESCRIPTION
                "SDH/Sonet Mode"
            ::= { systemModeTable 1 }

        sysProtectGroup1Mode            OBJECT-TYPE
            SYNTAX  INTEGER {
                    tm-1plus1(1),
                    two-tm(2),
                    adm-sncp(3),
                    adm-1plus1-sncp(4)
                }
            ACCESS  read-write
            STATUS  mandatory
            DESCRIPTION
                "Group 1 Application Mode"
            ::= { systemModeTable 2 }

        sysProtectGroup2Mode            OBJECT-TYPE
            SYNTAX  INTEGER {
                    tm-1plus1(1),
                    two-tm(2),
                    adm-sncp(3),
                    adm-1plus1-sncp(4)
                }
            ACCESS  read-write
            STATUS  mandatory
            DESCRIPTION
                "Group 2 Application Mode"
            ::= { systemModeTable 3 }

        sysXcu1Port1Rate                OBJECT-TYPE
            SYNTAX  INTEGER {
                    stm1-oc3(1),
                    stm4-oc12(2)
                }
            ACCESS  read-write
            STATUS  mandatory
            DESCRIPTION
                "XCU1(W) port 1 rate"
            ::= { systemModeTable 4 }

        sysXcu1Port2Rate                OBJECT-TYPE
            SYNTAX  INTEGER {
                    stm1-oc3(1),
                    stm4-oc12(2)
                }
            ACCESS  read-write
            STATUS  mandatory
            DESCRIPTION
                "XCU1(W) port 2 rate"
            ::= { systemModeTable 5 }

        sysXcu2Port1Rate                OBJECT-TYPE
            SYNTAX  INTEGER {
                    stm1-oc3(1),
                    stm4-oc12(2)
                }
            ACCESS  read-write
            STATUS  mandatory
            DESCRIPTION
                "XCU2(E) port 1 rate"
            ::= { systemModeTable 6 }

        sysXcu2Port2Rate                OBJECT-TYPE
            SYNTAX  INTEGER {
                    stm1-oc3(1),
                    stm4-oc12(2)
                }
            ACCESS  read-write
            STATUS  mandatory
            DESCRIPTION
                "XCU2(E) port 2 rate"
            ::= { systemModeTable 7 }

        sysTpsg1Protection              OBJECT-TYPE
            SYNTAX  INTEGER {
                    off(1),
                    on(2)
                }
            ACCESS  read-only
            STATUS  mandatory
            DESCRIPTION
                "TPSG1 protection enable/disable"
            ::= { systemModeTable 8 }

        sysTpsg2Protection              OBJECT-TYPE
            SYNTAX  INTEGER {
                    off(1),
                    on(2)
                }
            ACCESS  read-only
            STATUS  mandatory
            DESCRIPTION
                "TPSG2 protection enable/disable"
            ::= { systemModeTable 9 }


        sysMspWtrTimer          OBJECT-TYPE
            SYNTAX  INTEGER (3..900)
            ACCESS  read-write
            STATUS  mandatory
            DESCRIPTION
                "MSP 1+1 WTR Timer"
            ::= { systemModeTable 12 }

        sysGroupingMode         OBJECT-TYPE
            SYNTAX  INTEGER {
                    horizontal(1),
                    vertical(2)
                }
            ACCESS  read-write
            STATUS  mandatory
            DESCRIPTION
                "System Grouping Mode"
            ::= { systemModeTable 13 }

        sysIdlePathAlarmInsert  OBJECT-TYPE
            SYNTAX  INTEGER {
                    ais(1),
                    uneq(2)
                }
            ACCESS  read-write
            STATUS  mandatory
            DESCRIPTION
                "Alarm inserted for idle path(without XC)"
            ::= { systemModeTable 14 }

--
--  System Protect Table
--
        systemProtectionTable  OBJECT-TYPE
            SYNTAX  SEQUENCE OF  SystemProtectionEntry
            ACCESS  not-accessible
            STATUS  mandatory
            DESCRIPTION
                "System protection Table "
            ::= { system 15 }

        systemProtectionEntry OBJECT-TYPE
            SYNTAX  SystemProtectionEntry
            ACCESS  not-accessible
            STATUS  mandatory
            DESCRIPTION
                "An entry in the System protection table."
            INDEX { protectGroupIndex }
            ::= { systemProtectionTable 1 }

        SystemProtectionEntry ::= SEQUENCE  {
            protectGroupIndex           INTEGER,
            protectSncpEnable           INTEGER,
            protectSncpRevertive        INTEGER,
            protectSncpMode             INTEGER,
            protectMspEnable            INTEGER,
            protectMspRevertive         INTEGER,
            protectMspDirection         INTEGER,
            protectImplicitBypassXC     INTEGER
        }

        protectGroupIndex  OBJECT-TYPE
            SYNTAX  INTEGER {
                    group-1(1),
                    group-2(2)
                }
            ACCESS  read-only
            STATUS  mandatory
            DESCRIPTION
                "Protect group index"
            ::= { systemProtectionEntry  1 }

        protectSncpEnable  OBJECT-TYPE
            SYNTAX  INTEGER {
                    off(1),
                    on(2)
                }
            ACCESS  read-only
            STATUS  mandatory
            DESCRIPTION
                "SNCP/UPSR OFF or ON"
            ::= { systemProtectionEntry 2 }

        protectSncpRevertive  OBJECT-TYPE
            SYNTAX  INTEGER {
                    non-revertive(1),
                    revertive(2)
                }
            ACCESS  read-write
            STATUS  mandatory
            DESCRIPTION
                "SNCP/UPSR revertive or non-revertive"
            ::= { systemProtectionEntry 3 }

        protectSncpMode  OBJECT-TYPE
            SYNTAX  INTEGER {
                    intrusive(1),
                    non-intrusive(2)
                }
            ACCESS  read-write
            STATUS  mandatory
            DESCRIPTION
                "SNCP/UPSR Mode"
            ::= { systemProtectionEntry 4 }

        protectMspEnable  OBJECT-TYPE
            SYNTAX  INTEGER {
                    off(1),
                    on(2)
                }
            ACCESS  read-write
            STATUS  mandatory
            DESCRIPTION
                "MSP 1+1 OFF or ON"
            ::= { systemProtectionEntry 5 }

        protectMspRevertive  OBJECT-TYPE
            SYNTAX  INTEGER {
                    non-revertive(1),
                    revertive(2)
                }
            ACCESS  read-write
            STATUS  mandatory
            DESCRIPTION
                "MSP 1+1 revertive or non-revertive"
            ::= { systemProtectionEntry 6 }

        protectMspDirection  OBJECT-TYPE
            SYNTAX  INTEGER {
                    uni-directional(1),
                    bi-directional(2)
                }
            ACCESS  read-write
            STATUS  mandatory
            DESCRIPTION
                "MSP 1+1 direction"
            ::= { systemProtectionEntry 7 }

        protectImplicitBypassXC  OBJECT-TYPE
            SYNTAX  INTEGER {
                    enable(1),
                    disable(2)
                }
            ACCESS  read-write
            STATUS  mandatory
            DESCRIPTION
                "Implicit Bypass XC"
            ::= { systemProtectionEntry 8 }

--
--  ALS/APSD Table
--
    alsTable                OBJECT IDENTIFIER ::= { system 16 }

        alsEnable  OBJECT-TYPE
            SYNTAX  INTEGER {
                    off(1),
                    on(2)
                }
            ACCESS  read-write
            STATUS  mandatory
            DESCRIPTION
                "APSD enable"
            ::= { alsTable 1 }

        alsPulseRepetitionTime  OBJECT-TYPE
            SYNTAX  INTEGER (60..300)
            ACCESS  read-write
            STATUS  mandatory
            DESCRIPTION
                "ALS/APSD pulse repetition time for automatic restart(sec)"
            ::= { alsTable 2 }

        alsXcu1P1ManualRestart  OBJECT-TYPE
            SYNTAX  INTEGER {
                    off(1),
                    start(2)
                }
            ACCESS  read-write
            STATUS  mandatory
            DESCRIPTION
                "ALS XCU1 Port1(W1) manual restart"
            ::= { alsTable 3 }

        alsXcu1P2ManualRestart  OBJECT-TYPE
            SYNTAX  INTEGER {
                    off(1),
                    start(2)
                }
            ACCESS  read-write
            STATUS  mandatory
            DESCRIPTION
                "ALS XCU1 Port2(W2) manual restart"
            ::= { alsTable 4 }

        alsXcu2P1ManualRestart  OBJECT-TYPE
            SYNTAX  INTEGER {
                    off(1),
                    start(2)
                }
            ACCESS  read-write
            STATUS  mandatory
            DESCRIPTION
                "ALS XCU2 Port1(E1) manual restart"
            ::= { alsTable 5 }

        alsXcu2P2ManualRestart  OBJECT-TYPE
            SYNTAX  INTEGER {
                    off(1),
                    start(2)
                }
            ACCESS  read-write
            STATUS  mandatory
            DESCRIPTION
                "ALS XCU2 Port2(E2) manual restart"
            ::= { alsTable 6 }

        alsXcu1P1PowerDown  OBJECT-TYPE
            SYNTAX  INTEGER {
                    off(1),
                    on(2)
                }
            ACCESS  read-write
            STATUS  mandatory
            DESCRIPTION
                "ALS XCU1 Port1(W1) power down"
            ::= { alsTable 7 }

        alsXcu1P2PowerDown  OBJECT-TYPE
            SYNTAX  INTEGER {
                    off(1),
                    on(2)
                }
            ACCESS  read-write
            STATUS  mandatory
            DESCRIPTION
                "ALS XCU1 Port2(W2) power down"
            ::= { alsTable 8 }

        alsXcu2P1PowerDown  OBJECT-TYPE
            SYNTAX  INTEGER {
                    off(1),
                    on(2)
                }
            ACCESS  read-write
            STATUS  mandatory
            DESCRIPTION
                "ALS XCU2 Port1(E1) power down"
            ::= { alsTable 9 }

        alsXcu2P2PowerDown  OBJECT-TYPE
            SYNTAX  INTEGER {
                    off(1),
                    on(2)
                }
            ACCESS  read-write
            STATUS  mandatory
            DESCRIPTION
                "ALS XCU2 Port2(E2) power down"
            ::= { alsTable 10 }

--
--  SD/SF Alarm Threshold Table
--
    sdsfAlarmThresholdTable         OBJECT IDENTIFIER ::= { system 17 }

        cMs-LineSdThreshold     OBJECT-TYPE
            SYNTAX  INTEGER {
                    e-3(1),
                    e-4(2),
                    e-5(3),
                    e-6(4),
                    e-7(5),
                    e-8(6),
                    e-9(7),
                    e-10(8),
                    e-11(9)
                }
            ACCESS  read-write
            STATUS  mandatory
            DESCRIPTION
                "MS/line sd threshold"
            ::= { sdsfAlarmThresholdTable 1 }

        cMS-LineSfThreshold             OBJECT-TYPE
            SYNTAX  INTEGER {
                    e-3(1),
                    e-4(2),
                    e-5(3),
                    e-6(4),
                    e-7(5),
                    e-8(6),
                    e-9(7),
                    e-10(8),
                    e-11(9)
                }
            ACCESS  read-write
            STATUS  mandatory
            DESCRIPTION
                "MS/line sf threshold"
            ::= { sdsfAlarmThresholdTable 2 }

        cHO-STSPathSdThreshold          OBJECT-TYPE
            SYNTAX  INTEGER {
                    e-4(2),
                    e-5(3),
                    e-6(4),
                    e-7(5),
                    e-8(6),
                    e-9(7),
                    e-10(8),
                    e-11(9)
                }
            ACCESS  read-write
            STATUS  mandatory
            DESCRIPTION
                "HO/STS path sd threshold"
            ::= { sdsfAlarmThresholdTable 3 }

        cHO-STSPathSfThreshold          OBJECT-TYPE
            SYNTAX  INTEGER {
                    e-4(2),
                    e-5(3),
                    e-6(4),
                    e-7(5),
                    e-8(6),
                    e-9(7),
                    e-10(8),
                    e-11(9)
                }
            ACCESS  read-write
            STATUS  mandatory
            DESCRIPTION
                "HO/STS path sf threshold"
            ::= { sdsfAlarmThresholdTable 4 }

        cLO-VTPathSdThreshold           OBJECT-TYPE
            SYNTAX  INTEGER {
                    e-3(1),
                    e-4(2),
                    e-5(3),
                    e-6(4),
                    e-7(5),
                    e-8(6),
                    e-9(7),
                    e-10(8),
                    e-11(9)
                }
            ACCESS  read-write
            STATUS  mandatory
            DESCRIPTION
                "LO/VT path sd threshold"
            ::= { sdsfAlarmThresholdTable 5 }

        cLO-VTPathSfThreshold           OBJECT-TYPE
            SYNTAX  INTEGER {
                    e-3(1),
                    e-4(2),
                    e-5(3),
                    e-6(4),
                    e-7(5),
                    e-8(6),
                    e-9(7),
                    e-10(8),
                    e-11(9)
                }
            ACCESS  read-write
            STATUS  mandatory
            DESCRIPTION
                "LO/VT path sf threshold"
            ::= { sdsfAlarmThresholdTable 6 }

--
-- Insert AIS Alarm Table
--
    insertAisAlarmTable                     OBJECT IDENTIFIER ::= { system 18 }

        cRsTim-TimLToAis                OBJECT-TYPE
            SYNTAX  INTEGER {
                    disable(1),
                    enable(2)
                }
            ACCESS  read-write
            STATUS  mandatory
            DESCRIPTION
                "rs-tim to ais"
            ::= { insertAisAlarmTable 1 }

        cMsAis-AisLToAis                OBJECT-TYPE
            SYNTAX  INTEGER {
                    disable(1),
                    enable(2)
                }
            ACCESS  read-write
            STATUS  mandatory
            DESCRIPTION
                "ms-ais to ais"
            ::= { insertAisAlarmTable 2 }

        cAuLop-LopPToAis                OBJECT-TYPE
            SYNTAX  INTEGER {
                    disable(1),
                    enable(2)
                }
            ACCESS  read-write
            STATUS  mandatory
            DESCRIPTION
                "au-lop to ais"
            ::= { insertAisAlarmTable 3 }

        cAuAis-AisPToAis                OBJECT-TYPE
            SYNTAX  INTEGER {
                    disable(1),
                    enable(2)
                }
            ACCESS  read-write
            STATUS  mandatory
            DESCRIPTION
                "au-ais to ais"
            ::= { insertAisAlarmTable 4 }

        cHpUneq-UneqPToAis              OBJECT-TYPE
            SYNTAX  INTEGER {
                    disable(1),
                    enable(2)
                }
            ACCESS  read-write
            STATUS  mandatory
            DESCRIPTION
                "hp-uneq to ais"
            ::= { insertAisAlarmTable 5 }

        cHpTim-TimPToAis                OBJECT-TYPE
            SYNTAX  INTEGER {
                    disable(1),
                    enable(2)
                }
            ACCESS  read-write
            STATUS  mandatory
            DESCRIPTION
                "hp-tim to ais"
            ::= { insertAisAlarmTable 6 }

        cHpLom-LomPToAis                OBJECT-TYPE
            SYNTAX  INTEGER {
                    disable(1),
                    enable(2)
                }
            ACCESS  read-write
            STATUS  mandatory
            DESCRIPTION
                "hp-lom to ais"
            ::= { insertAisAlarmTable 7 }

        cHpPlm-PlmPToAis                OBJECT-TYPE
            SYNTAX  INTEGER {
                    disable(1),
                    enable(2)
                }
            ACCESS  read-write
            STATUS  mandatory
            DESCRIPTION
                "hp-plm to ais"
            ::= { insertAisAlarmTable 8 }

        cTuLop-LopVToAis                OBJECT-TYPE
            SYNTAX  INTEGER {
                    disable(1),
                    enable(2)
                }
            ACCESS  read-write
            STATUS  mandatory
            DESCRIPTION
                "tu-lop to ais"
            ::= { insertAisAlarmTable 9 }

        cTuAis-AisVToAis                OBJECT-TYPE
            SYNTAX  INTEGER {
                    disable(1),
                    enable(2)
                }
            ACCESS  read-write
            STATUS  mandatory
            DESCRIPTION
                "tu-ais to ais"
            ::= { insertAisAlarmTable 10 }

        cLpUneq-UneqVToAis              OBJECT-TYPE
            SYNTAX  INTEGER {
                    disable(1),
                    enable(2)
                }
            ACCESS  read-write
            STATUS  mandatory
            DESCRIPTION
                "lp-uneqp to ais"
            ::= { insertAisAlarmTable 11 }


--
--   Overhead Setup Table (J0, J1, and C2)
--
    overheadSetupTable     OBJECT IDENTIFIER ::= { system 19 }
--
--   Line Path Overhead setup
--
        overhead-J0Table OBJECT-TYPE
            SYNTAX  SEQUENCE OF OverheadJ0Entry
            ACCESS  not-accessible
            STATUS  mandatory
            DESCRIPTION
                "Overhead J0 Table"
            ::= { overheadSetupTable 1 }

        overheadJ0Entry OBJECT-TYPE
            SYNTAX  OverheadJ0Entry
            ACCESS  not-accessible
            STATUS  mandatory
            DESCRIPTION
                "Overhead J0 Entry."
            INDEX { cJ0XCUIndex , cJ0PortIndex }
            ::= { overhead-J0Table 1 }

        OverheadJ0Entry ::= SEQUENCE {
            cJ0XCUIndex                 XcuNum,
            cJ0PortIndex                PortNum,
            cJ0J0-Length                MsgLen,
            cJ0J0-ExpectMsg             DisplayString (SIZE(0..64)),
            cJ0J0-TxMsg                 DisplayString (SIZE(0..64)),
            cJ0J0-RxMsg                 DisplayString (SIZE(0..64)),
            cJ0J0-ExpectMsg1Byte        INTEGER (0..255),
            cJ0J0-TxMsg1Byte            INTEGER (0..255),
            cJ0J0-RxMsg1Byte            INTEGER (0..255)
        }

        cJ0XCUIndex OBJECT-TYPE
            SYNTAX  XcuNum
            ACCESS  read-only
            STATUS  mandatory
            DESCRIPTION
                "The number of line trace message side index."
            ::= { overheadJ0Entry 1 }

        cJ0PortIndex OBJECT-TYPE
            SYNTAX  PortNum
            ACCESS  read-only
            STATUS  mandatory
            DESCRIPTION
                "The number of line trace message port number index."
            ::= { overheadJ0Entry 2 }

        cJ0J0-Length OBJECT-TYPE
            SYNTAX  MsgLen
            ACCESS  read-write
            STATUS  mandatory
            DESCRIPTION
                "The length of J0."
            ::= { overheadJ0Entry 3 }

        cJ0J0-ExpectMsg OBJECT-TYPE
            SYNTAX  DisplayString (SIZE(0..64))
            ACCESS  read-write
            STATUS  mandatory
            DESCRIPTION
                "The expected J0 message."
            ::= { overheadJ0Entry 4 }

        cJ0J0-TxMsg OBJECT-TYPE
            SYNTAX  DisplayString (SIZE(0..64))
            ACCESS  read-write
            STATUS  mandatory
            DESCRIPTION
                "The transmitted J0 message."
            ::= { overheadJ0Entry 5 }

        cJ0J0-RxMsg OBJECT-TYPE
            SYNTAX  DisplayString (SIZE(0..64))
            ACCESS  read-only
            STATUS  mandatory
            DESCRIPTION
                "The received J0 message."
            ::= { overheadJ0Entry 6 }

        cJ0J0-ExpectMsg1Byte OBJECT-TYPE
            SYNTAX  INTEGER (0..255)
            ACCESS  read-write
            STATUS  mandatory
            DESCRIPTION
                "The expected J0 message (1 Byte)."
            ::= { overheadJ0Entry 7 }

        cJ0J0-TxMsg1Byte OBJECT-TYPE
            SYNTAX  INTEGER (0..255)
            ACCESS  read-write
            STATUS  mandatory
            DESCRIPTION
                "The transmitted J0 message (1 Byte)."
            ::= { overheadJ0Entry 8 }

        cJ0J0-RxMsg1Byte OBJECT-TYPE
            SYNTAX  INTEGER (0..255)
            ACCESS  read-only
            STATUS  mandatory
            DESCRIPTION
                "The received J0 message (1 Byte)."
            ::= { overheadJ0Entry 9 }

--
--   High Order Path Overhead J1 and C2 setup
--
        overhead-J1-C2Table OBJECT-TYPE
            SYNTAX  SEQUENCE OF Overhead-J1-C2Entry
            ACCESS  not-accessible
            STATUS  mandatory
            DESCRIPTION
                "Overhead -J1-C2 Table"
            ::= { overheadSetupTable 2 }

        overhead-J1-C2Entry OBJECT-TYPE
            SYNTAX  Overhead-J1-C2Entry
            ACCESS  not-accessible
            STATUS  mandatory
            DESCRIPTION
                "Overhead J1 and C2 Entry."
            INDEX { cJ1-C2XCUIndex , cJ1-C2PortIndex , cJ1-C2AUG1STS3Index , cJ1-C2VC3STS1Index }
            ::= { overhead-J1-C2Table 1 }

        Overhead-J1-C2Entry ::= SEQUENCE {
            cJ1-C2XCUIndex              XcuNum,
            cJ1-C2PortIndex             PortNum,
            cJ1-C2AUG1STS3Index         Aug1Sts3Num,
            cJ1-C2VC3STS1Index          Vc3Sts1Num,
            cJ1-C2J1-Length             MsgLen,
            cJ1-C2J1-ExpectMsg          DisplayString (SIZE(0..64)),
            cJ1-C2J1-TxMsg              DisplayString (SIZE(0..64)),
            cJ1-C2J1-RxMsg              DisplayString (SIZE(0..64)),
            cJ1-C2C2-EPSL               Integer32(0..255),
            cJ1-C2J1-ExpMsg1Byte        INTEGER(0..255),
            cJ1-C2J1-TxMsg1Byte         INTEGER(0..255),
            cJ1-C2J1-RxMsg1Byte         INTEGER(0..255),
            cJ1-C2C2-TxPSL              Integer32(0..255),
            cJ1-C2C2-RxPSL              Integer32(0..255)
        }

        cJ1-C2XCUIndex OBJECT-TYPE
            SYNTAX  XcuNum
            ACCESS  read-only
            STATUS  mandatory
            DESCRIPTION
                "The number of trace message side index."
            ::= { overhead-J1-C2Entry 1 }

        cJ1-C2PortIndex OBJECT-TYPE
            SYNTAX  PortNum
            ACCESS  read-only
            STATUS  mandatory
            DESCRIPTION
                "The number of  trace message port number index."
            ::= { overhead-J1-C2Entry 2 }

        cJ1-C2AUG1STS3Index OBJECT-TYPE
            SYNTAX  Aug1Sts3Num
            ACCESS  read-only
            STATUS  mandatory
            DESCRIPTION
                "The number of  trace message AUG1/STS3 index."
            ::= { overhead-J1-C2Entry 3 }

        cJ1-C2VC3STS1Index OBJECT-TYPE
            SYNTAX  Vc3Sts1Num
            ACCESS  read-only
            STATUS  mandatory
            DESCRIPTION
                "The number of  trace message VC3/STS1 index."
            ::= { overhead-J1-C2Entry 4 }

        cJ1-C2J1-Length OBJECT-TYPE
            SYNTAX  MsgLen
            ACCESS  read-write
            STATUS  mandatory
            DESCRIPTION
                "The length of J1."
            ::= { overhead-J1-C2Entry 5 }

        cJ1-C2J1-ExpectMsg OBJECT-TYPE
            SYNTAX  DisplayString (SIZE(0..64))
            ACCESS  read-write
            STATUS  mandatory
            DESCRIPTION
                "The expected J1 message."
            ::= { overhead-J1-C2Entry 6 }

        cJ1-C2J1-TxMsg OBJECT-TYPE
            SYNTAX  DisplayString (SIZE(0..64))
            ACCESS  read-write
            STATUS  mandatory
            DESCRIPTION
                "The transmitted J1 message."
            ::= { overhead-J1-C2Entry 7 }

        cJ1-C2J1-RxMsg OBJECT-TYPE
            SYNTAX  DisplayString (SIZE(0..64))
            ACCESS  read-only
            STATUS  mandatory
            DESCRIPTION
                "The received J1 message."
            ::= { overhead-J1-C2Entry 8 }

        cJ1-C2C2-EPSL OBJECT-TYPE
            SYNTAX  Integer32(0..255)
            ACCESS  read-write
            STATUS  mandatory
            DESCRIPTION
                "The expected C2 ."
            ::= { overhead-J1-C2Entry 9 }

        cJ1-C2J1-ExpMsg1Byte OBJECT-TYPE
            SYNTAX  INTEGER (0..255)
            ACCESS  read-write
            STATUS  mandatory
            DESCRIPTION
                "The expected J1 message (1 Byte)."
            ::= { overhead-J1-C2Entry 10 }

        cJ1-C2J1-TxMsg1Byte OBJECT-TYPE
            SYNTAX  INTEGER (0..255)
            ACCESS  read-write
            STATUS  mandatory
            DESCRIPTION
                "The transmitted J1 message (1 Byte)."
            ::= { overhead-J1-C2Entry 11 }

        cJ1-C2J1-RxMsg1Byte OBJECT-TYPE
            SYNTAX  INTEGER (0..255)
            ACCESS  read-only
            STATUS  mandatory
            DESCRIPTION
                "The received J1 message (1 Byte)."
            ::= { overhead-J1-C2Entry 12 }

        cJ1-C2C2-TxPSL OBJECT-TYPE
            SYNTAX  Integer32(0..255)
            ACCESS  read-write
            STATUS  mandatory
            DESCRIPTION
                "The Tx C2 ."
            ::= { overhead-J1-C2Entry 13 }

        cJ1-C2C2-RxPSL OBJECT-TYPE
            SYNTAX  Integer32(0..255)
            ACCESS  read-only
            STATUS  mandatory
            DESCRIPTION
                "The Rx C2 ."
            ::= { overhead-J1-C2Entry 14 }

--
--   Diagnostics Setup and Monitor Table
--

        diagnosticsTable OBJECT-TYPE
            SYNTAX  SEQUENCE OF DiagnosticsEntry
            ACCESS  not-accessible
            STATUS  mandatory
            DESCRIPTION
                "Diagnostics Table."
            ::= { system 21 }

        diagnosticsEntry OBJECT-TYPE
            SYNTAX  DiagnosticsEntry
            ACCESS  not-accessible
            STATUS  mandatory
            DESCRIPTION
                "Diagnostics Entry."
            INDEX { diagXCUIndex }
            ::= { diagnosticsTable 1 }

        DiagnosticsEntry ::= SEQUENCE {
            diagXCUIndex                XcuNum,
            diagPort                    INTEGER,
            diagAUG1STS3                Aug1Sts3Num,
            diagVC4VC3-STS3STS1         INTEGER,
            diagBERTOnOff               INTEGER,
            diagInsert-Error            INTEGER,
            diagSyncStatus              INTEGER,
            diagElapsed-Seconds         INTEGER,
            diagBitErrorCount           INTEGER,
            diagBER                     DisplayString (SIZE (0..25) ),
            diagES                      INTEGER,
            diagESR                     DisplayString (SIZE (0..25) ),
            diagSES                     INTEGER,
            diagSESR                    DisplayString (SIZE (0..25) ),
            diagUAS                     INTEGER,
            diagInserted-Error-Count    INTEGER
        }
        diagXCUIndex  OBJECT-TYPE
            SYNTAX  XcuNum
            ACCESS  read-only
            STATUS  mandatory
            DESCRIPTION
                "XCU1(W), XCU2(E)"
            ::= { diagnosticsEntry 1 }

        diagPort  OBJECT-TYPE
            SYNTAX  INTEGER{
                    port1(1),
                    port1-Full(2),
                    port2(3),
                    port2-Full(4)
                }
            ACCESS  read-write
            STATUS  mandatory
            DESCRIPTION
                "Port#1,Port#1 Full mode, Port#2,Port#2 Full mode,"
            ::= { diagnosticsEntry 2 }

        diagAUG1STS3  OBJECT-TYPE
            SYNTAX  Aug1Sts3Num
            ACCESS  read-write
            STATUS  mandatory
            DESCRIPTION
                "aug1/STS3#1~4"
            ::= { diagnosticsEntry 3 }

        diagVC4VC3-STS3STS1  OBJECT-TYPE
            SYNTAX  INTEGER{
                    vc4STS3-Full(1),
                    vc3STS1-Full(2),
--                    vc3STS1-1(3),
--                    vc3STS1-2(4),
--                    vc3STS1-3(5),
                    not-available(100)
                }
            ACCESS  read-write
            STATUS  mandatory
            DESCRIPTION
                ""
            ::= { diagnosticsEntry 4 }

        diagBERTOnOff  OBJECT-TYPE
            SYNTAX  INTEGER{
                    off(1),
                    on(2),
                    reset(3)
                }
            ACCESS  read-write
            STATUS  mandatory
            DESCRIPTION
                "Pattern OFF on PRBS"
            ::= { diagnosticsEntry 5 }

        diagInsert-Error  OBJECT-TYPE
            SYNTAX  INTEGER{
                    none(1),
                    insert(2)
                }
            ACCESS  read-write
            STATUS  mandatory
            DESCRIPTION
                "Insert Errors"
            ::= { diagnosticsEntry 6 }

        diagSyncStatus  OBJECT-TYPE
            SYNTAX  INTEGER{
                    unsync(1),
                    sync(2)
                }
            ACCESS  read-only
            STATUS  mandatory
            DESCRIPTION
                "Unsync and sync"
            ::= { diagnosticsEntry 7 }

        diagElapsed-Seconds  OBJECT-TYPE
            SYNTAX  INTEGER
            ACCESS  read-only
            STATUS  mandatory
            DESCRIPTION
                "Elapsed Seconds"
            ::= { diagnosticsEntry 8 }

        diagBitErrorCount  OBJECT-TYPE
            SYNTAX  INTEGER
            ACCESS  read-only
            STATUS  mandatory
            DESCRIPTION
                "Bit Error count"
            ::= { diagnosticsEntry 9 }

        diagBER  OBJECT-TYPE
            SYNTAX  DisplayString (SIZE (0..25) )
            ACCESS  read-only
            STATUS  mandatory
            DESCRIPTION
                "BER"
            ::= { diagnosticsEntry 10 }

        diagES  OBJECT-TYPE
            SYNTAX  INTEGER
            ACCESS  read-only
            STATUS  mandatory
            DESCRIPTION
                "Error seconds"
            ::= { diagnosticsEntry 11 }

        diagESR  OBJECT-TYPE
            SYNTAX  DisplayString (SIZE (0..25) )
            ACCESS  read-only
            STATUS  mandatory
            DESCRIPTION
                "Error seconds ratio"
            ::= { diagnosticsEntry 12 }

        diagSES  OBJECT-TYPE
            SYNTAX  INTEGER
            ACCESS  read-only
            STATUS  mandatory
            DESCRIPTION
                "Severely error second"
            ::= { diagnosticsEntry 13 }

        diagSESR  OBJECT-TYPE
            SYNTAX  DisplayString (SIZE (0..25) )
            ACCESS  read-only
            STATUS  mandatory
            DESCRIPTION
                "Severely error second ratio"
            ::= { diagnosticsEntry 14 }

        diagUAS  OBJECT-TYPE
            SYNTAX  INTEGER
            ACCESS  read-only
            STATUS  mandatory
            DESCRIPTION
                "Unavailable Seconds"
            ::= { diagnosticsEntry 15 }

        diagInserted-Error-Count  OBJECT-TYPE
            SYNTAX  INTEGER
            ACCESS  read-only
            STATUS  mandatory
            DESCRIPTION
                "Inserted Error Count(s)"
            ::= { diagnosticsEntry 16 }

--
--  Power State Table
--
        powerTable  OBJECT-TYPE
            SYNTAX  SEQUENCE OF PowerEntry
            ACCESS  not-accessible
            STATUS  mandatory
            DESCRIPTION
                "Power state table"
            ::= { system 22 }

        powerEntry  OBJECT-TYPE
            SYNTAX  PowerEntry
            ACCESS  not-accessible
            STATUS  mandatory
            DESCRIPTION
                "Power state entry"
            INDEX { powerIndex }
            ::= { powerTable 1 }

        PowerEntry ::= SEQUENCE {
            powerIndex                  INTEGER,
            powerType                   INTEGER,
            powerState                  INTEGER
        }

        powerIndex  OBJECT-TYPE
            SYNTAX  INTEGER{
                    power-1(1),
                    power-2(2)
                }
            ACCESS  read-only
            STATUS  mandatory
            DESCRIPTION
                "power index"
            ::= { powerEntry 1 }

        powerType  OBJECT-TYPE
            SYNTAX  INTEGER {
                    none(1),
                    dc-48v(2),
                    dc-24v(3),
                    ac-dc(4),
                    dc-20v-to-60v(5),
                    unequipped(6),
                    dc-125v(7),
                    dc-250v(8)
                }
            ACCESS  read-only
            STATUS  mandatory
            DESCRIPTION
                "power type"
            ::= { powerEntry 2 }

        powerState  OBJECT-TYPE
            SYNTAX  INTEGER {
                    loss(1),
                    on(2),
                    none(3)
                }
            ACCESS  read-only
            STATUS  mandatory
            DESCRIPTION
                "power state"
            ::= { powerEntry 3 }

--
--  Fan State Table
--
        fanTable  OBJECT-TYPE
            SYNTAX  SEQUENCE OF FanEntry
            ACCESS  not-accessible
            STATUS  mandatory
            DESCRIPTION
                "Fan state table"
            ::= { system 23 }

        fanEntry  OBJECT-TYPE
            SYNTAX  FanEntry
            ACCESS  not-accessible
            STATUS  mandatory
            DESCRIPTION
                "Fan state entry"
            INDEX { fanIndex }
            ::= { fanTable 1 }

        FanEntry ::= SEQUENCE {
            fanIndex                    INTEGER,
            fanState                    INTEGER
        }

        fanIndex  OBJECT-TYPE
            SYNTAX  INTEGER{
                    fan-module(1),
                    fan-1(2),
                    fan-2(3),
                    fan-3(4),
                    fan-4(5),
                    fan-5(6),
                    fan-6(7),
                    fan-7(8),
                    fan-8(9)
                }
            ACCESS  read-only
            STATUS  mandatory
            DESCRIPTION
                "fan index"
            ::= { fanEntry 1 }

        fanState  OBJECT-TYPE
            SYNTAX  INTEGER {
                    on(1),
                    off(2),
                    fail(3),
                    unequipped(4),
                    none(5)
                }
            ACCESS  read-only
            STATUS  mandatory
            DESCRIPTION
                "fan state"
            ::= { fanEntry 2 }

--
--      Bridge Spannnig Tree Info
--

    bridgeSpanningTreeTable OBJECT IDENTIFIER  ::= { system 24 }

--
--
    rstpRootTable             OBJECT IDENTIFIER ::= { bridgeSpanningTreeTable 1 }
        rstpRootMacAddr  OBJECT-TYPE
            SYNTAX  DisplayString (SIZE (0..255))
            ACCESS  read-only
            STATUS  mandatory
            DESCRIPTION
                "An entry in the bridge Spanning Tree table."
            ::= { rstpRootTable 1 }

        rstpRootPriority OBJECT-TYPE
            SYNTAX  INTEGER
            ACCESS  read-only
            STATUS  mandatory
            DESCRIPTION
                "An rstp root priority."
            ::= { rstpRootTable 2 }

        rstpRootCost     OBJECT-TYPE
            SYNTAX  INTEGER
            ACCESS  read-only
            STATUS  mandatory
            DESCRIPTION
                "An rstp root cost."
            ::= { rstpRootTable 3 }

        rstpRootMaxAge OBJECT-TYPE
            SYNTAX  INTEGER
            ACCESS  read-only
            STATUS  mandatory
            DESCRIPTION
                "An rstp root max age."
            ::= { rstpRootTable 4 }

        rstpRootHelloTime OBJECT-TYPE
            SYNTAX  INTEGER
            ACCESS  read-only
            STATUS  mandatory
            DESCRIPTION
                "An rstp root hello time."
            ::= { rstpRootTable 5 }

        rstpRootFwdDelay OBJECT-TYPE
            SYNTAX  INTEGER
            ACCESS  read-only
            STATUS  mandatory
            DESCRIPTION
                "An rstp root forward delay."
            ::= { rstpRootTable 6 }

--
--
    rstpBridgeTable           OBJECT IDENTIFIER ::= { bridgeSpanningTreeTable 2 }

        rstpbrgMacAddr  OBJECT-TYPE
            SYNTAX  DisplayString (SIZE (0..255))
            ACCESS  read-only
            STATUS  mandatory
            DESCRIPTION
                "An rstp bridge mac address."
            ::= { rstpBridgeTable 1 }

        rstpbrgPriority OBJECT-TYPE
            SYNTAX  INTEGER (0..65535)
            ACCESS  read-write
            STATUS  mandatory
            DESCRIPTION
                "An rstp bridge priority."
            ::= { rstpBridgeTable 2 }

        rstpbrgMaxAge OBJECT-TYPE
            SYNTAX  INTEGER (6..40)
            ACCESS  read-write
            STATUS  mandatory
            DESCRIPTION
                "An rstp bridge max age."
            ::= { rstpBridgeTable 3 }

        rstpbrgHelloTime OBJECT-TYPE
            SYNTAX  INTEGER (1..10)
            ACCESS  read-write
            STATUS  mandatory
            DESCRIPTION
                "An rstp bridge hello time."
            ::= { rstpBridgeTable 4 }

        rstpbrgFwdDelay OBJECT-TYPE
            SYNTAX  INTEGER (4..30)
            ACCESS  read-write
            STATUS  mandatory
            DESCRIPTION
                "An rstp bridge forward delay."
            ::= { rstpBridgeTable 5 }

        rstpbrgAgingTime OBJECT-TYPE
            SYNTAX  INTEGER (10..999)
            ACCESS  read-write
            STATUS  mandatory
            DESCRIPTION
                "An rstp bridge aging time."
            ::= { rstpBridgeTable 6 }

--
--
        rstpPortTable  OBJECT-TYPE
            SYNTAX  SEQUENCE OF RstpPortEntry
            ACCESS  not-accessible
            STATUS  mandatory
            DESCRIPTION
                "rstp port table."
            ::= { bridgeSpanningTreeTable  3 }

        rstpPortEntry  OBJECT-TYPE
            SYNTAX  RstpPortEntry
            ACCESS  not-accessible
            STATUS  mandatory
            DESCRIPTION
                "An entry in rstp port table."
            INDEX { portNumIndex }
            ::= { rstpPortTable 1 }

        RstpPortEntry ::= SEQUENCE  {
            portNumIndex                NiIndex,
            portRoot                    INTEGER,
            portState                   INTEGER,
            portCost                    INTEGER(1..999),
            portPrio                    INTEGER(0..255),
            edgePort                    INTEGER,
            point-to-point              INTEGER
        }

        portNumIndex  OBJECT-TYPE
            SYNTAX  NiIndex
            ACCESS  read-only
            STATUS  mandatory
            DESCRIPTION
                "rstp port number select."
            ::= { rstpPortEntry  1 }

        portRoot  OBJECT-TYPE
            SYNTAX  INTEGER {
                    no(1),
                    yes(2),
                    not-available(100)
                }
            ACCESS  read-only
            STATUS  mandatory
            DESCRIPTION
                "rstp port role."
            ::= { rstpPortEntry 2 }

        portState  OBJECT-TYPE
            SYNTAX  INTEGER {
                    disable(1),
                    listen(2),
                    learn(3),
                    forward(4),
                    block(5),
                    not-available(100)
                }
            ACCESS  read-only
            STATUS  mandatory
            DESCRIPTION
                "rstp port state."
            ::= { rstpPortEntry 3 }

        portCost  OBJECT-TYPE
            SYNTAX  INTEGER (1..999)
            ACCESS  read-write
            STATUS  mandatory
            DESCRIPTION
                "rstp port cost."
            ::= { rstpPortEntry 4 }

        portPrio  OBJECT-TYPE
            SYNTAX  INTEGER (0..255)
            ACCESS  read-write
            STATUS  mandatory
            DESCRIPTION
                "rstp port priority."
            ::= { rstpPortEntry 5 }

        edgePort  OBJECT-TYPE
            SYNTAX  INTEGER {
                    no(1),
                    yes(2),
                    not-available(100)
                }
            ACCESS  read-write
            STATUS  mandatory
            DESCRIPTION
                "rstp edge port."
            ::= { rstpPortEntry 6 }

        point-to-point  OBJECT-TYPE
            SYNTAX  INTEGER {
                    no(1),
                    yes(2),
                    not-available(100)
                }
            ACCESS  read-write
            STATUS  mandatory
            DESCRIPTION
                "rstp port link type."
            ::= { rstpPortEntry 7 }

--
--  network interface setup table
--


        networkInterfaceTable  OBJECT-TYPE
            SYNTAX  SEQUENCE OF NetworkInterfaceEntry
            ACCESS  not-accessible
            STATUS  mandatory
            DESCRIPTION
                "Network Interface Setup Table"
            ::= { system 25 }

        networkInterfaceEntry  OBJECT-TYPE
            SYNTAX  NetworkInterfaceEntry
            ACCESS  not-accessible
            STATUS  mandatory
            DESCRIPTION
                "An entry in Network Interface Setup table."
            INDEX { interfaceNI }
            ::= { networkInterfaceTable 1 }

        NetworkInterfaceEntry ::= SEQUENCE  {
            interfaceNI                 NiIndex,
            interfaceMode               NiMode,
            interfaceRIP                INTEGER,
            interfaceIPAddress          IpAddress,
            interfaceSubnetMask         IpAddress,
            interfaceFrame              INTEGER,
            interfaceActivate           INTEGER,
            interfaceResult             INTEGER,
            areaid                      IpAddress,
            interfacePPPstat            INTEGER
--IPv6

--               networkInterfaceErrorMsg
--                 DisplayString (SIZE(0..255))



    }

        interfaceNI  OBJECT-TYPE
            SYNTAX  NiIndex
            ACCESS  read-only
            STATUS  mandatory
            DESCRIPTION
                "Network Interface Number"
            ::= { networkInterfaceEntry  1 }

        interfaceMode  OBJECT-TYPE
            SYNTAX  NiMode
            ACCESS  read-write
            STATUS  mandatory
            DESCRIPTION
                "Network Interface Mode"
            ::= { networkInterfaceEntry  2 }

        interfaceRIP  OBJECT-TYPE
            SYNTAX  INTEGER {
                    off(1),
                    rip1(2),
                    rip2(3),
                    ospf(4)
--IPv6
                }
            ACCESS  read-write
            STATUS  mandatory
            DESCRIPTION
                "Network Interface RIP Selection"
            ::= { networkInterfaceEntry  3 }

        interfaceIPAddress  OBJECT-TYPE
            SYNTAX  IpAddress
            ACCESS  read-write
            STATUS  mandatory
            DESCRIPTION
                "Network Interface IP Address"
            ::= { networkInterfaceEntry  4 }

        interfaceSubnetMask  OBJECT-TYPE
            SYNTAX  IpAddress
            ACCESS  read-write
            STATUS  mandatory
            DESCRIPTION
                "Network Interface Subnet Mask"
            ::= { networkInterfaceEntry  5 }

        interfaceFrame  OBJECT-TYPE
            SYNTAX   INTEGER {
                    ethernet(1),
                    hdlc(2),
                    ppp(3)
                }
            ACCESS  read-write
            STATUS  mandatory
            DESCRIPTION
                "Network Interface Frame Setup"
            ::= { networkInterfaceEntry  6 }

        interfaceActivate  OBJECT-TYPE
            SYNTAX   INTEGER {
                    no(1),
                    yes(2),
                    done(3),
                    waitForUser(4)
                }
            ACCESS  read-write
            STATUS  mandatory
            DESCRIPTION
                "Network Interface Setting Activate"
            ::= { networkInterfaceEntry  7}

        interfaceResult  OBJECT-TYPE
            SYNTAX   INTEGER {
                    none(1),
                    fail(2),
                    success(3)
                }
            ACCESS  read-only
            STATUS  mandatory
            DESCRIPTION
                "Network Interface Setting Result"
            ::= { networkInterfaceEntry  8}

--IPv6
        areaid  OBJECT-TYPE
            SYNTAX  IpAddress
            ACCESS  read-write
            STATUS  mandatory
            DESCRIPTION
                "Area ID"
            ::= { networkInterfaceEntry 9}

        interfacePPPstat  OBJECT-TYPE
            SYNTAX   INTEGER {
                    na(1),
                    pppup(2),
                    pppdown(3)
                }
            ACCESS  read-only
            STATUS  current
            DESCRIPTION
                "Network Interface ppp status"
            ::= { networkInterfaceEntry  10}

--IPv6

--        networkInterfaceErrorMsg  OBJECT-TYPE
--             SYNTAX  DisplayString (SIZE(0..255))
--             ACCESS  read-only
--             STATUS  mandatory
--             DESCRIPTION
--                "Network Interface Setup Error Message"
--            ::= { networkInterfaceEntry  7 }


--
--  Static Route Setup table
--


        staticRouteTable  OBJECT-TYPE
            SYNTAX  SEQUENCE OF StaticRouteEntry
            ACCESS  not-accessible
            STATUS  mandatory
            DESCRIPTION
                "Static Route Setup Table"
            ::= { system 26 }

        staticRouteEntry  OBJECT-TYPE
            SYNTAX  StaticRouteEntry
            ACCESS  not-accessible
            STATUS  mandatory
            DESCRIPTION
                "An entry in Static Route Setup table."
            INDEX { routeIndex }
            ::= { staticRouteTable 1 }

        StaticRouteEntry ::= SEQUENCE  {
            routeIndex                  INTEGER,
            routeNet-Destination        IpAddress,
            routeNet-Mask               IpAddress,
            routeGateway                IpAddress,
            routeNI                     NiNum,
            routeActivate               INTEGER,
            routeResult                 INTEGER

--               staticRouteErrorMsg
--                 DisplayString (SIZE(0..255))



    }

        routeIndex  OBJECT-TYPE
            SYNTAX  INTEGER(1..16)
            ACCESS  read-only
            STATUS  mandatory
            DESCRIPTION
                "Static route Index"
            ::= { staticRouteEntry  1 }

        routeNet-Destination  OBJECT-TYPE
            SYNTAX  IpAddress
            ACCESS  read-write
            STATUS  mandatory
            DESCRIPTION
                "Static route Network Destination"
            ::= { staticRouteEntry  2 }

        routeNet-Mask  OBJECT-TYPE
            SYNTAX  IpAddress
            ACCESS  read-write
            STATUS  mandatory
            DESCRIPTION
                "Static route Network Mask"
            ::= { staticRouteEntry  3 }

        routeGateway   OBJECT-TYPE
            SYNTAX  IpAddress
            ACCESS  read-write
            STATUS  mandatory
            DESCRIPTION
                "Static Route Gateway"
            ::= { staticRouteEntry  4 }

        routeNI  OBJECT-TYPE
            SYNTAX  NiNum
            ACCESS  read-write
            STATUS  mandatory
            DESCRIPTION
                "Static Route Network Interface"
            ::= { staticRouteEntry  5 }


        routeActivate  OBJECT-TYPE
            SYNTAX   INTEGER {
                    no(1),
                    yes(2),
                    none(3)
                }
            ACCESS  read-write
            STATUS  mandatory
            DESCRIPTION
                "Static Route Setting Activate"
            ::= { staticRouteEntry  6}

        routeResult  OBJECT-TYPE
            SYNTAX   INTEGER {
                    none(1),
                    fail(2),
                    success(3)
                }
            ACCESS  read-only
            STATUS  mandatory
            DESCRIPTION
                "Static Route Setting Result"
            ::= { staticRouteEntry  7}

--
--    SNTP Setup Table
--
    sntpSetupTable OBJECT IDENTIFIER ::= { system 27 }


        ccSntpSetupOnOff  OBJECT-TYPE
            SYNTAX  INTEGER {
                    enable(1),
                    disable(2)
                }
            ACCESS  read-write
            STATUS  mandatory
            DESCRIPTION
                "SNTP On/Off"
            ::= { sntpSetupTable 1 }

        ccSntpSetupServer1  OBJECT-TYPE
            SYNTAX  IpAddress
            ACCESS  read-write
            STATUS  mandatory
            DESCRIPTION
                "SNTP Sever 1"
            ::= { sntpSetupTable 2 }

        ccSntpSetupServer2  OBJECT-TYPE
            SYNTAX  IpAddress
            ACCESS  read-write
            STATUS  mandatory
            DESCRIPTION
                "SNTP Sever 2"
            ::= { sntpSetupTable 3 }

        ccSntpSetupTimeZone  OBJECT-TYPE
            SYNTAX  INTEGER
            ACCESS  read-write
            STATUS  mandatory
            DESCRIPTION
                "SNTP Time Zone  0,1,2,...10,11,12,-12,-11,-10,...,-3,-2,-1"
            ::= { sntpSetupTable 4 }

        ccSntpUpdatePeriod  OBJECT-TYPE
            SYNTAX  Integer32 (5..1440)
            MAX-ACCESS  read-write
            STATUS  current
            DESCRIPTION
                "SNTP Update Period (minute)"
            ::= { sntpSetupTable 5 }

        ccSntpIPv6Server1  OBJECT-TYPE
            SYNTAX  DisplayString (SIZE(2..40))
            ACCESS  read-write
            STATUS  mandatory
            DESCRIPTION
                "SNTP IPv6 Sever 1"
            ::= { sntpSetupTable 6 }

        ccSntpIPv6Server2  OBJECT-TYPE
            SYNTAX  DisplayString (SIZE(2..40))
            ACCESS  read-write
            STATUS  mandatory
            DESCRIPTION
                "SNTP IPv6 Sever 2"
            ::= { sntpSetupTable 7 }

        ccSntpLastUpdate  OBJECT-TYPE
            SYNTAX  DisplayString
            ACCESS  read-only
            STATUS  mandatory
            DESCRIPTION
                "SNTP last update time"
            ::= { sntpSetupTable 8 }

        ccSntpTimeZoneMinutes  OBJECT-TYPE
            SYNTAX  INTEGER {
                    min00(1),
                    min15(2),
                    min30(3),
                    min45(4)
                }
            ACCESS  read-write
            STATUS  mandatory
            DESCRIPTION
                "SNTP Time Zone minutes"
            ::= { sntpSetupTable 9 }


--
--  DHCP Table
--

    dhcpInformationTable    OBJECT IDENTIFIER ::= { system 28 }

        ccDhcpServerIPTable  OBJECT-TYPE
            SYNTAX  IpAddress
            ACCESS  read-write
            STATUS  mandatory
            DESCRIPTION
                "DHCP server IP table."
            ::= { dhcpInformationTable 1 }

        ccDhcpRelayTable  OBJECT-TYPE
            SYNTAX  INTEGER {
                    disable(1),
                    enable(2)
                }
            ACCESS  read-write
            STATUS  mandatory
            DESCRIPTION
                "DHCP relay table."
            ::= { dhcpInformationTable 2 }

        ccDhcpIPv6Server  OBJECT-TYPE
            SYNTAX  DisplayString (SIZE(2..40))
            ACCESS  read-write
            STATUS  mandatory
            DESCRIPTION
                "DHCP IPv6 server."
            ::= { dhcpInformationTable 3 }


--
--      performance threshold Table
--

    perfThresholdTable              OBJECT IDENTIFIER ::= { system 29 }

--
--      performance mask Threshold Table
--

    perfTCAMaskTable                OBJECT IDENTIFIER ::= { perfThresholdTable 1 }

        tcaMaskRS-Section       OBJECT-TYPE
            SYNTAX  INTEGER {
                    disable(1),
                    enable(2)
                }
            ACCESS  read-write
            STATUS  mandatory
            DESCRIPTION
                "RS-Section Threshold Mask Setup."
            ::= { perfTCAMaskTable 1  }

        tcaMaskMS-Line  OBJECT-TYPE
            SYNTAX  INTEGER {
                    disable(1),
                    enable(2)
                }
            ACCESS  read-write
            STATUS  mandatory
            DESCRIPTION
                "MS-Line Threshold Mask Setup."
            ::= { perfTCAMaskTable 2  }

        tcaMaskFarEndMS-Line    OBJECT-TYPE
            SYNTAX  INTEGER {
                    disable(1),
                    enable(2)
                }
            ACCESS  read-write
            STATUS  mandatory
            DESCRIPTION
                "Far End MS-Line Threshold Mask Setup."
            ::= { perfTCAMaskTable 3 }

        tcaMaskHP-STS   OBJECT-TYPE
            SYNTAX  INTEGER {
                    disable(1),
                    enable(2)
                }
            ACCESS  read-write
            STATUS  mandatory
            DESCRIPTION
                "HP-STS Threshold Mask Setup."
            ::= { perfTCAMaskTable 4  }

        tcaMaskFarEndHP-STS     OBJECT-TYPE
            SYNTAX  INTEGER {
                    disable(1),
                    enable(2)
                }
            ACCESS  read-write
            STATUS  mandatory
            DESCRIPTION
                "Far End HP-STS Threshold Mask Setup."
            ::= { perfTCAMaskTable 5 }

        tcaMaskLP-VT-V5 OBJECT-TYPE
            SYNTAX  INTEGER {
                    disable(1),
                    enable(2)
                }
            ACCESS  read-write
            STATUS  mandatory
            DESCRIPTION
                "LP-VT(V5) Threshold Mask Setup."
            ::= { perfTCAMaskTable 6 }

        tcaMaskFarEndLP-VT-V5   OBJECT-TYPE
            SYNTAX  INTEGER {
                    disable(1),
                    enable(2)
                }
            ACCESS  read-write
            STATUS  mandatory
            DESCRIPTION
                "Far End LP-VT(V5) Threshold Mask Setup."
            ::= { perfTCAMaskTable 7 }

        tcaMaskLP-VT-B3 OBJECT-TYPE
            SYNTAX  INTEGER {
                    disable(1),
                    enable(2)
                }
            ACCESS  read-write
            STATUS  mandatory
            DESCRIPTION
                "LP-VT(B3) Threshold Mask Setup."
            ::= { perfTCAMaskTable 8 }

        tcaMaskFarEndLP-VT-B3   OBJECT-TYPE
            SYNTAX  INTEGER {
                    disable(1),
                    enable(2)
                }
            ACCESS  read-write
            STATUS  mandatory
            DESCRIPTION
                "Far End LP-VT(B3) Threshold Mask Setup."
            ::= { perfTCAMaskTable 9 }

--
--      performance severity Table
--

    perfTCASeverityTable            OBJECT IDENTIFIER ::= { perfThresholdTable 2 }

        tcaSvrityRS-Section     OBJECT-TYPE
            SYNTAX  Severity
            ACCESS  read-write
            STATUS  mandatory
            DESCRIPTION
                "RS-Section Threshold Severity Setup."
            ::= { perfTCASeverityTable 1  }

        tcaSvrityMS-Line        OBJECT-TYPE
            SYNTAX  Severity
            ACCESS  read-write
            STATUS  mandatory
            DESCRIPTION
                "MS-Line Threshold Severity Setup."
            ::= { perfTCASeverityTable 2  }

        tcaSvrityFarEndMS-Line  OBJECT-TYPE
            SYNTAX  Severity
            ACCESS  read-write
            STATUS  mandatory
            DESCRIPTION
                "Far End MS-Line Threshold Severity Setup."
            ::= { perfTCASeverityTable 3 }

        tcaSvrityHP-STS OBJECT-TYPE
            SYNTAX  Severity
            ACCESS  read-write
            STATUS  mandatory
            DESCRIPTION
                "HP-STS Threshold Severity Setup."
            ::= { perfTCASeverityTable 4  }

        tcaSvrityFarEndHP-STS   OBJECT-TYPE
            SYNTAX  Severity
            ACCESS  read-write
            STATUS  mandatory
            DESCRIPTION
                "Far End HP-STS Threshold Severity Setup."
            ::= { perfTCASeverityTable 5 }

        tcaSvrityLP-VT-V5       OBJECT-TYPE
            SYNTAX  Severity
            ACCESS  read-write
            STATUS  mandatory
            DESCRIPTION
                "LP-VT(V5) Threshold Severity Setup."
            ::= { perfTCASeverityTable 6 }

        stcaSvrityFarEndLP-VT-V5        OBJECT-TYPE
            SYNTAX  Severity
            ACCESS  read-write
            STATUS  mandatory
            DESCRIPTION
                "Far End LP-VT(V5) Threshold Severity Setup."
            ::= { perfTCASeverityTable 7 }

        tcaSvrityLP-VT-B3       OBJECT-TYPE
            SYNTAX  Severity
            ACCESS  read-write
            STATUS  mandatory
            DESCRIPTION
                "LP-VT(B3) Threshold Severity Setup."
            ::= { perfTCASeverityTable 8 }

        tcaSvrityFarEndLP-VT-B3 OBJECT-TYPE
            SYNTAX  Severity
            ACCESS  read-write
            STATUS  mandatory
            DESCRIPTION
                "Far End LP-VT(B3) Threshold Severity Setup."
            ::= { perfTCASeverityTable 9 }

--
--      performance threshold Table
--

    perfTCAThresholdTable           OBJECT IDENTIFIER ::= { perfThresholdTable 3 }

        tcaThreshRS-Section     OBJECT-TYPE
            SYNTAX  INTEGER (1..99999)
            ACCESS  read-write
            STATUS  mandatory
            DESCRIPTION
                "RS-Section Threshold Setup."
            ::= { perfTCAThresholdTable 1  }

        tcaThreshMS-Line        OBJECT-TYPE
            SYNTAX  INTEGER (1..99999)
            ACCESS  read-write
            STATUS  mandatory
            DESCRIPTION
                "MS-Line Threshold Setup."
            ::= { perfTCAThresholdTable 2  }

        tcaThreshFarEndMS-Line  OBJECT-TYPE
            SYNTAX  INTEGER (1..99999)
            ACCESS  read-write
            STATUS  mandatory
            DESCRIPTION
                "Far End MS-Line Threshold Setup."
            ::= { perfTCAThresholdTable 3 }

        tcaThreshHP-STS OBJECT-TYPE
            SYNTAX  INTEGER (1..99999)
            ACCESS  read-write
            STATUS  mandatory
            DESCRIPTION
                "HP-STS Threshold Setup."
            ::= { perfTCAThresholdTable 4  }

        tcaThreshFarEndHP-STS   OBJECT-TYPE
            SYNTAX  INTEGER (1..99999)
            ACCESS  read-write
            STATUS  mandatory
            DESCRIPTION
                "Far End HP-STS Threshold Setup."
            ::= { perfTCAThresholdTable 5 }

        tcaThreshLP-VT-V5       OBJECT-TYPE
            SYNTAX  INTEGER (1..99999)
            ACCESS  read-write
            STATUS  mandatory
            DESCRIPTION
                "LP-VT(V5) Threshold Setup."
            ::= { perfTCAThresholdTable 6 }

        tcaThreshFarEndLP-VT-V5 OBJECT-TYPE
            SYNTAX  INTEGER (1..99999)
            ACCESS  read-write
            STATUS  mandatory
            DESCRIPTION
                "Far End LP-VT(V5) Threshold Setup."
            ::= { perfTCAThresholdTable 7 }

        tcaThreshLP-VT-B3       OBJECT-TYPE
            SYNTAX  INTEGER (1..99999)
            ACCESS  read-write
            STATUS  mandatory
            DESCRIPTION
                "LP-VT(B3) Threshold Setup."
            ::= { perfTCAThresholdTable 8 }

        tcaThreshFarEndLP-VT-B3 OBJECT-TYPE
            SYNTAX  INTEGER (1..99999)
            ACCESS  read-write
            STATUS  mandatory
            DESCRIPTION
                "Far End LP-VT(B3) Threshold Setup."
            ::= { perfTCAThresholdTable 9 }

--
--   Performance Control Table
--
    perfControlTable  OBJECT IDENTIFIER  ::= { system 30 }

        perfControlPerfClear  OBJECT-TYPE
            SYNTAX  INTEGER {
                    no(1),
                    clear(2)
                }
            ACCESS  read-write
            STATUS  mandatory
            DESCRIPTION
                "Clear performance"
            ::= { perfControlTable 1 }

--
--  Performance Display Table
--
    perfDisplayTable  OBJECT IDENTIFIER ::= { system 31 }

--
--  Performance B1 Current Table
--
        cRS-SectionCurrTab  OBJECT-TYPE
            SYNTAX  SEQUENCE OF  CRS-SectionCurrEty
            ACCESS  not-accessible
            STATUS  mandatory
            DESCRIPTION
                "The B1 Current table."
            ::= { perfDisplayTable 1 }

        cRS-SectionCurrEty  OBJECT-TYPE
            SYNTAX  CRS-SectionCurrEty
            ACCESS  not-accessible
            STATUS  mandatory
            DESCRIPTION
                "An entry in the B1 Current table."
            INDEX { rsSecCurrXCUIndex , rsSecCurrPortIndex }
            ::= { cRS-SectionCurrTab 1 }

        CRS-SectionCurrEty ::= SEQUENCE {
            rsSecCurrXCUIndex           XcuNum,
            rsSecCurrPortIndex          PortNum,
            rsSecCurrEBs                Counter,
            rsSecCurrBBEs               Counter,
            rsSecCurrESs                Counter,
            rsSecCurrBESs               Counter,
            rsSecCurrSESs               Counter,
            rsSecCurrUASs               Counter,
            rsSecCurr24HValid15M        Counter,
            rsSecCurr7DayValidDay       Counter,
            rsSecCurr15MTimeElaps       Counter,
            rsSecCurrDayValid15M        Counter
        }

        rsSecCurrXCUIndex  OBJECT-TYPE
            SYNTAX  XcuNum
            ACCESS  read-only
            STATUS  mandatory
            DESCRIPTION
                "XCU index"
            ::= { cRS-SectionCurrEty 1 }

        rsSecCurrPortIndex  OBJECT-TYPE
            SYNTAX  PortNum
            ACCESS  read-only
            STATUS  mandatory
            DESCRIPTION
                "PORT #1~#2"
            ::= { cRS-SectionCurrEty 2 }

        rsSecCurrEBs  OBJECT-TYPE
            SYNTAX  Counter
            ACCESS  read-only
            STATUS  mandatory
            DESCRIPTION
                "B1(BIP-8) Error Block"
            ::= { cRS-SectionCurrEty 3 }

        rsSecCurrBBEs  OBJECT-TYPE
            SYNTAX  Counter
            ACCESS  read-only
            STATUS  mandatory
            DESCRIPTION
                "B1(BIP-8) Background Block Error"
            ::= { cRS-SectionCurrEty 4 }

        rsSecCurrESs  OBJECT-TYPE
            SYNTAX  Counter
            ACCESS  read-only
            STATUS  mandatory
            DESCRIPTION
                "B1(BIP-8) Error Second"
            ::= { cRS-SectionCurrEty 5 }

        rsSecCurrBESs  OBJECT-TYPE
            SYNTAX  Counter
            ACCESS  read-only
            STATUS  mandatory
            DESCRIPTION
                "B1(BIP-8) Background Error Second"
            ::= { cRS-SectionCurrEty 6 }

        rsSecCurrSESs  OBJECT-TYPE
            SYNTAX  Counter
            ACCESS  read-only
            STATUS  mandatory
            DESCRIPTION
                "B1(BIP-8) Severly Error Second"
            ::= { cRS-SectionCurrEty 7 }

        rsSecCurrUASs  OBJECT-TYPE
            SYNTAX  Counter
            ACCESS  read-only
            STATUS  mandatory
            DESCRIPTION
                "B1(BIP-8) Unavailable Second"
            ::= { cRS-SectionCurrEty 8 }

        rsSecCurr24HValid15M  OBJECT-TYPE
            SYNTAX  Counter
            ACCESS  read-only
            STATUS  mandatory
            DESCRIPTION
                "B1(BIP-8) Valid 15-Min Interval"
            ::= { cRS-SectionCurrEty 9 }

        rsSecCurr7DayValidDay  OBJECT-TYPE
            SYNTAX  Counter
            ACCESS  read-only
            STATUS  mandatory
            DESCRIPTION
                "B1(BIP-8) Valid 1-Day Interval"
            ::= { cRS-SectionCurrEty 10 }

        rsSecCurr15MTimeElaps  OBJECT-TYPE
            SYNTAX  Counter
            ACCESS  read-only
            STATUS  mandatory
            DESCRIPTION
                "B1(BIP-8) Current 15-MIN Time Elapsed"
            ::= { cRS-SectionCurrEty 11 }

        rsSecCurrDayValid15M  OBJECT-TYPE
            SYNTAX  Counter
            ACCESS  read-only
            STATUS  mandatory
            DESCRIPTION
                "B1(BIP-8) Current Day Time Elapsed"
            ::= { cRS-SectionCurrEty 12 }

--
--  Performance B1 Interval Table
--
        cRS-SectionIntervTab  OBJECT-TYPE
            SYNTAX  SEQUENCE OF  CRS-SectionIntervEty
            ACCESS  not-accessible
            STATUS  mandatory
            DESCRIPTION
                "The B1 Interval table."
            ::= { perfDisplayTable 2 }

        cRS-SectionIntervEty  OBJECT-TYPE
            SYNTAX  CRS-SectionIntervEty
            ACCESS  not-accessible
            STATUS  mandatory
            DESCRIPTION
                "An entry in the B1 Interval table."
            INDEX { rsSecIntervXCUIndex , rsSecIntervPortIndex ,
                    rsSecIntervNumber }
            ::= { cRS-SectionIntervTab 1 }

        CRS-SectionIntervEty ::= SEQUENCE {
            rsSecIntervXCUIndex         XcuNum,
            rsSecIntervPortIndex        PortNum,
            rsSecIntervNumber           INTEGER (1..96),
            rsSecIntervEBs              Counter,
            rsSecIntervBBEs             Counter,
            rsSecIntervESs              Counter,
            rsSecIntervBESs             Counter,
            rsSecIntervSESs             Counter,
            rsSecIntervUASs             Counter
        }

        rsSecIntervXCUIndex  OBJECT-TYPE
            SYNTAX  XcuNum
            ACCESS  read-only
            STATUS  mandatory
            DESCRIPTION
                "XCU index"
            ::= { cRS-SectionIntervEty 1 }

        rsSecIntervPortIndex  OBJECT-TYPE
            SYNTAX  PortNum
            ACCESS  read-only
            STATUS  mandatory
            DESCRIPTION
                "PORT #1~#2"
            ::= { cRS-SectionIntervEty 2 }

        rsSecIntervNumber  OBJECT-TYPE
            SYNTAX  INTEGER (1..96)
            ACCESS  read-only
            STATUS  mandatory
            DESCRIPTION
                "A number between 1 and 96"
            ::= { cRS-SectionIntervEty 3 }

        rsSecIntervEBs  OBJECT-TYPE
            SYNTAX  Counter
            ACCESS  read-only
            STATUS  mandatory
            DESCRIPTION
                "B1(BIP-8) Error Block"
            ::= { cRS-SectionIntervEty 4 }

        rsSecIntervBBEs  OBJECT-TYPE
            SYNTAX  Counter
            ACCESS  read-only
            STATUS  mandatory
            DESCRIPTION
                "B1(BIP-8) Background Block Error"
            ::= { cRS-SectionIntervEty 5 }

        rsSecIntervESs  OBJECT-TYPE
            SYNTAX  Counter
            ACCESS  read-only
            STATUS  mandatory
            DESCRIPTION
                "B1(BIP-8) Error Second"
            ::= { cRS-SectionIntervEty 6 }

        rsSecIntervBESs  OBJECT-TYPE
            SYNTAX  Counter
            ACCESS  read-only
            STATUS  mandatory
            DESCRIPTION
                "B1(BIP-8) Background Error Second"
            ::= { cRS-SectionIntervEty 7 }

        rsSecIntervSESs  OBJECT-TYPE
            SYNTAX  Counter
            ACCESS  read-only
            STATUS  mandatory
            DESCRIPTION
                "B1(BIP-8) Severly Error Second"
            ::= { cRS-SectionIntervEty 8 }

        rsSecIntervUASs  OBJECT-TYPE
            SYNTAX  Counter
            ACCESS  read-only
            STATUS  mandatory
            DESCRIPTION
                "B1(BIP-8) Unavailable Second"
            ::= { cRS-SectionIntervEty 9 }

--
--  Performance B1 7 Days Table
--
        cRS-Section7DaysTab  OBJECT-TYPE
            SYNTAX  SEQUENCE OF  CRS-Section7DaysEty
            ACCESS  not-accessible
            STATUS  mandatory
            DESCRIPTION
                "The B1 7 days table."
            ::= { perfDisplayTable 3 }

        cRS-Section7DaysEty  OBJECT-TYPE
            SYNTAX  CRS-Section7DaysEty
            ACCESS  not-accessible
            STATUS  mandatory
            DESCRIPTION
                "An entry in the B1 7 days table."
            INDEX { rsSec7DaysXCUIndex , rsSec7DaysPortIndex ,
                    rsSec7DaysNumber }
            ::= { cRS-Section7DaysTab 1 }

        CRS-Section7DaysEty ::= SEQUENCE {
            rsSec7DaysXCUIndex          XcuNum,
            rsSec7DaysPortIndex         PortNum,
            rsSec7DaysNumber            INTEGER (1..7),
            rsSec7DaysDate              DisplayString (SIZE (0..255)),
            rsSec7DaysEBs               Counter,
            rsSec7DaysBBEs              Counter,
            rsSec7DaysESs               Counter,
            rsSec7DaysBESs              Counter,
            rsSec7DaysSESs              Counter,
            rsSec7DaysUASs              Counter
        }

        rsSec7DaysXCUIndex  OBJECT-TYPE
            SYNTAX  XcuNum
            ACCESS  read-only
            STATUS  mandatory
            DESCRIPTION
                "XCU index"
            ::= { cRS-Section7DaysEty 1 }

        rsSec7DaysPortIndex  OBJECT-TYPE
            SYNTAX  PortNum
            ACCESS  read-only
            STATUS  mandatory
            DESCRIPTION
                "PORT #1~#2"
            ::= { cRS-Section7DaysEty 2 }

        rsSec7DaysNumber  OBJECT-TYPE
            SYNTAX  INTEGER (1..7)
            ACCESS  read-only
            STATUS  mandatory
            DESCRIPTION
                "A number between 1 and 7"
            ::= { cRS-Section7DaysEty 3 }

        rsSec7DaysDate  OBJECT-TYPE
            SYNTAX  DisplayString (SIZE (0..255))
            ACCESS  read-only
            STATUS  mandatory
            DESCRIPTION
                "Date"
            ::= { cRS-Section7DaysEty 4 }

        rsSec7DaysEBs  OBJECT-TYPE
            SYNTAX  Counter
            ACCESS  read-only
            STATUS  mandatory
            DESCRIPTION
                "B1(BIP-8) Error Block"
            ::= { cRS-Section7DaysEty 5 }

        rsSec7DaysBBEs  OBJECT-TYPE
            SYNTAX  Counter
            ACCESS  read-only
            STATUS  mandatory
            DESCRIPTION
                "B1(BIP-8) Background Block Error"
            ::= { cRS-Section7DaysEty 6 }

        rsSec7DaysESs  OBJECT-TYPE
            SYNTAX  Counter
            ACCESS  read-only
            STATUS  mandatory
            DESCRIPTION
                "B1(BIP-8) Error Second"
            ::= { cRS-Section7DaysEty 7 }

        rsSec7DaysBESs  OBJECT-TYPE
            SYNTAX  Counter
            ACCESS  read-only
            STATUS  mandatory
            DESCRIPTION
                "B1(BIP-8) Background Error Second"
            ::= { cRS-Section7DaysEty 8 }

        rsSec7DaysSESs  OBJECT-TYPE
            SYNTAX  Counter
            ACCESS  read-only
            STATUS  mandatory
            DESCRIPTION
                "B1(BIP-8) Severly Error Second"
            ::= { cRS-Section7DaysEty 9 }

        rsSec7DaysUASs  OBJECT-TYPE
            SYNTAX  Counter
            ACCESS  read-only
            STATUS  mandatory
            DESCRIPTION
                "B1(BIP-8) Unavailable Second"
            ::= { cRS-Section7DaysEty 10 }

--
--  Performance B1 Total Table
--
        cRS-SectionTotalTab  OBJECT-TYPE
            SYNTAX  SEQUENCE OF  CRS-SectionTotalEty
            ACCESS  not-accessible
            STATUS  mandatory
            DESCRIPTION
                "The B1 Total table."
            ::= { perfDisplayTable 4 }

        cRS-SectionTotalEty  OBJECT-TYPE
            SYNTAX  CRS-SectionTotalEty
            ACCESS  not-accessible
            STATUS  mandatory
            DESCRIPTION
                "An entry in the B1 Total table."
            INDEX { rsSecTotalXCUIndex , rsSecTotalPortIndex }
            ::= { cRS-SectionTotalTab 1 }

        CRS-SectionTotalEty ::= SEQUENCE {
            rsSecTotalXCUIndex          XcuNum,
            rsSecTotalPortIndex         PortNum,
            rsSecTotalEBs               Counter,
            rsSecTotalBBEs              Counter,
            rsSecTotalESs               Counter,
            rsSecTotalBESs              Counter,
            rsSecTotalSESs              Counter,
            rsSecTotalUASs              Counter
        }

        rsSecTotalXCUIndex  OBJECT-TYPE
            SYNTAX  XcuNum
            ACCESS  read-only
            STATUS  mandatory
            DESCRIPTION
                "XCU index"
            ::= { cRS-SectionTotalEty 1 }

        rsSecTotalPortIndex  OBJECT-TYPE
            SYNTAX  PortNum
            ACCESS  read-only
            STATUS  mandatory
            DESCRIPTION
                "PORT #1~#2"
            ::= { cRS-SectionTotalEty 2 }

        rsSecTotalEBs  OBJECT-TYPE
            SYNTAX  Counter
            ACCESS  read-only
            STATUS  mandatory
            DESCRIPTION
                "B1(BIP-8) Error Block"
            ::= { cRS-SectionTotalEty 3 }

        rsSecTotalBBEs  OBJECT-TYPE
            SYNTAX  Counter
            ACCESS  read-only
            STATUS  mandatory
            DESCRIPTION
                "B1(BIP-8) Background Block Error"
            ::= { cRS-SectionTotalEty 4 }

        rsSecTotalESs  OBJECT-TYPE
            SYNTAX  Counter
            ACCESS  read-only
            STATUS  mandatory
            DESCRIPTION
                "B1(BIP-8) Error Second"
            ::= { cRS-SectionTotalEty 5 }

        rsSecTotalBESs  OBJECT-TYPE
            SYNTAX  Counter
            ACCESS  read-only
            STATUS  mandatory
            DESCRIPTION
                "B1(BIP-8) Background Error Second"
            ::= { cRS-SectionTotalEty 6 }

        rsSecTotalSESs  OBJECT-TYPE
            SYNTAX  Counter
            ACCESS  read-only
            STATUS  mandatory
            DESCRIPTION
                "B1(BIP-8) Severly Error Second"
            ::= { cRS-SectionTotalEty 7 }

        rsSecTotalUASs  OBJECT-TYPE
            SYNTAX  Counter
            ACCESS  read-only
            STATUS  mandatory
            DESCRIPTION
                "B1(BIP-8) Unavailable Second"
            ::= { cRS-SectionTotalEty 8 }

--
--  Performance B2 Current Table
--
        cMS-LineCurrTab  OBJECT-TYPE
            SYNTAX  SEQUENCE OF  CMS-LineCurrEty
            ACCESS  not-accessible
            STATUS  mandatory
            DESCRIPTION
                "The B2 Current table."
            ::= { perfDisplayTable 5 }

        cMS-LineCurrEty  OBJECT-TYPE
            SYNTAX  CMS-LineCurrEty
            ACCESS  not-accessible
            STATUS  mandatory
            DESCRIPTION
                "An entry in the B2 Current table."
            INDEX { msLineCurrXCUIndex , msLineCurrPortIndex }
            ::= { cMS-LineCurrTab 1 }

        CMS-LineCurrEty ::= SEQUENCE {
            msLineCurrXCUIndex          XcuNum,
            msLineCurrPortIndex         PortNum,
            msLineCurrEBs               Counter,
            msLineCurrBBEs              Counter,
            msLineCurrESs               Counter,
            msLineCurrBESs              Counter,
            msLineCurrSESs              Counter,
            msLineCurrUASs              Counter,
            msLineCurr24HValid15M       Counter,
            msLineCurr7DayValidDay      Counter,
            msLineCurr15MTimeElaps      Counter,
            msLineCurrDayValid15M       Counter
        }

        msLineCurrXCUIndex  OBJECT-TYPE
            SYNTAX  XcuNum
            ACCESS  read-only
            STATUS  mandatory
            DESCRIPTION
                "XCU index"
            ::= { cMS-LineCurrEty 1 }

        msLineCurrPortIndex  OBJECT-TYPE
            SYNTAX  PortNum
            ACCESS  read-only
            STATUS  mandatory
            DESCRIPTION
                "PORT #1~#2"
            ::= { cMS-LineCurrEty 2 }

        msLineCurrEBs  OBJECT-TYPE
            SYNTAX  Counter
            ACCESS  read-only
            STATUS  mandatory
            DESCRIPTION
                "B2(BIP-8) Error Block"
            ::= { cMS-LineCurrEty 3 }

        msLineCurrBBEs  OBJECT-TYPE
            SYNTAX  Counter
            ACCESS  read-only
            STATUS  mandatory
            DESCRIPTION
                "B2(BIP-8) Background Block Error"
            ::= { cMS-LineCurrEty 4 }

        msLineCurrESs  OBJECT-TYPE
            SYNTAX  Counter
            ACCESS  read-only
            STATUS  mandatory
            DESCRIPTION
                "B2(BIP-8) Error Second"
            ::= { cMS-LineCurrEty 5 }

        msLineCurrBESs  OBJECT-TYPE
            SYNTAX  Counter
            ACCESS  read-only
            STATUS  mandatory
            DESCRIPTION
                "B2(BIP-8) Background Error Second"
            ::= { cMS-LineCurrEty 6 }

        msLineCurrSESs  OBJECT-TYPE
            SYNTAX  Counter
            ACCESS  read-only
            STATUS  mandatory
            DESCRIPTION
                "B2(BIP-8) Severly Error Second"
            ::= { cMS-LineCurrEty 7 }

        msLineCurrUASs  OBJECT-TYPE
            SYNTAX  Counter
            ACCESS  read-only
            STATUS  mandatory
            DESCRIPTION
                "B2(BIP-8) Unavailable Second"
            ::= { cMS-LineCurrEty 8 }

        msLineCurr24HValid15M  OBJECT-TYPE
            SYNTAX  Counter
            ACCESS  read-only
            STATUS  mandatory
            DESCRIPTION
                "B1(BIP-8) Valid 15-Min Interval"
            ::= { cMS-LineCurrEty 9 }

        msLineCurr7DayValidDay  OBJECT-TYPE
            SYNTAX  Counter
            ACCESS  read-only
            STATUS  mandatory
            DESCRIPTION
                "B1(BIP-8) Valid 1-Day Interval"
            ::= { cMS-LineCurrEty 10 }

        msLineCurr15MTimeElaps  OBJECT-TYPE
            SYNTAX  Counter
            ACCESS  read-only
            STATUS  mandatory
            DESCRIPTION
                "B1(BIP-8) Current 15-MIN Time Elapsed"
            ::= { cMS-LineCurrEty 11 }

        msLineCurrDayValid15M  OBJECT-TYPE
            SYNTAX  Counter
            ACCESS  read-only
            STATUS  mandatory
            DESCRIPTION
                "B1(BIP-8) Current Day Time Elapsed"
            ::= { cMS-LineCurrEty 12 }

--
--  Performance B2 Interval Table
--
        cMS-LineIntervTab  OBJECT-TYPE
            SYNTAX  SEQUENCE OF  CMS-LineIntervEty
            ACCESS  not-accessible
            STATUS  mandatory
            DESCRIPTION
                "The B2 Interval table."
            ::= { perfDisplayTable 6 }

        cMS-LineIntervEty  OBJECT-TYPE
            SYNTAX  CMS-LineIntervEty
            ACCESS  not-accessible
            STATUS  mandatory
            DESCRIPTION
                "An entry in the B2 Interval table."
            INDEX { msLineIntervXCUIndex , msLineIntervPortIndex ,
                    msLineIntervNumber }
            ::= { cMS-LineIntervTab 1 }

        CMS-LineIntervEty ::= SEQUENCE {
            msLineIntervXCUIndex        XcuNum,
            msLineIntervPortIndex       PortNum,
            msLineIntervNumber          INTEGER (1..96),
            msLineIntervEBs             Counter,
            msLineIntervBBEs            Counter,
            msLineIntervESs             Counter,
            msLineIntervBESs            Counter,
            msLineIntervSESs            Counter,
            msLineIntervUASs            Counter
        }

        msLineIntervXCUIndex  OBJECT-TYPE
            SYNTAX  XcuNum
            ACCESS  read-only
            STATUS  mandatory
            DESCRIPTION
                "XCU index"
            ::= { cMS-LineIntervEty 1 }

        msLineIntervPortIndex  OBJECT-TYPE
            SYNTAX  PortNum
            ACCESS  read-only
            STATUS  mandatory
            DESCRIPTION
                "PORT #1~#2"
            ::= { cMS-LineIntervEty 2 }

        msLineIntervNumber  OBJECT-TYPE
            SYNTAX  INTEGER (1..96)
            ACCESS  read-only
            STATUS  mandatory
            DESCRIPTION
                "A number between 1 and 96"
            ::= { cMS-LineIntervEty 3 }

        msLineIntervEBs  OBJECT-TYPE
            SYNTAX  Counter
            ACCESS  read-only
            STATUS  mandatory
            DESCRIPTION
                "B2(BIP-8) Error Block"
            ::= { cMS-LineIntervEty 4 }

        msLineIntervBBEs  OBJECT-TYPE
            SYNTAX  Counter
            ACCESS  read-only
            STATUS  mandatory
            DESCRIPTION
                "B2(BIP-8) Background Block Error"
            ::= { cMS-LineIntervEty 5 }

        msLineIntervESs  OBJECT-TYPE
            SYNTAX  Counter
            ACCESS  read-only
            STATUS  mandatory
            DESCRIPTION
                "B2(BIP-8) Error Second"
            ::= { cMS-LineIntervEty 6 }

        msLineIntervBESs  OBJECT-TYPE
            SYNTAX  Counter
            ACCESS  read-only
            STATUS  mandatory
            DESCRIPTION
                "B2(BIP-8) Background Error Second"
            ::= { cMS-LineIntervEty 7 }

        msLineIntervSESs  OBJECT-TYPE
            SYNTAX  Counter
            ACCESS  read-only
            STATUS  mandatory
            DESCRIPTION
                "B2(BIP-8) Severly Error Second"
            ::= { cMS-LineIntervEty 8 }

        msLineIntervUASs  OBJECT-TYPE
            SYNTAX  Counter
            ACCESS  read-only
            STATUS  mandatory
            DESCRIPTION
                "B2(BIP-8) Unavailable Second"
            ::= { cMS-LineIntervEty 9 }

--
--  Performance B2 7 Days Table
--
        cMS-Line7DaysTab  OBJECT-TYPE
            SYNTAX  SEQUENCE OF  CMS-Line7DaysEty
            ACCESS  not-accessible
            STATUS  mandatory
            DESCRIPTION
                "The B2 7 days table."
            ::= { perfDisplayTable 7 }

        cMS-Line7DaysEty  OBJECT-TYPE
            SYNTAX  CMS-Line7DaysEty
            ACCESS  not-accessible
            STATUS  mandatory
            DESCRIPTION
                "An entry in the B2 7 days table."
            INDEX { msLine7DaysXCUIndex , msLine7DaysPortIndex ,
                    msLine7DaysNumber }
            ::= { cMS-Line7DaysTab 1 }

        CMS-Line7DaysEty ::= SEQUENCE {
            msLine7DaysXCUIndex         XcuNum,
            msLine7DaysPortIndex        PortNum,
            msLine7DaysNumber           INTEGER (1..7),
            msLine7DaysDate             DisplayString (SIZE (0..255)),
            msLine7DaysEBs              Counter,
            msLine7DaysBBEs             Counter,
            msLine7DaysESs              Counter,
            msLine7DaysBESs             Counter,
            msLine7DaysSESs             Counter,
            msLine7DaysUASs             Counter
        }

        msLine7DaysXCUIndex  OBJECT-TYPE
            SYNTAX  XcuNum
            ACCESS  read-only
            STATUS  mandatory
            DESCRIPTION
                "XCU index"
            ::= { cMS-Line7DaysEty 1 }

        msLine7DaysPortIndex  OBJECT-TYPE
            SYNTAX  PortNum
            ACCESS  read-only
            STATUS  mandatory
            DESCRIPTION
                "PORT #1~#2"
            ::= { cMS-Line7DaysEty 2 }

        msLine7DaysNumber  OBJECT-TYPE
            SYNTAX  INTEGER (1..7)
            ACCESS  read-only
            STATUS  mandatory
            DESCRIPTION
                "A number between 1 and 7"
            ::= { cMS-Line7DaysEty 3 }

        msLine7DaysDate  OBJECT-TYPE
            SYNTAX  DisplayString (SIZE (0..255))
            ACCESS  read-only
            STATUS  mandatory
            DESCRIPTION
                "Date"
            ::= { cMS-Line7DaysEty 4 }

        msLine7DaysEBs  OBJECT-TYPE
            SYNTAX  Counter
            ACCESS  read-only
            STATUS  mandatory
            DESCRIPTION
                "B2(BIP-8) Error Block"
            ::= { cMS-Line7DaysEty 5 }

        msLine7DaysBBEs  OBJECT-TYPE
            SYNTAX  Counter
            ACCESS  read-only
            STATUS  mandatory
            DESCRIPTION
                "B2(BIP-8) Background Block Error"
            ::= { cMS-Line7DaysEty 6 }

        msLine7DaysESs  OBJECT-TYPE
            SYNTAX  Counter
            ACCESS  read-only
            STATUS  mandatory
            DESCRIPTION
                "B2(BIP-8) Error Second"
            ::= { cMS-Line7DaysEty 7 }

        msLine7DaysBESs  OBJECT-TYPE
            SYNTAX  Counter
            ACCESS  read-only
            STATUS  mandatory
            DESCRIPTION
                "B2(BIP-8) Background Error Second"
            ::= { cMS-Line7DaysEty 8 }

        msLine7DaysSESs  OBJECT-TYPE
            SYNTAX  Counter
            ACCESS  read-only
            STATUS  mandatory
            DESCRIPTION
                "B2(BIP-8) Severly Error Second"
            ::= { cMS-Line7DaysEty 9 }

        msLine7DaysUASs  OBJECT-TYPE
            SYNTAX  Counter
            ACCESS  read-only
            STATUS  mandatory
            DESCRIPTION
                "B2(BIP-8) Unavailable Second"
            ::= { cMS-Line7DaysEty 10 }

--
--  Performance B2 Total Table
--
        cMS-LineTotalTab  OBJECT-TYPE
            SYNTAX  SEQUENCE OF  CMS-LineTotalEty
            ACCESS  not-accessible
            STATUS  mandatory
            DESCRIPTION
                "The B2 Total table."
            ::= { perfDisplayTable 8 }

        cMS-LineTotalEty  OBJECT-TYPE
            SYNTAX  CMS-LineTotalEty
            ACCESS  not-accessible
            STATUS  mandatory
            DESCRIPTION
                "An entry in the B2 Total table."
            INDEX { msLineTotalXCUIndex , msLineTotalPortIndex }
            ::= { cMS-LineTotalTab 1 }

        CMS-LineTotalEty ::= SEQUENCE {
            msLineTotalXCUIndex         XcuNum,
            msLineTotalPortIndex        PortNum,
            msLineTotalEBs              Counter,
            msLineTotalBBEs             Counter,
            msLineTotalESs              Counter,
            msLineTotalBESs             Counter,
            msLineTotalSESs             Counter,
            msLineTotalUASs             Counter
        }

        msLineTotalXCUIndex  OBJECT-TYPE
            SYNTAX  XcuNum
            ACCESS  read-only
            STATUS  mandatory
            DESCRIPTION
                "XCU index"
            ::= { cMS-LineTotalEty 1 }

        msLineTotalPortIndex  OBJECT-TYPE
            SYNTAX  PortNum
            ACCESS  read-only
            STATUS  mandatory
            DESCRIPTION
                "PORT #1~#2"
            ::= { cMS-LineTotalEty 2 }

        msLineTotalEBs  OBJECT-TYPE
            SYNTAX  Counter
            ACCESS  read-only
            STATUS  mandatory
            DESCRIPTION
                "B2(BIP-8) Error Block"
            ::= { cMS-LineTotalEty 3 }

        msLineTotalBBEs  OBJECT-TYPE
            SYNTAX  Counter
            ACCESS  read-only
            STATUS  mandatory
            DESCRIPTION
                "B2(BIP-8) Background Block Error"
            ::= { cMS-LineTotalEty 4 }

        msLineTotalESs  OBJECT-TYPE
            SYNTAX  Counter
            ACCESS  read-only
            STATUS  mandatory
            DESCRIPTION
                "B2(BIP-8) Error Second"
            ::= { cMS-LineTotalEty 5 }

        msLineTotalBESs  OBJECT-TYPE
            SYNTAX  Counter
            ACCESS  read-only
            STATUS  mandatory
            DESCRIPTION
                "B2(BIP-8) Background Error Second"
            ::= { cMS-LineTotalEty 6 }

        msLineTotalSESs  OBJECT-TYPE
            SYNTAX  Counter
            ACCESS  read-only
            STATUS  mandatory
            DESCRIPTION
                "B2(BIP-8) Severly Error Second"
            ::= { cMS-LineTotalEty 7 }

        msLineTotalUASs  OBJECT-TYPE
            SYNTAX  Counter
            ACCESS  read-only
            STATUS  mandatory
            DESCRIPTION
                "B2(BIP-8) Unavailable Second"
            ::= { cMS-LineTotalEty 8 }

--
--  Performance MS-REI/REI-L Current Table
--
        cFarEndMS-LineCurrTab  OBJECT-TYPE
            SYNTAX  SEQUENCE OF  CFarEndMS-LineCurrEty
            ACCESS  not-accessible
            STATUS  mandatory
            DESCRIPTION
                "The MS-REI/REI-L Current table."
            ::= { perfDisplayTable 9 }

        cFarEndMS-LineCurrEty  OBJECT-TYPE
            SYNTAX  CFarEndMS-LineCurrEty
            ACCESS  not-accessible
            STATUS  mandatory
            DESCRIPTION
                "An entry in the MS-REI/REI-L Current table."
            INDEX { frMsLineCurrXCUIndex , frMsLineCurrPortIndex }
            ::= { cFarEndMS-LineCurrTab 1 }

        CFarEndMS-LineCurrEty ::= SEQUENCE {
            frMsLineCurrXCUIndex        XcuNum,
            frMsLineCurrPortIndex       PortNum,
            frMsLineCurrEBs             Counter,
            frMsLineCurrBBEs            Counter,
            frMsLineCurrESs             Counter,
            frMsLineCurrBESs            Counter,
            frMsLineCurrSESs            Counter,
            frMsLineCurrUASs            Counter,
            frMsLineCurr24HValid15M     Counter,
            frMsLineCurr7DayValidDay    Counter,
            frMsLineCurr15MTimeElaps    Counter,
            frMsLineCurrDayValid15M     Counter
        }

        frMsLineCurrXCUIndex  OBJECT-TYPE
            SYNTAX  XcuNum
            ACCESS  read-only
            STATUS  mandatory
            DESCRIPTION
                "XCU index"
            ::= { cFarEndMS-LineCurrEty 1 }

        frMsLineCurrPortIndex  OBJECT-TYPE
            SYNTAX  PortNum
            ACCESS  read-only
            STATUS  mandatory
            DESCRIPTION
                "PORT #1~#2"
            ::= { cFarEndMS-LineCurrEty 2 }

        frMsLineCurrEBs  OBJECT-TYPE
            SYNTAX  Counter
            ACCESS  read-only
            STATUS  mandatory
            DESCRIPTION
                "MS-REI/REI-L Error Block"
            ::= { cFarEndMS-LineCurrEty 3 }

        frMsLineCurrBBEs  OBJECT-TYPE
            SYNTAX  Counter
            ACCESS  read-only
            STATUS  mandatory
            DESCRIPTION
                "MS-REI/REI-L Background Block Error"
            ::= { cFarEndMS-LineCurrEty 4 }

        frMsLineCurrESs  OBJECT-TYPE
            SYNTAX  Counter
            ACCESS  read-only
            STATUS  mandatory
            DESCRIPTION
                "MS-REI/REI-L Error Second"
            ::= { cFarEndMS-LineCurrEty 5 }

        frMsLineCurrBESs  OBJECT-TYPE
            SYNTAX  Counter
            ACCESS  read-only
            STATUS  mandatory
            DESCRIPTION
                "MS-REI/REI-L Background Error Second"
            ::= { cFarEndMS-LineCurrEty 6 }

        frMsLineCurrSESs  OBJECT-TYPE
            SYNTAX  Counter
            ACCESS  read-only
            STATUS  mandatory
            DESCRIPTION
                "MS-REI/REI-L Severly Error Second"
            ::= { cFarEndMS-LineCurrEty 7 }

        frMsLineCurrUASs  OBJECT-TYPE
            SYNTAX  Counter
            ACCESS  read-only
            STATUS  mandatory
            DESCRIPTION
                "MS-REI/REI-L Unavailable Second"
            ::= { cFarEndMS-LineCurrEty 8 }

        frMsLineCurr24HValid15M  OBJECT-TYPE
            SYNTAX  Counter
            ACCESS  read-only
            STATUS  mandatory
            DESCRIPTION
                "B1(BIP-8) Valid 15-Min Interval"
            ::= { cFarEndMS-LineCurrEty 9 }

        frMsLineCurr7DayValidDay  OBJECT-TYPE
            SYNTAX  Counter
            ACCESS  read-only
            STATUS  mandatory
            DESCRIPTION
                "B1(BIP-8) Valid 1-Day Interval"
            ::= { cFarEndMS-LineCurrEty 10 }

        frMsLineCurr15MTimeElaps  OBJECT-TYPE
            SYNTAX  Counter
            ACCESS  read-only
            STATUS  mandatory
            DESCRIPTION
                "B1(BIP-8) Current 15-MIN Time Elapsed"
            ::= { cFarEndMS-LineCurrEty 11 }

        frMsLineCurrDayValid15M  OBJECT-TYPE
            SYNTAX  Counter
            ACCESS  read-only
            STATUS  mandatory
            DESCRIPTION
                "B1(BIP-8) Current Day Time Elapsed"
            ::= { cFarEndMS-LineCurrEty 12 }

--
--  Performance MS-REI/REI-L Interval Table
--
        cFarEndMS-LineIntervTab  OBJECT-TYPE
            SYNTAX  SEQUENCE OF  CFarEndMS-LineIntervEty
            ACCESS  not-accessible
            STATUS  mandatory
            DESCRIPTION
                "The MS-REI/REI-L Interval table."
            ::= { perfDisplayTable 10 }

        cFarEndMS-LineIntervEty  OBJECT-TYPE
            SYNTAX  CFarEndMS-LineIntervEty
            ACCESS  not-accessible
            STATUS  mandatory
            DESCRIPTION
                "An entry in the MS-REI/REI-L Interval table."
            INDEX { frMsLineIntervXCUIndex , frMsLineIntervPortIndex ,
                    frMsLineIntervNumber }
            ::= { cFarEndMS-LineIntervTab 1 }

        CFarEndMS-LineIntervEty ::= SEQUENCE {
            frMsLineIntervXCUIndex      XcuNum,
            frMsLineIntervPortIndex     PortNum,
            frMsLineIntervNumber        INTEGER (1..96),
            frMsLineIntervEBs           Counter,
            frMsLineIntervBBEs          Counter,
            frMsLineIntervESs           Counter,
            frMsLineIntervBESs          Counter,
            frMsLineIntervSESs          Counter,
            frMsLineIntervUASs          Counter
        }

        frMsLineIntervXCUIndex  OBJECT-TYPE
            SYNTAX  XcuNum
            ACCESS  read-only
            STATUS  mandatory
            DESCRIPTION
                "XCU index"
            ::= { cFarEndMS-LineIntervEty 1 }

        frMsLineIntervPortIndex  OBJECT-TYPE
            SYNTAX  PortNum
            ACCESS  read-only
            STATUS  mandatory
            DESCRIPTION
                "PORT #1~#2"
            ::= { cFarEndMS-LineIntervEty 2 }

        frMsLineIntervNumber  OBJECT-TYPE
            SYNTAX  INTEGER (1..96)
            ACCESS  read-only
            STATUS  mandatory
            DESCRIPTION
                "A number between 1 and 96"
            ::= { cFarEndMS-LineIntervEty 3 }

        frMsLineIntervEBs  OBJECT-TYPE
            SYNTAX  Counter
            ACCESS  read-only
            STATUS  mandatory
            DESCRIPTION
                "MS-REI/REI-L Error Block"
            ::= { cFarEndMS-LineIntervEty 4 }

        frMsLineIntervBBEs  OBJECT-TYPE
            SYNTAX  Counter
            ACCESS  read-only
            STATUS  mandatory
            DESCRIPTION
                "MS-REI/REI-L Background Block Error"
            ::= { cFarEndMS-LineIntervEty 5 }

        frMsLineIntervESs  OBJECT-TYPE
            SYNTAX  Counter
            ACCESS  read-only
            STATUS  mandatory
            DESCRIPTION
                "MS-REI/REI-L Error Second"
            ::= { cFarEndMS-LineIntervEty 6 }

        frMsLineIntervBESs  OBJECT-TYPE
            SYNTAX  Counter
            ACCESS  read-only
            STATUS  mandatory
            DESCRIPTION
                "MS-REI/REI-L Background Error Second"
            ::= { cFarEndMS-LineIntervEty 7 }

        frMsLineIntervSESs  OBJECT-TYPE
            SYNTAX  Counter
            ACCESS  read-only
            STATUS  mandatory
            DESCRIPTION
                "MS-REI/REI-L Severly Error Second"
            ::= { cFarEndMS-LineIntervEty 8 }

        frMsLineIntervUASs  OBJECT-TYPE
            SYNTAX  Counter
            ACCESS  read-only
            STATUS  mandatory
            DESCRIPTION
                "MS-REI/REI-L Unavailable Second"
            ::= { cFarEndMS-LineIntervEty 9 }

--
--  Performance MS-REI/REI-L 7 Days Table
--
        cFarEndMS-Line7DaysTab  OBJECT-TYPE
            SYNTAX  SEQUENCE OF  CFarEndMS-Line7DaysEty
            ACCESS  not-accessible
            STATUS  mandatory
            DESCRIPTION
                "The MS-REI/REI-L 7 days table."
            ::= { perfDisplayTable 11 }

        cFarEndMS-Line7DaysEty  OBJECT-TYPE
            SYNTAX  CFarEndMS-Line7DaysEty
            ACCESS  not-accessible
            STATUS  mandatory
            DESCRIPTION
                "An entry in the MS-REI/REI-L 7 days table."
            INDEX { frMsLine7DaysXCUIndex , frMsLine7DaysPortIndex ,
                    frMsLine7DaysNumber }
            ::= { cFarEndMS-Line7DaysTab 1 }

        CFarEndMS-Line7DaysEty ::= SEQUENCE {
            frMsLine7DaysXCUIndex       XcuNum,
            frMsLine7DaysPortIndex      PortNum,
            frMsLine7DaysNumber         INTEGER (1..7),
            frMsLine7DaysDate           DisplayString (SIZE (0..255)),
            frMsLine7DaysEBs            Counter,
            frMsLine7DaysBBEs           Counter,
            frMsLine7DaysESs            Counter,
            frMsLine7DaysBESs           Counter,
            frMsLine7DaysSESs           Counter,
            frMsLine7DaysUASs           Counter
        }

        frMsLine7DaysXCUIndex  OBJECT-TYPE
            SYNTAX  XcuNum
            ACCESS  read-only
            STATUS  mandatory
            DESCRIPTION
                "XCU index"
            ::= { cFarEndMS-Line7DaysEty 1 }

        frMsLine7DaysPortIndex  OBJECT-TYPE
            SYNTAX  PortNum
            ACCESS  read-only
            STATUS  mandatory
            DESCRIPTION
                "PORT #1~#2"
            ::= { cFarEndMS-Line7DaysEty 2 }

        frMsLine7DaysNumber  OBJECT-TYPE
            SYNTAX  INTEGER (1..7)
            ACCESS  read-only
            STATUS  mandatory
            DESCRIPTION
                "A number between 1 and 7"
            ::= { cFarEndMS-Line7DaysEty 3 }

        frMsLine7DaysDate  OBJECT-TYPE
            SYNTAX  DisplayString (SIZE (0..255))
            ACCESS  read-only
            STATUS  mandatory
            DESCRIPTION
                "Date"
            ::= { cFarEndMS-Line7DaysEty 4 }

        frMsLine7DaysEBs  OBJECT-TYPE
            SYNTAX  Counter
            ACCESS  read-only
            STATUS  mandatory
            DESCRIPTION
                "MS-REI/REI-L Error Block"
            ::= { cFarEndMS-Line7DaysEty 5 }

        frMsLine7DaysBBEs  OBJECT-TYPE
            SYNTAX  Counter
            ACCESS  read-only
            STATUS  mandatory
            DESCRIPTION
                "MS-REI/REI-L Background Block Error"
            ::= { cFarEndMS-Line7DaysEty 6 }

        frMsLine7DaysESs  OBJECT-TYPE
            SYNTAX  Counter
            ACCESS  read-only
            STATUS  mandatory
            DESCRIPTION
                "MS-REI/REI-L Error Second"
            ::= { cFarEndMS-Line7DaysEty 7 }

        frMsLine7DaysBESs  OBJECT-TYPE
            SYNTAX  Counter
            ACCESS  read-only
            STATUS  mandatory
            DESCRIPTION
                "MS-REI/REI-L Background Error Second"
            ::= { cFarEndMS-Line7DaysEty 8 }

        frMsLine7DaysSESs  OBJECT-TYPE
            SYNTAX  Counter
            ACCESS  read-only
            STATUS  mandatory
            DESCRIPTION
                "MS-REI/REI-L Severly Error Second"
            ::= { cFarEndMS-Line7DaysEty 9 }

        frMsLine7DaysUASs  OBJECT-TYPE
            SYNTAX  Counter
            ACCESS  read-only
            STATUS  mandatory
            DESCRIPTION
                "MS-REI/REI-L Unavailable Second"
            ::= { cFarEndMS-Line7DaysEty 10 }

--
--  Performance MS-REI/REI-L Total Table
--
        cFarEndMS-LineTotalTab  OBJECT-TYPE
            SYNTAX  SEQUENCE OF  CFarEndMS-LineTotalEty
            ACCESS  not-accessible
            STATUS  mandatory
            DESCRIPTION
                "The MS-REI/REI-L Total table."
            ::= { perfDisplayTable 12 }

        cFarEndMS-LineTotalEty  OBJECT-TYPE
            SYNTAX  CFarEndMS-LineTotalEty
            ACCESS  not-accessible
            STATUS  mandatory
            DESCRIPTION
                "An entry in the MS-REI/REI-L Total table."
            INDEX { frMsLineTotalXCUIndex , frMsLineTotalPortIndex }
            ::= { cFarEndMS-LineTotalTab 1 }

        CFarEndMS-LineTotalEty ::= SEQUENCE {
            frMsLineTotalXCUIndex       XcuNum,
            frMsLineTotalPortIndex      PortNum,
            frMsLineTotalEBs            Counter,
            frMsLineTotalBBEs           Counter,
            frMsLineTotalESs            Counter,
            frMsLineTotalBESs           Counter,
            frMsLineTotalSESs           Counter,
            frMsLineTotalUASs           Counter
        }

        frMsLineTotalXCUIndex  OBJECT-TYPE
            SYNTAX  XcuNum
            ACCESS  read-only
            STATUS  mandatory
            DESCRIPTION
                "XCU index"
            ::= { cFarEndMS-LineTotalEty 1 }

        frMsLineTotalPortIndex  OBJECT-TYPE
            SYNTAX  PortNum
            ACCESS  read-only
            STATUS  mandatory
            DESCRIPTION
                "PORT #1~#2"
            ::= { cFarEndMS-LineTotalEty 2 }

        frMsLineTotalEBs  OBJECT-TYPE
            SYNTAX  Counter
            ACCESS  read-only
            STATUS  mandatory
            DESCRIPTION
                "MS-REI/REI-L Error Block"
            ::= { cFarEndMS-LineTotalEty 3 }

        frMsLineTotalBBEs  OBJECT-TYPE
            SYNTAX  Counter
            ACCESS  read-only
            STATUS  mandatory
            DESCRIPTION
                "MS-REI/REI-L Background Block Error"
            ::= { cFarEndMS-LineTotalEty 4 }

        frMsLineTotalESs  OBJECT-TYPE
            SYNTAX  Counter
            ACCESS  read-only
            STATUS  mandatory
            DESCRIPTION
                "MS-REI/REI-L Error Second"
            ::= { cFarEndMS-LineTotalEty 5 }

        frMsLineTotalBESs  OBJECT-TYPE
            SYNTAX  Counter
            ACCESS  read-only
            STATUS  mandatory
            DESCRIPTION
                "MS-REI/REI-L Background Error Second"
            ::= { cFarEndMS-LineTotalEty 6 }

        frMsLineTotalSESs  OBJECT-TYPE
            SYNTAX  Counter
            ACCESS  read-only
            STATUS  mandatory
            DESCRIPTION
                "MS-REI/REI-L Severly Error Second"
            ::= { cFarEndMS-LineTotalEty 7 }

        frMsLineTotalUASs  OBJECT-TYPE
            SYNTAX  Counter
            ACCESS  read-only
            STATUS  mandatory
            DESCRIPTION
                "MS-REI/REI-L Unavailable Second"
            ::= { cFarEndMS-LineTotalEty 8 }

--
--  Performance B3 Current Table
--
        cHP-STSCurrTab  OBJECT-TYPE
            SYNTAX  SEQUENCE OF  CHP-STSCurrEty
            ACCESS  not-accessible
            STATUS  mandatory
            DESCRIPTION
                "The B3 Current table."
            ::= { perfDisplayTable 13 }

        cHP-STSCurrEty  OBJECT-TYPE
            SYNTAX  CHP-STSCurrEty
            ACCESS  not-accessible
            STATUS  mandatory
            DESCRIPTION
                "An entry in the B3 Current table."
            INDEX { hpStsCurrXCUIndex , hpStsCurrPortIndex ,
                    hpStsCurrAug1Sts3Index , hpStsCurrVc3Sts1Index }
            ::= { cHP-STSCurrTab 1 }

        CHP-STSCurrEty ::= SEQUENCE {
            hpStsCurrXCUIndex           XcuNum,
            hpStsCurrPortIndex          PortNum,
            hpStsCurrAug1Sts3Index      Aug1Sts3Num,
            hpStsCurrVc3Sts1Index       Vc3Sts1Num,
            hpStsCurrEBs                Counter,
            hpStsCurrBBEs               Counter,
            hpStsCurrESs                Counter,
            hpStsCurrBESs               Counter,
            hpStsCurrSESs               Counter,
            hpStsCurrUASs               Counter,
            hpStsCurr24HValid15M        Counter,
            hpStsCurr7DayValidDay       Counter,
            hpStsCurr15MTimeElaps       Counter,
            hpStsCurrDayValid15M        Counter
        }

        hpStsCurrXCUIndex  OBJECT-TYPE
            SYNTAX  XcuNum
            ACCESS  read-only
            STATUS  mandatory
            DESCRIPTION
                "XCU index"
            ::= { cHP-STSCurrEty 1 }

        hpStsCurrPortIndex  OBJECT-TYPE
            SYNTAX  PortNum
            ACCESS  read-only
            STATUS  mandatory
            DESCRIPTION
                "PORT #1~#2"
            ::= { cHP-STSCurrEty 2 }

        hpStsCurrAug1Sts3Index  OBJECT-TYPE
            SYNTAX  Aug1Sts3Num
            ACCESS  read-only
            STATUS  mandatory
            DESCRIPTION
                "AUG1/STS3 index"
            ::= { cHP-STSCurrEty 3 }

        hpStsCurrVc3Sts1Index  OBJECT-TYPE
            SYNTAX  Vc3Sts1Num
            ACCESS  read-only
            STATUS  mandatory
            DESCRIPTION
                "VC3/STS1 index"
            ::= { cHP-STSCurrEty 4 }

        hpStsCurrEBs  OBJECT-TYPE
            SYNTAX  Counter
            ACCESS  read-only
            STATUS  mandatory
            DESCRIPTION
                "B3(BIP-8) Error Block"
            ::= { cHP-STSCurrEty 5 }

        hpStsCurrBBEs  OBJECT-TYPE
            SYNTAX  Counter
            ACCESS  read-only
            STATUS  mandatory
            DESCRIPTION
                "B3(BIP-8) Background Block Error"
            ::= { cHP-STSCurrEty 6 }

        hpStsCurrESs  OBJECT-TYPE
            SYNTAX  Counter
            ACCESS  read-only
            STATUS  mandatory
            DESCRIPTION
                "B3(BIP-8) Error Second"
            ::= { cHP-STSCurrEty 7 }

        hpStsCurrBESs  OBJECT-TYPE
            SYNTAX  Counter
            ACCESS  read-only
            STATUS  mandatory
            DESCRIPTION
                "B3(BIP-8) Background Error Second"
            ::= { cHP-STSCurrEty 8 }

        hpStsCurrSESs  OBJECT-TYPE
            SYNTAX  Counter
            ACCESS  read-only
            STATUS  mandatory
            DESCRIPTION
                "B3(BIP-8) Severly Error Second"
            ::= { cHP-STSCurrEty 9 }

        hpStsCurrUASs  OBJECT-TYPE
            SYNTAX  Counter
            ACCESS  read-only
            STATUS  mandatory
            DESCRIPTION
                "B3(BIP-8) Unavailable Second"
            ::= { cHP-STSCurrEty 10 }

        hpStsCurr24HValid15M  OBJECT-TYPE
            SYNTAX  Counter
            ACCESS  read-only
            STATUS  mandatory
            DESCRIPTION
                "B3(BIP-8) Valid 15-Min Interval"
            ::= { cHP-STSCurrEty 11 }

        hpStsCurr7DayValidDay  OBJECT-TYPE
            SYNTAX  Counter
            ACCESS  read-only
            STATUS  mandatory
            DESCRIPTION
                "B3(BIP-8) Valid 1-Day Interval"
            ::= { cHP-STSCurrEty 12 }

        hpStsCurr15MTimeElaps  OBJECT-TYPE
            SYNTAX  Counter
            ACCESS  read-only
            STATUS  mandatory
            DESCRIPTION
                "B3(BIP-8) Current 15-MIN Time Elapsed"
            ::= { cHP-STSCurrEty 13 }

        hpStsCurrDayValid15M  OBJECT-TYPE
            SYNTAX  Counter
            ACCESS  read-only
            STATUS  mandatory
            DESCRIPTION
                "B3(BIP-8) Current Day Time Elapsed"
            ::= { cHP-STSCurrEty 14 }

--
--  Performance B3 Interval Table
--
        cHP-STSIntervTab  OBJECT-TYPE
            SYNTAX  SEQUENCE OF  CHP-STSIntervEty
            ACCESS  not-accessible
            STATUS  mandatory
            DESCRIPTION
                "The B3 Interval table."
            ::= { perfDisplayTable 14 }

        cHP-STSIntervEty  OBJECT-TYPE
            SYNTAX  CHP-STSIntervEty
            ACCESS  not-accessible
            STATUS  mandatory
            DESCRIPTION
                "An entry in the B3 Interval table."
            INDEX { hpStsIntervXCUIndex , hpStsIntervPortIndex ,
                    hpStsIntervAug1Sts3Index , hpStsIntervVc3Sts1Index ,
                    hpStsIntervNumber }
            ::= { cHP-STSIntervTab 1 }

        CHP-STSIntervEty ::= SEQUENCE {
            hpStsIntervXCUIndex         XcuNum,
            hpStsIntervPortIndex        PortNum,
            hpStsIntervAug1Sts3Index    Aug1Sts3Num,
            hpStsIntervVc3Sts1Index     Vc3Sts1Num,
            hpStsIntervNumber           INTEGER (1..96),
            hpStsIntervEBs              Counter,
            hpStsIntervBBEs             Counter,
            hpStsIntervESs              Counter,
            hpStsIntervBESs             Counter,
            hpStsIntervSESs             Counter,
            hpStsIntervUASs             Counter
        }

        hpStsIntervXCUIndex  OBJECT-TYPE
            SYNTAX  XcuNum
            ACCESS  read-only
            STATUS  mandatory
            DESCRIPTION
                "XCU index"
            ::= { cHP-STSIntervEty 1 }

        hpStsIntervPortIndex  OBJECT-TYPE
            SYNTAX  PortNum
            ACCESS  read-only
            STATUS  mandatory
            DESCRIPTION
                "PORT #1~#2"
            ::= { cHP-STSIntervEty 2 }

        hpStsIntervAug1Sts3Index  OBJECT-TYPE
            SYNTAX  Aug1Sts3Num
            ACCESS  read-only
            STATUS  mandatory
            DESCRIPTION
                "AUG1/STS3 index"
            ::= { cHP-STSIntervEty 3 }

        hpStsIntervVc3Sts1Index  OBJECT-TYPE
            SYNTAX  Vc3Sts1Num
            ACCESS  read-only
            STATUS  mandatory
            DESCRIPTION
                "VC3/STS1 index"
            ::= { cHP-STSIntervEty 4 }

        hpStsIntervNumber  OBJECT-TYPE
            SYNTAX  INTEGER (1..96)
            ACCESS  read-only
            STATUS  mandatory
            DESCRIPTION
                "A number between 1 and 96"
            ::= { cHP-STSIntervEty 5 }

        hpStsIntervEBs  OBJECT-TYPE
            SYNTAX  Counter
            ACCESS  read-only
            STATUS  mandatory
            DESCRIPTION
                "B3(BIP-8) Error Block"
            ::= { cHP-STSIntervEty 6 }

        hpStsIntervBBEs  OBJECT-TYPE
            SYNTAX  Counter
            ACCESS  read-only
            STATUS  mandatory
            DESCRIPTION
                "B3(BIP-8) Background Block Error"
            ::= { cHP-STSIntervEty 7 }

        hpStsIntervESs  OBJECT-TYPE
            SYNTAX  Counter
            ACCESS  read-only
            STATUS  mandatory
            DESCRIPTION
                "B3(BIP-8) Error Second"
            ::= { cHP-STSIntervEty 8 }

        hpStsIntervBESs  OBJECT-TYPE
            SYNTAX  Counter
            ACCESS  read-only
            STATUS  mandatory
            DESCRIPTION
                "B3(BIP-8) Background Error Second"
            ::= { cHP-STSIntervEty 9 }

        hpStsIntervSESs  OBJECT-TYPE
            SYNTAX  Counter
            ACCESS  read-only
            STATUS  mandatory
            DESCRIPTION
                "B3(BIP-8) Severly Error Second"
            ::= { cHP-STSIntervEty 10 }

        hpStsIntervUASs  OBJECT-TYPE
            SYNTAX  Counter
            ACCESS  read-only
            STATUS  mandatory
            DESCRIPTION
                "B3(BIP-8) Unavailable Second"
            ::= { cHP-STSIntervEty 11 }

--
--  Performance B3 7 Days Table
--
        cHP-STS7DaysTab  OBJECT-TYPE
            SYNTAX  SEQUENCE OF  CHP-STS7DaysEty
            ACCESS  not-accessible
            STATUS  mandatory
            DESCRIPTION
                "The B3 7 days table."
            ::= { perfDisplayTable 15 }

        cHP-STS7DaysEty  OBJECT-TYPE
            SYNTAX  CHP-STS7DaysEty
            ACCESS  not-accessible
            STATUS  mandatory
            DESCRIPTION
                "An entry in the B3 7 days table."
            INDEX { hpSts7DaysXCUIndex , hpSts7DaysPortIndex ,
                    hpSts7DaysAug1Sts3Index , hpSts7DaysVc3Sts1Index ,
                    hpSts7DaysNumber }
            ::= { cHP-STS7DaysTab 1 }

        CHP-STS7DaysEty ::= SEQUENCE {
            hpSts7DaysXCUIndex          XcuNum,
            hpSts7DaysPortIndex         PortNum,
            hpSts7DaysAug1Sts3Index     Aug1Sts3Num,
            hpSts7DaysVc3Sts1Index      Vc3Sts1Num,
            hpSts7DaysNumber            INTEGER (1..7),
            hpSts7DaysDate              DisplayString (SIZE (0..255)),
            hpSts7DaysEBs               Counter,
            hpSts7DaysBBEs              Counter,
            hpSts7DaysESs               Counter,
            hpSts7DaysBESs              Counter,
            hpSts7DaysSESs              Counter,
            hpSts7DaysUASs              Counter
        }

        hpSts7DaysXCUIndex  OBJECT-TYPE
            SYNTAX  XcuNum
            ACCESS  read-only
            STATUS  mandatory
            DESCRIPTION
                "XCU index"
            ::= { cHP-STS7DaysEty 1 }

        hpSts7DaysPortIndex  OBJECT-TYPE
            SYNTAX  PortNum
            ACCESS  read-only
            STATUS  mandatory
            DESCRIPTION
                "PORT #1~#2"
            ::= { cHP-STS7DaysEty 2 }

        hpSts7DaysAug1Sts3Index  OBJECT-TYPE
            SYNTAX  Aug1Sts3Num
            ACCESS  read-only
            STATUS  mandatory
            DESCRIPTION
                "AUG1/STS3 index"
            ::= { cHP-STS7DaysEty 3 }

        hpSts7DaysVc3Sts1Index  OBJECT-TYPE
            SYNTAX  Vc3Sts1Num
            ACCESS  read-only
            STATUS  mandatory
            DESCRIPTION
                "VC3/STS1 index"
            ::= { cHP-STS7DaysEty 4 }

        hpSts7DaysNumber  OBJECT-TYPE
            SYNTAX  INTEGER (1..7)
            ACCESS  read-only
            STATUS  mandatory
            DESCRIPTION
                "A number between 1 and 7"
            ::= { cHP-STS7DaysEty 5 }

        hpSts7DaysDate  OBJECT-TYPE
            SYNTAX  DisplayString (SIZE (0..255))
            ACCESS  read-only
            STATUS  mandatory
            DESCRIPTION
                "Date"
            ::= { cHP-STS7DaysEty 6 }

        hpSts7DaysEBs  OBJECT-TYPE
            SYNTAX  Counter
            ACCESS  read-only
            STATUS  mandatory
            DESCRIPTION
                "B3(BIP-8) Error Block"
            ::= { cHP-STS7DaysEty 7 }

        hpSts7DaysBBEs  OBJECT-TYPE
            SYNTAX  Counter
            ACCESS  read-only
            STATUS  mandatory
            DESCRIPTION
                "B3(BIP-8) Background Block Error"
            ::= { cHP-STS7DaysEty 8 }

        hpSts7DaysESs  OBJECT-TYPE
            SYNTAX  Counter
            ACCESS  read-only
            STATUS  mandatory
            DESCRIPTION
                "B3(BIP-8) Error Second"
            ::= { cHP-STS7DaysEty 9 }

        hpSts7DaysBESs  OBJECT-TYPE
            SYNTAX  Counter
            ACCESS  read-only
            STATUS  mandatory
            DESCRIPTION
                "B3(BIP-8) Background Error Second"
            ::= { cHP-STS7DaysEty 10 }

        hpSts7DaysSESs  OBJECT-TYPE
            SYNTAX  Counter
            ACCESS  read-only
            STATUS  mandatory
            DESCRIPTION
                "B3(BIP-8) Severly Error Second"
            ::= { cHP-STS7DaysEty 11 }

        hpSts7DaysUASs  OBJECT-TYPE
            SYNTAX  Counter
            ACCESS  read-only
            STATUS  mandatory
            DESCRIPTION
                "B3(BIP-8) Unavailable Second"
            ::= { cHP-STS7DaysEty 12 }

--
--  Performance B3 Total Table
--
        cHP-STSTotalTab  OBJECT-TYPE
            SYNTAX  SEQUENCE OF  CHP-STSTotalEty
            ACCESS  not-accessible
            STATUS  mandatory
            DESCRIPTION
                "The B3 Total table."
            ::= { perfDisplayTable 16 }

        cHP-STSTotalEty  OBJECT-TYPE
            SYNTAX  CHP-STSTotalEty
            ACCESS  not-accessible
            STATUS  mandatory
            DESCRIPTION
                "An entry in the B3 Total table."
            INDEX { hpStsTotalXCUIndex , hpStsTotalPortIndex ,
                    hpStsTotalAug1Sts3Index , hpStsTotalVc3Sts1Index }
            ::= { cHP-STSTotalTab 1 }

        CHP-STSTotalEty ::= SEQUENCE {
            hpStsTotalXCUIndex          XcuNum,
            hpStsTotalPortIndex         PortNum,
            hpStsTotalAug1Sts3Index     Aug1Sts3Num,
            hpStsTotalVc3Sts1Index      Vc3Sts1Num,
            hpStsTotalEBs               Counter,
            hpStsTotalBBEs              Counter,
            hpStsTotalESs               Counter,
            hpStsTotalBESs              Counter,
            hpStsTotalSESs              Counter,
            hpStsTotalUASs              Counter
        }

        hpStsTotalXCUIndex  OBJECT-TYPE
            SYNTAX  XcuNum
            ACCESS  read-only
            STATUS  mandatory
            DESCRIPTION
                "XCU index"
            ::= { cHP-STSTotalEty 1 }

        hpStsTotalPortIndex  OBJECT-TYPE
            SYNTAX  PortNum
            ACCESS  read-only
            STATUS  mandatory
            DESCRIPTION
                "PORT #1~#2"
            ::= { cHP-STSTotalEty 2 }

        hpStsTotalAug1Sts3Index  OBJECT-TYPE
            SYNTAX  Aug1Sts3Num
            ACCESS  read-only
            STATUS  mandatory
            DESCRIPTION
                "AUG1/STS3 index"
            ::= { cHP-STSTotalEty 3 }

        hpStsTotalVc3Sts1Index  OBJECT-TYPE
            SYNTAX  Vc3Sts1Num
            ACCESS  read-only
            STATUS  mandatory
            DESCRIPTION
                "VC3/STS1 index"
            ::= { cHP-STSTotalEty 4 }

        hpStsTotalEBs  OBJECT-TYPE
            SYNTAX  Counter
            ACCESS  read-only
            STATUS  mandatory
            DESCRIPTION
                "B3(BIP-8) Error Block"
            ::= { cHP-STSTotalEty 5 }

        hpStsTotalBBEs  OBJECT-TYPE
            SYNTAX  Counter
            ACCESS  read-only
            STATUS  mandatory
            DESCRIPTION
                "B3(BIP-8) Background Block Error"
            ::= { cHP-STSTotalEty 6 }

        hpStsTotalESs  OBJECT-TYPE
            SYNTAX  Counter
            ACCESS  read-only
            STATUS  mandatory
            DESCRIPTION
                "B3(BIP-8) Error Second"
            ::= { cHP-STSTotalEty 7 }

        hpStsTotalBESs  OBJECT-TYPE
            SYNTAX  Counter
            ACCESS  read-only
            STATUS  mandatory
            DESCRIPTION
                "B3(BIP-8) Background Error Second"
            ::= { cHP-STSTotalEty 8 }

        hpStsTotalSESs  OBJECT-TYPE
            SYNTAX  Counter
            ACCESS  read-only
            STATUS  mandatory
            DESCRIPTION
                "B3(BIP-8) Severly Error Second"
            ::= { cHP-STSTotalEty 9 }

        hpStsTotalUASs  OBJECT-TYPE
            SYNTAX  Counter
            ACCESS  read-only
            STATUS  mandatory
            DESCRIPTION
                "B3(BIP-8) Unavailable Second"
            ::= { cHP-STSTotalEty 10 }

--
--  Performance HP-REI Current Table
--
        cFarEndHP-STSCurrTab  OBJECT-TYPE
            SYNTAX  SEQUENCE OF  CFarEndHP-STSCurrEty
            ACCESS  not-accessible
            STATUS  mandatory
            DESCRIPTION
                "The HP-REI/REI-P Current table."
            ::= { perfDisplayTable 17 }

        cFarEndHP-STSCurrEty  OBJECT-TYPE
            SYNTAX  CFarEndHP-STSCurrEty
            ACCESS  not-accessible
            STATUS  mandatory
            DESCRIPTION
                "An entry in the HP-REI/REI-P Current table."
            INDEX { frHpStsCurrXCUIndex , frHpStsCurrPortIndex ,
                    frHpStsCurrAug1Sts3Index , frHpStsCurrVc3Sts1Index }
            ::= { cFarEndHP-STSCurrTab 1 }

        CFarEndHP-STSCurrEty ::= SEQUENCE {
            frHpStsCurrXCUIndex         XcuNum,
            frHpStsCurrPortIndex        PortNum,
            frHpStsCurrAug1Sts3Index    Aug1Sts3Num,
            frHpStsCurrVc3Sts1Index     Vc3Sts1Num,
            frHpStsCurrEBs              Counter,
            frHpStsCurrBBEs             Counter,
            frHpStsCurrESs              Counter,
            frHpStsCurrBESs             Counter,
            frHpStsCurrSESs             Counter,
            frHpStsCurrUASs             Counter,
            frHpStsCurr24HValid15M      Counter,
            frHpStsCurr7DayValidDay     Counter,
            frHpStsCurr15MTimeElaps     Counter,
            frHpStsCurrDayValid15M      Counter
        }

        frHpStsCurrXCUIndex  OBJECT-TYPE
            SYNTAX  XcuNum
            ACCESS  read-only
            STATUS  mandatory
            DESCRIPTION
                "XCU index"
            ::= { cFarEndHP-STSCurrEty 1 }

        frHpStsCurrPortIndex  OBJECT-TYPE
            SYNTAX  PortNum
            ACCESS  read-only
            STATUS  mandatory
            DESCRIPTION
                "PORT #1~#2"
            ::= { cFarEndHP-STSCurrEty 2 }

        frHpStsCurrAug1Sts3Index  OBJECT-TYPE
            SYNTAX  Aug1Sts3Num
            ACCESS  read-only
            STATUS  mandatory
            DESCRIPTION
                "AUG1/STS3 index"
            ::= { cFarEndHP-STSCurrEty 3 }

        frHpStsCurrVc3Sts1Index  OBJECT-TYPE
            SYNTAX  Vc3Sts1Num
            ACCESS  read-only
            STATUS  mandatory
            DESCRIPTION
                "VC3/STS1 index"
            ::= { cFarEndHP-STSCurrEty 4 }

        frHpStsCurrEBs  OBJECT-TYPE
            SYNTAX  Counter
            ACCESS  read-only
            STATUS  mandatory
            DESCRIPTION
                "HP-REI/REI-P(BIP-8) Error Block"
            ::= { cFarEndHP-STSCurrEty 5 }

        frHpStsCurrBBEs  OBJECT-TYPE
            SYNTAX  Counter
            ACCESS  read-only
            STATUS  mandatory
            DESCRIPTION
                "HP-REI/REI-P(BIP-8) Background Block Error"
            ::= { cFarEndHP-STSCurrEty 6 }

        frHpStsCurrESs  OBJECT-TYPE
            SYNTAX  Counter
            ACCESS  read-only
            STATUS  mandatory
            DESCRIPTION
                "HP-REI/REI-P(BIP-8) Error Second"
            ::= { cFarEndHP-STSCurrEty 7 }

        frHpStsCurrBESs  OBJECT-TYPE
            SYNTAX  Counter
            ACCESS  read-only
            STATUS  mandatory
            DESCRIPTION
                "HP-REI/REI-P(BIP-8) Background Error Second"
            ::= { cFarEndHP-STSCurrEty 8 }

        frHpStsCurrSESs  OBJECT-TYPE
            SYNTAX  Counter
            ACCESS  read-only
            STATUS  mandatory
            DESCRIPTION
                "HP-REI/REI-P(BIP-8) Severly Error Second"
            ::= { cFarEndHP-STSCurrEty 9 }

        frHpStsCurrUASs  OBJECT-TYPE
            SYNTAX  Counter
            ACCESS  read-only
            STATUS  mandatory
            DESCRIPTION
                "HP-REI/REI-P(BIP-8) Unavailable Second"
            ::= { cFarEndHP-STSCurrEty 10 }

        frHpStsCurr24HValid15M  OBJECT-TYPE
            SYNTAX  Counter
            ACCESS  read-only
            STATUS  mandatory
            DESCRIPTION
                "HP-REI/REI-P(BIP-8) Valid 15-Min Interval"
            ::= { cFarEndHP-STSCurrEty 11 }

        frHpStsCurr7DayValidDay  OBJECT-TYPE
            SYNTAX  Counter
            ACCESS  read-only
            STATUS  mandatory
            DESCRIPTION
                "HP-REI/REI-P(BIP-8) Valid 1-Day Interval"
            ::= { cFarEndHP-STSCurrEty 12 }

        frHpStsCurr15MTimeElaps  OBJECT-TYPE
            SYNTAX  Counter
            ACCESS  read-only
            STATUS  mandatory
            DESCRIPTION
                "HP-REI/REI-P(BIP-8) Current 15-MIN Time Elapsed"
            ::= { cFarEndHP-STSCurrEty 13 }

        frHpStsCurrDayValid15M  OBJECT-TYPE
            SYNTAX  Counter
            ACCESS  read-only
            STATUS  mandatory
            DESCRIPTION
                "HP-REI/REI-P(BIP-8) Current Day Time Elapsed"
            ::= { cFarEndHP-STSCurrEty 14 }

--
--  Performance HP-REI/REI-P Interval Table
--
        cFarEndHP-STSIntervTab  OBJECT-TYPE
            SYNTAX  SEQUENCE OF  CFarEndHP-STSIntervEty
            ACCESS  not-accessible
            STATUS  mandatory
            DESCRIPTION
                "The HP-REI/REI-P Interval table."
            ::= { perfDisplayTable 18 }

        cFarEndHP-STSIntervEty  OBJECT-TYPE
            SYNTAX  CFarEndHP-STSIntervEty
            ACCESS  not-accessible
            STATUS  mandatory
            DESCRIPTION
                "An entry in the HP-REI/REI-P Interval table."
            INDEX { frHpStsIntervXCUIndex , frHpStsIntervPortIndex ,
                    frHpStsIntervAug1Sts3Index , frHpStsIntervVc3Sts1Index ,
                    frHpStsIntervNumber }
            ::= { cFarEndHP-STSIntervTab 1 }

        CFarEndHP-STSIntervEty ::= SEQUENCE {
            frHpStsIntervXCUIndex       XcuNum,
            frHpStsIntervPortIndex      PortNum,
            frHpStsIntervAug1Sts3Index  Aug1Sts3Num,
            frHpStsIntervVc3Sts1Index   Vc3Sts1Num,
            frHpStsIntervNumber         INTEGER (1..96),
            frHpStsIntervEBs            Counter,
            frHpStsIntervBBEs           Counter,
            frHpStsIntervESs            Counter,
            frHpStsIntervBESs           Counter,
            frHpStsIntervSESs           Counter,
            frHpStsIntervUASs           Counter
        }

        frHpStsIntervXCUIndex  OBJECT-TYPE
            SYNTAX  XcuNum
            ACCESS  read-only
            STATUS  mandatory
            DESCRIPTION
                "XCU index"
            ::= { cFarEndHP-STSIntervEty 1 }

        frHpStsIntervPortIndex  OBJECT-TYPE
            SYNTAX  PortNum
            ACCESS  read-only
            STATUS  mandatory
            DESCRIPTION
                "PORT #1~#2"
            ::= { cFarEndHP-STSIntervEty 2 }

        frHpStsIntervAug1Sts3Index  OBJECT-TYPE
            SYNTAX  Aug1Sts3Num
            ACCESS  read-only
            STATUS  mandatory
            DESCRIPTION
                "AUG1/STS3 index"
            ::= { cFarEndHP-STSIntervEty 3 }

        frHpStsIntervVc3Sts1Index  OBJECT-TYPE
            SYNTAX  Vc3Sts1Num
            ACCESS  read-only
            STATUS  mandatory
            DESCRIPTION
                "VC3/STS1 index"
            ::= { cFarEndHP-STSIntervEty 4 }

        frHpStsIntervNumber  OBJECT-TYPE
            SYNTAX  INTEGER (1..96)
            ACCESS  read-only
            STATUS  mandatory
            DESCRIPTION
                "A number between 1 and 96"
            ::= { cFarEndHP-STSIntervEty 5 }

        frHpStsIntervEBs  OBJECT-TYPE
            SYNTAX  Counter
            ACCESS  read-only
            STATUS  mandatory
            DESCRIPTION
                "HP-REI/REI-P(BIP-8) Error Block"
            ::= { cFarEndHP-STSIntervEty 6 }

        frHpStsIntervBBEs  OBJECT-TYPE
            SYNTAX  Counter
            ACCESS  read-only
            STATUS  mandatory
            DESCRIPTION
                "HP-REI/REI-P(BIP-8) Background Block Error"
            ::= { cFarEndHP-STSIntervEty 7 }

        frHpStsIntervESs  OBJECT-TYPE
            SYNTAX  Counter
            ACCESS  read-only
            STATUS  mandatory
            DESCRIPTION
                "HP-REI/REI-P(BIP-8) Error Second"
            ::= { cFarEndHP-STSIntervEty 8 }

        frHpStsIntervBESs  OBJECT-TYPE
            SYNTAX  Counter
            ACCESS  read-only
            STATUS  mandatory
            DESCRIPTION
                "HP-REI/REI-P(BIP-8) Background Error Second"
            ::= { cFarEndHP-STSIntervEty 9 }

        frHpStsIntervSESs  OBJECT-TYPE
            SYNTAX  Counter
            ACCESS  read-only
            STATUS  mandatory
            DESCRIPTION
                "HP-REI/REI-P(BIP-8) Severly Error Second"
            ::= { cFarEndHP-STSIntervEty 10 }

        frHpStsIntervUASs  OBJECT-TYPE
            SYNTAX  Counter
            ACCESS  read-only
            STATUS  mandatory
            DESCRIPTION
                "HP-REI/REI-P(BIP-8) Unavailable Second"
            ::= { cFarEndHP-STSIntervEty 11 }

--
--  Performance HP-REI/REI-P 7 Days Table
--
        cFarEndHP-STS7DaysTab  OBJECT-TYPE
            SYNTAX  SEQUENCE OF  CFarEndHP-STS7DaysEty
            ACCESS  not-accessible
            STATUS  mandatory
            DESCRIPTION
                "The HP-REI/REI-P 7 days table."
            ::= { perfDisplayTable 19 }

        cFarEndHP-STS7DaysEty  OBJECT-TYPE
            SYNTAX  CFarEndHP-STS7DaysEty
            ACCESS  not-accessible
            STATUS  mandatory
            DESCRIPTION
                "An entry in the HP-REI/REI-P 7 days table."
            INDEX { frHpSts7DaysXCUIndex , frHpSts7DaysPortIndex ,
                    frHpSts7DaysAug1Sts3Index , frHpSts7DaysVc3Sts1Index ,
                    frHpSts7DaysNumber }
            ::= { cFarEndHP-STS7DaysTab 1 }

        CFarEndHP-STS7DaysEty ::= SEQUENCE {
            frHpSts7DaysXCUIndex        XcuNum,
            frHpSts7DaysPortIndex       PortNum,
            frHpSts7DaysAug1Sts3Index   Aug1Sts3Num,
            frHpSts7DaysVc3Sts1Index    Vc3Sts1Num,
            frHpSts7DaysNumber          INTEGER (1..7),
            frHpSts7DaysDate            DisplayString (SIZE (0..255)),
            frHpSts7DaysEBs             Counter,
            frHpSts7DaysBBEs            Counter,
            frHpSts7DaysESs             Counter,
            frHpSts7DaysBESs            Counter,
            frHpSts7DaysSESs            Counter,
            frHpSts7DaysUASs            Counter
        }

        frHpSts7DaysXCUIndex  OBJECT-TYPE
            SYNTAX  XcuNum
            ACCESS  read-only
            STATUS  mandatory
            DESCRIPTION
                "XCU index"
            ::= { cFarEndHP-STS7DaysEty 1 }

        frHpSts7DaysPortIndex  OBJECT-TYPE
            SYNTAX  PortNum
            ACCESS  read-only
            STATUS  mandatory
            DESCRIPTION
                "PORT #1~#2"
            ::= { cFarEndHP-STS7DaysEty 2 }

        frHpSts7DaysAug1Sts3Index  OBJECT-TYPE
            SYNTAX  Aug1Sts3Num
            ACCESS  read-only
            STATUS  mandatory
            DESCRIPTION
                "AUG1/STS3 index"
            ::= { cFarEndHP-STS7DaysEty 3 }

        frHpSts7DaysVc3Sts1Index  OBJECT-TYPE
            SYNTAX  Vc3Sts1Num
            ACCESS  read-only
            STATUS  mandatory
            DESCRIPTION
                "VC3/STS1 index"
            ::= { cFarEndHP-STS7DaysEty 4 }

        frHpSts7DaysNumber  OBJECT-TYPE
            SYNTAX  INTEGER (1..7)
            ACCESS  read-only
            STATUS  mandatory
            DESCRIPTION
                "A number between 1 and 7"
            ::= { cFarEndHP-STS7DaysEty 5 }

        frHpSts7DaysDate  OBJECT-TYPE
            SYNTAX  DisplayString (SIZE (0..255))
            ACCESS  read-only
            STATUS  mandatory
            DESCRIPTION
                "Date"
            ::= { cFarEndHP-STS7DaysEty 6 }

        frHpSts7DaysEBs  OBJECT-TYPE
            SYNTAX  Counter
            ACCESS  read-only
            STATUS  mandatory
            DESCRIPTION
                "HP-REI/REI-P(BIP-8) Error Block"
            ::= { cFarEndHP-STS7DaysEty 7 }

        frHpSts7DaysBBEs  OBJECT-TYPE
            SYNTAX  Counter
            ACCESS  read-only
            STATUS  mandatory
            DESCRIPTION
                "HP-REI/REI-P(BIP-8) Background Block Error"
            ::= { cFarEndHP-STS7DaysEty 8 }

        frHpSts7DaysESs  OBJECT-TYPE
            SYNTAX  Counter
            ACCESS  read-only
            STATUS  mandatory
            DESCRIPTION
                "HP-REI/REI-P(BIP-8) Error Second"
            ::= { cFarEndHP-STS7DaysEty 9 }

        frHpSts7DaysBESs  OBJECT-TYPE
            SYNTAX  Counter
            ACCESS  read-only
            STATUS  mandatory
            DESCRIPTION
                "HP-REI/REI-P(BIP-8) Background Error Second"
            ::= { cFarEndHP-STS7DaysEty 10 }

        frHpSts7DaysSESs  OBJECT-TYPE
            SYNTAX  Counter
            ACCESS  read-only
            STATUS  mandatory
            DESCRIPTION
                "HP-REI/REI-P(BIP-8) Severly Error Second"
            ::= { cFarEndHP-STS7DaysEty 11 }

        frHpSts7DaysUASs  OBJECT-TYPE
            SYNTAX  Counter
            ACCESS  read-only
            STATUS  mandatory
            DESCRIPTION
                "HP-REI/REI-P(BIP-8) Unavailable Second"
            ::= { cFarEndHP-STS7DaysEty 12 }

--
--  Performance HP-REI/REI-P Total Table
--
        cFarEndHP-STSTotalTab  OBJECT-TYPE
            SYNTAX  SEQUENCE OF  CFarEndHP-STSTotalEty
            ACCESS  not-accessible
            STATUS  mandatory
            DESCRIPTION
                "The HP-REI/REI-P Total table."
            ::= { perfDisplayTable 20 }

        cFarEndHP-STSTotalEty  OBJECT-TYPE
            SYNTAX  CFarEndHP-STSTotalEty
            ACCESS  not-accessible
            STATUS  mandatory
            DESCRIPTION
                "An entry in the HP-REI/REI-P Total table."
            INDEX { frHpStsTotalXCUIndex , frHpStsTotalPortIndex ,
                    frHpStsTotalAug1Sts3Index , frHpStsTotalVc3Sts1Index }
            ::= { cFarEndHP-STSTotalTab 1 }

        CFarEndHP-STSTotalEty ::= SEQUENCE {
            frHpStsTotalXCUIndex        XcuNum,
            frHpStsTotalPortIndex       PortNum,
            frHpStsTotalAug1Sts3Index   Aug1Sts3Num,
            frHpStsTotalVc3Sts1Index    Vc3Sts1Num,
            frHpStsTotalEBs             Counter,
            frHpStsTotalBBEs            Counter,
            frHpStsTotalESs             Counter,
            frHpStsTotalBESs            Counter,
            frHpStsTotalSESs            Counter,
            frHpStsTotalUASs            Counter
        }

        frHpStsTotalXCUIndex  OBJECT-TYPE
            SYNTAX  XcuNum
            ACCESS  read-only
            STATUS  mandatory
            DESCRIPTION
                "XCU index"
            ::= { cFarEndHP-STSTotalEty 1 }

        frHpStsTotalPortIndex  OBJECT-TYPE
            SYNTAX  PortNum
            ACCESS  read-only
            STATUS  mandatory
            DESCRIPTION
                "PORT #1~#2"
            ::= { cFarEndHP-STSTotalEty 2 }

        frHpStsTotalAug1Sts3Index  OBJECT-TYPE
            SYNTAX  Aug1Sts3Num
            ACCESS  read-only
            STATUS  mandatory
            DESCRIPTION
                "AUG1/STS3 index"
            ::= { cFarEndHP-STSTotalEty 3 }

        frHpStsTotalVc3Sts1Index  OBJECT-TYPE
            SYNTAX  Vc3Sts1Num
            ACCESS  read-only
            STATUS  mandatory
            DESCRIPTION
                "VC3/STS1 index"
            ::= { cFarEndHP-STSTotalEty 4 }

        frHpStsTotalEBs  OBJECT-TYPE
            SYNTAX  Counter
            ACCESS  read-only
            STATUS  mandatory
            DESCRIPTION
                "HP-REI/REI-P(BIP-8) Error Block"
            ::= { cFarEndHP-STSTotalEty 5 }

        frHpStsTotalBBEs  OBJECT-TYPE
            SYNTAX  Counter
            ACCESS  read-only
            STATUS  mandatory
            DESCRIPTION
                "HP-REI/REI-P(BIP-8) Background Block Error"
            ::= { cFarEndHP-STSTotalEty 6 }

        frHpStsTotalESs  OBJECT-TYPE
            SYNTAX  Counter
            ACCESS  read-only
            STATUS  mandatory
            DESCRIPTION
                "HP-REI/REI-P(BIP-8) Error Second"
            ::= { cFarEndHP-STSTotalEty 7 }

        frHpStsTotalBESs  OBJECT-TYPE
            SYNTAX  Counter
            ACCESS  read-only
            STATUS  mandatory
            DESCRIPTION
                "HP-REI/REI-P(BIP-8) Background Error Second"
            ::= { cFarEndHP-STSTotalEty 8 }

        frHpStsTotalSESs  OBJECT-TYPE
            SYNTAX  Counter
            ACCESS  read-only
            STATUS  mandatory
            DESCRIPTION
                "HP-REI/REI-P(BIP-8) Severly Error Second"
            ::= { cFarEndHP-STSTotalEty 9 }

        frHpStsTotalUASs  OBJECT-TYPE
            SYNTAX  Counter
            ACCESS  read-only
            STATUS  mandatory
            DESCRIPTION
                "HP-REI/REI-P(BIP-8) Unavailable Second"
            ::= { cFarEndHP-STSTotalEty 10 }

--
--  Performance LP-BIP Current Table
--
        cLP-VTCurrTab  OBJECT-TYPE
            SYNTAX  SEQUENCE OF  CLP-VTCurrEty
            ACCESS  not-accessible
            STATUS  mandatory
            DESCRIPTION
                "The LP-BIP Current table."
            ::= { perfDisplayTable 21 }

        cLP-VTCurrEty  OBJECT-TYPE
            SYNTAX  CLP-VTCurrEty
            ACCESS  not-accessible
            STATUS  mandatory
            DESCRIPTION
                "An entry in the LP-BIP Current table."
            INDEX { lpVtCurrXCUIndex , lpVtCurrPortIndex ,
                    lpVtCurrAug1Sts3Index , lpVtCurrVc3Sts1Index ,
                    lpVtCurrTU1xVtxIndex }
            ::= { cLP-VTCurrTab 1 }

        CLP-VTCurrEty ::= SEQUENCE {
            lpVtCurrXCUIndex            XcuNum,
            lpVtCurrPortIndex           PortNum,
            lpVtCurrAug1Sts3Index       Aug1Sts3Num,
            lpVtCurrVc3Sts1Index        Vc3Sts1Num,
            lpVtCurrTU1xVtxIndex        TU1xVtxNum,
            lpVtCurrEBs                 Counter,
            lpVtCurrBBEs                Counter,
            lpVtCurrESs                 Counter,
            lpVtCurrBESs                Counter,
            lpVtCurrSESs                Counter,
            lpVtCurrUASs                Counter,
            lpVtCurr24HValid15M         Counter,
            lpVtCurr7DayValidDay        Counter,
            lpVtCurr15MTimeElaps        Counter,
            lpVtCurrDayValid15M         Counter
        }

        lpVtCurrXCUIndex  OBJECT-TYPE
            SYNTAX  XcuNum
            ACCESS  read-only
            STATUS  mandatory
            DESCRIPTION
                "XCU index"
            ::= { cLP-VTCurrEty 1 }

        lpVtCurrPortIndex  OBJECT-TYPE
            SYNTAX  PortNum
            ACCESS  read-only
            STATUS  mandatory
            DESCRIPTION
                "PORT #1~#2"
            ::= { cLP-VTCurrEty 2 }

        lpVtCurrAug1Sts3Index  OBJECT-TYPE
            SYNTAX  Aug1Sts3Num
            ACCESS  read-only
            STATUS  mandatory
            DESCRIPTION
                "AUG1/STS3 index"
            ::= { cLP-VTCurrEty 3 }

        lpVtCurrVc3Sts1Index  OBJECT-TYPE
            SYNTAX  Vc3Sts1Num
            ACCESS  read-only
            STATUS  mandatory
            DESCRIPTION
                "VC3/STS1 index"
            ::= { cLP-VTCurrEty 4 }

        lpVtCurrTU1xVtxIndex  OBJECT-TYPE
            SYNTAX  TU1xVtxNum
            ACCESS  read-only
            STATUS  mandatory
            DESCRIPTION
                "VC1x/VTx index"
            ::= { cLP-VTCurrEty 5 }

        lpVtCurrEBs  OBJECT-TYPE
            SYNTAX  Counter
            ACCESS  read-only
            STATUS  mandatory
            DESCRIPTION
                "LP-BIP Error Block"
            ::= { cLP-VTCurrEty 6 }

        lpVtCurrBBEs  OBJECT-TYPE
            SYNTAX  Counter
            ACCESS  read-only
            STATUS  mandatory
            DESCRIPTION
                "LP-BIP Background Block Error"
            ::= { cLP-VTCurrEty 7 }

        lpVtCurrESs  OBJECT-TYPE
            SYNTAX  Counter
            ACCESS  read-only
            STATUS  mandatory
            DESCRIPTION
                "LP-BIP Error Second"
            ::= { cLP-VTCurrEty 8 }

        lpVtCurrBESs  OBJECT-TYPE
            SYNTAX  Counter
            ACCESS  read-only
            STATUS  mandatory
            DESCRIPTION
                "LP-BIP Background Error Second"
            ::= { cLP-VTCurrEty 9 }

        lpVtCurrSESs  OBJECT-TYPE
            SYNTAX  Counter
            ACCESS  read-only
            STATUS  mandatory
            DESCRIPTION
                "LP-BIP Severly Error Second"
            ::= { cLP-VTCurrEty 10 }

        lpVtCurrUASs  OBJECT-TYPE
            SYNTAX  Counter
            ACCESS  read-only
            STATUS  mandatory
            DESCRIPTION
                "LP-BIP Unavailable Second"
            ::= { cLP-VTCurrEty 11 }

        lpVtCurr24HValid15M  OBJECT-TYPE
            SYNTAX  Counter
            ACCESS  read-only
            STATUS  mandatory
            DESCRIPTION
                "LP-BIP Valid 15-Min Interval"
            ::= { cLP-VTCurrEty 12 }

        lpVtCurr7DayValidDay  OBJECT-TYPE
            SYNTAX  Counter
            ACCESS  read-only
            STATUS  mandatory
            DESCRIPTION
                "LP-BIP Valid 1-Day Interval"
            ::= { cLP-VTCurrEty 13 }

        lpVtCurr15MTimeElaps  OBJECT-TYPE
            SYNTAX  Counter
            ACCESS  read-only
            STATUS  mandatory
            DESCRIPTION
                "LP-BIP Current 15-MIN Time Elapsed"
            ::= { cLP-VTCurrEty 14 }

        lpVtCurrDayValid15M  OBJECT-TYPE
            SYNTAX  Counter
            ACCESS  read-only
            STATUS  mandatory
            DESCRIPTION
                "LP-BIP Current Day Time Elapsed"
            ::= { cLP-VTCurrEty 15 }

--
--  Performance LP-BIP Interval Table
--
        cLP-VTIntervTab  OBJECT-TYPE
            SYNTAX  SEQUENCE OF  CLP-VTIntervEty
            ACCESS  not-accessible
            STATUS  mandatory
            DESCRIPTION
                "The LP-BIP Interval table."
            ::= { perfDisplayTable 22 }

        cLP-VTIntervEty  OBJECT-TYPE
            SYNTAX  CLP-VTIntervEty
            ACCESS  not-accessible
            STATUS  mandatory
            DESCRIPTION
                "An entry in the LP-BIP Interval table."
            INDEX { lpVtIntervXCUIndex , lpVtIntervPortIndex ,
                    lpVtIntervAug1Sts3Index , lpVtIntervVc3Sts1Index ,
                    lpVtIntervTU1xVtxIndex , lpVtIntervNumber }
            ::= { cLP-VTIntervTab 1 }

        CLP-VTIntervEty ::= SEQUENCE {
            lpVtIntervXCUIndex          XcuNum,
            lpVtIntervPortIndex         PortNum,
            lpVtIntervAug1Sts3Index     Aug1Sts3Num,
            lpVtIntervVc3Sts1Index      Vc3Sts1Num,
            lpVtIntervTU1xVtxIndex      TU1xVtxNum,
            lpVtIntervNumber            INTEGER (1..96),
            lpVtIntervEBs               Counter,
            lpVtIntervBBEs              Counter,
            lpVtIntervESs               Counter,
            lpVtIntervBESs              Counter,
            lpVtIntervSESs              Counter,
            lpVtIntervUASs              Counter
        }

        lpVtIntervXCUIndex  OBJECT-TYPE
            SYNTAX  XcuNum
            ACCESS  read-only
            STATUS  mandatory
            DESCRIPTION
                "XCU index"
            ::= { cLP-VTIntervEty 1 }

        lpVtIntervPortIndex  OBJECT-TYPE
            SYNTAX  PortNum
            ACCESS  read-only
            STATUS  mandatory
            DESCRIPTION
                "PORT #1~#2"
            ::= { cLP-VTIntervEty 2 }

        lpVtIntervAug1Sts3Index  OBJECT-TYPE
            SYNTAX  Aug1Sts3Num
            ACCESS  read-only
            STATUS  mandatory
            DESCRIPTION
                "AUG1/STS3 index"
            ::= { cLP-VTIntervEty 3 }

        lpVtIntervVc3Sts1Index  OBJECT-TYPE
            SYNTAX  Vc3Sts1Num
            ACCESS  read-only
            STATUS  mandatory
            DESCRIPTION
                "VC3/STS1 index"
            ::= { cLP-VTIntervEty 4 }

        lpVtIntervTU1xVtxIndex  OBJECT-TYPE
            SYNTAX  TU1xVtxNum
            ACCESS  read-only
            STATUS  mandatory
            DESCRIPTION
                "VC1x/VTx index"
            ::= { cLP-VTIntervEty 5 }

        lpVtIntervNumber  OBJECT-TYPE
            SYNTAX  INTEGER (1..96)
            ACCESS  read-only
            STATUS  mandatory
            DESCRIPTION
                "A number between 1 and 96"
            ::= { cLP-VTIntervEty 6 }

        lpVtIntervEBs  OBJECT-TYPE
            SYNTAX  Counter
            ACCESS  read-only
            STATUS  mandatory
            DESCRIPTION
                "LP-BIP Error Block"
            ::= { cLP-VTIntervEty 7 }

        lpVtIntervBBEs  OBJECT-TYPE
            SYNTAX  Counter
            ACCESS  read-only
            STATUS  mandatory
            DESCRIPTION
                "LP-BIP Background Block Error"
            ::= { cLP-VTIntervEty 8 }

        lpVtIntervESs  OBJECT-TYPE
            SYNTAX  Counter
            ACCESS  read-only
            STATUS  mandatory
            DESCRIPTION
                "LP-BIP Error Second"
            ::= { cLP-VTIntervEty 9 }

        lpVtIntervBESs  OBJECT-TYPE
            SYNTAX  Counter
            ACCESS  read-only
            STATUS  mandatory
            DESCRIPTION
                "LP-BIP Background Error Second"
            ::= { cLP-VTIntervEty 10 }

        lpVtIntervSESs  OBJECT-TYPE
            SYNTAX  Counter
            ACCESS  read-only
            STATUS  mandatory
            DESCRIPTION
                "LP-BIP Severly Error Second"
            ::= { cLP-VTIntervEty 11 }

        lpVtIntervUASs  OBJECT-TYPE
            SYNTAX  Counter
            ACCESS  read-only
            STATUS  mandatory
            DESCRIPTION
                "LP-BIP Unavailable Second"
            ::= { cLP-VTIntervEty 12 }

--
--  Performance LP-BIP 7 Days Table
--
        cLP-VT7DaysTab  OBJECT-TYPE
            SYNTAX  SEQUENCE OF  CLP-VT7DaysEty
            ACCESS  not-accessible
            STATUS  mandatory
            DESCRIPTION
                "The LP-BIP 7 days table."
            ::= { perfDisplayTable 23 }

        cLP-VT7DaysEty  OBJECT-TYPE
            SYNTAX  CLP-VT7DaysEty
            ACCESS  not-accessible
            STATUS  mandatory
            DESCRIPTION
                "An entry in the LP-BIP 7 days table."
            INDEX { lpVt7DaysXCUIndex , lpVt7DaysPortIndex ,
                    lpVt7DaysAug1Sts3Index , lpVt7DaysVc3Sts1Index ,
                    lpVt7DaysTU1xVtxIndex , lpVt7DaysNumber }
            ::= { cLP-VT7DaysTab 1 }

        CLP-VT7DaysEty ::= SEQUENCE {
            lpVt7DaysXCUIndex           XcuNum,
            lpVt7DaysPortIndex          PortNum,
            lpVt7DaysAug1Sts3Index      Aug1Sts3Num,
            lpVt7DaysVc3Sts1Index       Vc3Sts1Num,
            lpVt7DaysTU1xVtxIndex       TU1xVtxNum,
            lpVt7DaysNumber             INTEGER (1..7),
            lpVt7DaysDate               DisplayString (SIZE (0..255)),
            lpVt7DaysEBs                Counter,
            lpVt7DaysBBEs               Counter,
            lpVt7DaysESs                Counter,
            lpVt7DaysBESs               Counter,
            lpVt7DaysSESs               Counter,
            lpVt7DaysUASs               Counter
        }

        lpVt7DaysXCUIndex  OBJECT-TYPE
            SYNTAX  XcuNum
            ACCESS  read-only
            STATUS  mandatory
            DESCRIPTION
                "XCU index"
            ::= { cLP-VT7DaysEty 1 }

        lpVt7DaysPortIndex  OBJECT-TYPE
            SYNTAX  PortNum
            ACCESS  read-only
            STATUS  mandatory
            DESCRIPTION
                "PORT #1~#2"
            ::= { cLP-VT7DaysEty 2 }

        lpVt7DaysAug1Sts3Index  OBJECT-TYPE
            SYNTAX  Aug1Sts3Num
            ACCESS  read-only
            STATUS  mandatory
            DESCRIPTION
                "AUG1/STS3 index"
            ::= { cLP-VT7DaysEty 3 }

        lpVt7DaysVc3Sts1Index  OBJECT-TYPE
            SYNTAX  Vc3Sts1Num
            ACCESS  read-only
            STATUS  mandatory
            DESCRIPTION
                "VC3/STS1 index"
            ::= { cLP-VT7DaysEty 4 }

        lpVt7DaysTU1xVtxIndex  OBJECT-TYPE
            SYNTAX  TU1xVtxNum
            ACCESS  read-only
            STATUS  mandatory
            DESCRIPTION
                "VC1x/VTx index"
            ::= { cLP-VT7DaysEty 5 }

        lpVt7DaysNumber  OBJECT-TYPE
            SYNTAX  INTEGER (1..7)
            ACCESS  read-only
            STATUS  mandatory
            DESCRIPTION
                "A number between 1 and 7"
            ::= { cLP-VT7DaysEty 6 }

        lpVt7DaysDate  OBJECT-TYPE
            SYNTAX  DisplayString (SIZE (0..255))
            ACCESS  read-only
            STATUS  mandatory
            DESCRIPTION
                "Date"
            ::= { cLP-VT7DaysEty 7 }

        lpVt7DaysEBs  OBJECT-TYPE
            SYNTAX  Counter
            ACCESS  read-only
            STATUS  mandatory
            DESCRIPTION
                "LP-BIP Error Block"
            ::= { cLP-VT7DaysEty 8 }

        lpVt7DaysBBEs  OBJECT-TYPE
            SYNTAX  Counter
            ACCESS  read-only
            STATUS  mandatory
            DESCRIPTION
                "LP-BIP Background Block Error"
            ::= { cLP-VT7DaysEty 9 }

        lpVt7DaysESs  OBJECT-TYPE
            SYNTAX  Counter
            ACCESS  read-only
            STATUS  mandatory
            DESCRIPTION
                "LP-BIP Error Second"
            ::= { cLP-VT7DaysEty 10 }

        lpVt7DaysBESs  OBJECT-TYPE
            SYNTAX  Counter
            ACCESS  read-only
            STATUS  mandatory
            DESCRIPTION
                "LP-BIP Background Error Second"
            ::= { cLP-VT7DaysEty 11 }

        lpVt7DaysSESs  OBJECT-TYPE
            SYNTAX  Counter
            ACCESS  read-only
            STATUS  mandatory
            DESCRIPTION
                "LP-BIP Severly Error Second"
            ::= { cLP-VT7DaysEty 12 }

        lpVt7DaysUASs  OBJECT-TYPE
            SYNTAX  Counter
            ACCESS  read-only
            STATUS  mandatory
            DESCRIPTION
                "LP-BIP Unavailable Second"
            ::= { cLP-VT7DaysEty 13 }

--
--  Performance LP-BIP Total Table
--
        cLP-VTTotalTab  OBJECT-TYPE
            SYNTAX  SEQUENCE OF  CLP-VTTotalEty
            ACCESS  not-accessible
            STATUS  mandatory
            DESCRIPTION
                "The LP-BIP Total table."
            ::= { perfDisplayTable 24 }

        cLP-VTTotalEty  OBJECT-TYPE
            SYNTAX  CLP-VTTotalEty
            ACCESS  not-accessible
            STATUS  mandatory
            DESCRIPTION
                "An entry in the LP-BIP Total table."
            INDEX { lpVtTotalXCUIndex , lpVtTotalPortIndex ,
                    lpVtTotalAug1Sts3Index , lpVtTotalVc3Sts1Index ,
                    lpVtTotalTU1xVtxIndex }
            ::= { cLP-VTTotalTab 1 }

        CLP-VTTotalEty ::= SEQUENCE {
            lpVtTotalXCUIndex           XcuNum,
            lpVtTotalPortIndex          PortNum,
            lpVtTotalAug1Sts3Index      Aug1Sts3Num,
            lpVtTotalVc3Sts1Index       Vc3Sts1Num,
            lpVtTotalTU1xVtxIndex       TU1xVtxNum,
            lpVtTotalEBs                Counter,
            lpVtTotalBBEs               Counter,
            lpVtTotalESs                Counter,
            lpVtTotalBESs               Counter,
            lpVtTotalSESs               Counter,
            lpVtTotalUASs               Counter
        }

        lpVtTotalXCUIndex  OBJECT-TYPE
            SYNTAX  XcuNum
            ACCESS  read-only
            STATUS  mandatory
            DESCRIPTION
                "XCU index"
            ::= { cLP-VTTotalEty 1 }

        lpVtTotalPortIndex  OBJECT-TYPE
            SYNTAX  PortNum
            ACCESS  read-only
            STATUS  mandatory
            DESCRIPTION
                "PORT #1~#2"
            ::= { cLP-VTTotalEty 2 }

        lpVtTotalAug1Sts3Index  OBJECT-TYPE
            SYNTAX  Aug1Sts3Num
            ACCESS  read-only
            STATUS  mandatory
            DESCRIPTION
                "AUG1/STS3 index"
            ::= { cLP-VTTotalEty 3 }

        lpVtTotalVc3Sts1Index  OBJECT-TYPE
            SYNTAX  Vc3Sts1Num
            ACCESS  read-only
            STATUS  mandatory
            DESCRIPTION
                "VC3/STS1 index"
            ::= { cLP-VTTotalEty 4 }

        lpVtTotalTU1xVtxIndex  OBJECT-TYPE
            SYNTAX  TU1xVtxNum
            ACCESS  read-only
            STATUS  mandatory
            DESCRIPTION
                "VC1x/VTx index"
            ::= { cLP-VTTotalEty 5 }

        lpVtTotalEBs  OBJECT-TYPE
            SYNTAX  Counter
            ACCESS  read-only
            STATUS  mandatory
            DESCRIPTION
                "LP-BIP Error Block"
            ::= { cLP-VTTotalEty 6 }

        lpVtTotalBBEs  OBJECT-TYPE
            SYNTAX  Counter
            ACCESS  read-only
            STATUS  mandatory
            DESCRIPTION
                "LP-BIP Background Block Error"
            ::= { cLP-VTTotalEty 7 }

        lpVtTotalESs  OBJECT-TYPE
            SYNTAX  Counter
            ACCESS  read-only
            STATUS  mandatory
            DESCRIPTION
                "LP-BIP Error Second"
            ::= { cLP-VTTotalEty 8 }

        lpVtTotalBESs  OBJECT-TYPE
            SYNTAX  Counter
            ACCESS  read-only
            STATUS  mandatory
            DESCRIPTION
                "LP-BIP Background Error Second"
            ::= { cLP-VTTotalEty 9 }

        lpVtTotalSESs  OBJECT-TYPE
            SYNTAX  Counter
            ACCESS  read-only
            STATUS  mandatory
            DESCRIPTION
                "LP-BIP Severly Error Second"
            ::= { cLP-VTTotalEty 10 }

        lpVtTotalUASs  OBJECT-TYPE
            SYNTAX  Counter
            ACCESS  read-only
            STATUS  mandatory
            DESCRIPTION
                "LP-BIP Unavailable Second"
            ::= { cLP-VTTotalEty 11 }

--
--  Performance LP-REI Current Table
--
        cFarEndLP-VTCurrTab  OBJECT-TYPE
            SYNTAX  SEQUENCE OF  CFarEndLP-VTCurrEty
            ACCESS  not-accessible
            STATUS  mandatory
            DESCRIPTION
                "The LP-REI/REI-V Current table."
            ::= { perfDisplayTable 25 }

        cFarEndLP-VTCurrEty  OBJECT-TYPE
            SYNTAX  CFarEndLP-VTCurrEty
            ACCESS  not-accessible
            STATUS  mandatory
            DESCRIPTION
                "An entry in the LP-REI/REI-V Current table."
            INDEX { frLpVtCurrXCUIndex , frLpVtCurrPortIndex ,
                    frLpVtCurrAug1Sts3Index , frLpVtCurrVc3Sts1Index ,
                    frLpVtCurrTU1xVtxIndex }
            ::= { cFarEndLP-VTCurrTab 1 }

        CFarEndLP-VTCurrEty ::= SEQUENCE {
            frLpVtCurrXCUIndex          XcuNum,
            frLpVtCurrPortIndex         PortNum,
            frLpVtCurrAug1Sts3Index     Aug1Sts3Num,
            frLpVtCurrVc3Sts1Index      Vc3Sts1Num,
            frLpVtCurrTU1xVtxIndex      TU1xVtxNum,
            frLpVtCurrEBs               Counter,
            frLpVtCurrBBEs              Counter,
            frLpVtCurrESs               Counter,
            frLpVtCurrBESs              Counter,
            frLpVtCurrSESs              Counter,
            frLpVtCurrUASs              Counter,
            frLpVtCurr24HValid15M       Counter,
            frLpVtCurr7DayValidDay      Counter,
            frLpVtCurr15MTimeElaps      Counter,
            frLpVtCurrDayValid15M       Counter
        }

        frLpVtCurrXCUIndex  OBJECT-TYPE
            SYNTAX  XcuNum
            ACCESS  read-only
            STATUS  mandatory
            DESCRIPTION
                "XCU index"
            ::= { cFarEndLP-VTCurrEty 1 }

        frLpVtCurrPortIndex  OBJECT-TYPE
            SYNTAX  PortNum
            ACCESS  read-only
            STATUS  mandatory
            DESCRIPTION
                "PORT #1~#2"
            ::= { cFarEndLP-VTCurrEty 2 }

        frLpVtCurrAug1Sts3Index  OBJECT-TYPE
            SYNTAX  Aug1Sts3Num
            ACCESS  read-only
            STATUS  mandatory
            DESCRIPTION
                "AUG1/STS3 index"
            ::= { cFarEndLP-VTCurrEty 3 }

        frLpVtCurrVc3Sts1Index  OBJECT-TYPE
            SYNTAX  Vc3Sts1Num
            ACCESS  read-only
            STATUS  mandatory
            DESCRIPTION
                "VC3/STS1 index"
            ::= { cFarEndLP-VTCurrEty 4 }

        frLpVtCurrTU1xVtxIndex  OBJECT-TYPE
            SYNTAX  TU1xVtxNum
            ACCESS  read-only
            STATUS  mandatory
            DESCRIPTION
                "VC1x/VTx index"
            ::= { cFarEndLP-VTCurrEty 5 }

        frLpVtCurrEBs  OBJECT-TYPE
            SYNTAX  Counter
            ACCESS  read-only
            STATUS  mandatory
            DESCRIPTION
                "LP-REI/REI-V Error Block"
            ::= { cFarEndLP-VTCurrEty 6 }

        frLpVtCurrBBEs  OBJECT-TYPE
            SYNTAX  Counter
            ACCESS  read-only
            STATUS  mandatory
            DESCRIPTION
                "LP-REI/REI-V Background Block Error"
            ::= { cFarEndLP-VTCurrEty 7 }

        frLpVtCurrESs  OBJECT-TYPE
            SYNTAX  Counter
            ACCESS  read-only
            STATUS  mandatory
            DESCRIPTION
                "LP-REI/REI-V Error Second"
            ::= { cFarEndLP-VTCurrEty 8 }

        frLpVtCurrBESs  OBJECT-TYPE
            SYNTAX  Counter
            ACCESS  read-only
            STATUS  mandatory
            DESCRIPTION
                "LP-REI/REI-V Background Error Second"
            ::= { cFarEndLP-VTCurrEty 9 }

        frLpVtCurrSESs  OBJECT-TYPE
            SYNTAX  Counter
            ACCESS  read-only
            STATUS  mandatory
            DESCRIPTION
                "LP-REI/REI-V Severly Error Second"
            ::= { cFarEndLP-VTCurrEty 10 }

        frLpVtCurrUASs  OBJECT-TYPE
            SYNTAX  Counter
            ACCESS  read-only
            STATUS  mandatory
            DESCRIPTION
                "LP-REI/REI-V Unavailable Second"
            ::= { cFarEndLP-VTCurrEty 11 }

        frLpVtCurr24HValid15M  OBJECT-TYPE
            SYNTAX  Counter
            ACCESS  read-only
            STATUS  mandatory
            DESCRIPTION
                "LP-REI/REI-V Valid 15-Min Interval"
            ::= { cFarEndLP-VTCurrEty 12 }

        frLpVtCurr7DayValidDay  OBJECT-TYPE
            SYNTAX  Counter
            ACCESS  read-only
            STATUS  mandatory
            DESCRIPTION
                "LP-REI/REI-V Valid 1-Day Interval"
            ::= { cFarEndLP-VTCurrEty 13 }

        frLpVtCurr15MTimeElaps  OBJECT-TYPE
            SYNTAX  Counter
            ACCESS  read-only
            STATUS  mandatory
            DESCRIPTION
                "LP-REI/REI-V Current 15-MIN Time Elapsed"
            ::= { cFarEndLP-VTCurrEty 14 }

        frLpVtCurrDayValid15M  OBJECT-TYPE
            SYNTAX  Counter
            ACCESS  read-only
            STATUS  mandatory
            DESCRIPTION
                "LP-REI/REI-V Current Day Time Elapsed"
            ::= { cFarEndLP-VTCurrEty 15 }

--
--  Performance LP-REI/REI-V Interval Table
--
        cFarEndLP-VTIntervTab  OBJECT-TYPE
            SYNTAX  SEQUENCE OF  CFarEndLP-VTIntervEty
            ACCESS  not-accessible
            STATUS  mandatory
            DESCRIPTION
                "The LP-REI/REI-V Interval table."
            ::= { perfDisplayTable 26 }

        cFarEndLP-VTIntervEty  OBJECT-TYPE
            SYNTAX  CFarEndLP-VTIntervEty
            ACCESS  not-accessible
            STATUS  mandatory
            DESCRIPTION
                "An entry in the LP-REI/REI-V Interval table."
            INDEX { frLpVtIntervXCUIndex , frLpVtIntervPortIndex ,
                    frLpVtIntervAug1Sts3Index , frLpVtIntervVc3Sts1Index ,
                    frLpVtIntervTU1xVtxIndex , frLpVtIntervNumber }
            ::= { cFarEndLP-VTIntervTab 1 }

        CFarEndLP-VTIntervEty ::= SEQUENCE {
            frLpVtIntervXCUIndex        XcuNum,
            frLpVtIntervPortIndex       PortNum,
            frLpVtIntervAug1Sts3Index   Aug1Sts3Num,
            frLpVtIntervVc3Sts1Index    Vc3Sts1Num,
            frLpVtIntervTU1xVtxIndex    TU1xVtxNum,
            frLpVtIntervNumber          INTEGER (1..96),
            frLpVtIntervEBs             Counter,
            frLpVtIntervBBEs            Counter,
            frLpVtIntervESs             Counter,
            frLpVtIntervBESs            Counter,
            frLpVtIntervSESs            Counter,
            frLpVtIntervUASs            Counter
        }

        frLpVtIntervXCUIndex  OBJECT-TYPE
            SYNTAX  XcuNum
            ACCESS  read-only
            STATUS  mandatory
            DESCRIPTION
                "XCU index"
            ::= { cFarEndLP-VTIntervEty 1 }

        frLpVtIntervPortIndex  OBJECT-TYPE
            SYNTAX  PortNum
            ACCESS  read-only
            STATUS  mandatory
            DESCRIPTION
                "PORT #1~#2"
            ::= { cFarEndLP-VTIntervEty 2 }

        frLpVtIntervAug1Sts3Index  OBJECT-TYPE
            SYNTAX  Aug1Sts3Num
            ACCESS  read-only
            STATUS  mandatory
            DESCRIPTION
                "AUG1/STS3 index"
            ::= { cFarEndLP-VTIntervEty 3 }

        frLpVtIntervVc3Sts1Index  OBJECT-TYPE
            SYNTAX  Vc3Sts1Num
            ACCESS  read-only
            STATUS  mandatory
            DESCRIPTION
                "VC3/STS1 index"
            ::= { cFarEndLP-VTIntervEty 4 }

        frLpVtIntervTU1xVtxIndex  OBJECT-TYPE
            SYNTAX  TU1xVtxNum
            ACCESS  read-only
            STATUS  mandatory
            DESCRIPTION
                "VC1x/VTx index"
            ::= { cFarEndLP-VTIntervEty 5 }

        frLpVtIntervNumber  OBJECT-TYPE
            SYNTAX  INTEGER (1..96)
            ACCESS  read-only
            STATUS  mandatory
            DESCRIPTION
                "A number between 1 and 96"
            ::= { cFarEndLP-VTIntervEty 6 }

        frLpVtIntervEBs  OBJECT-TYPE
            SYNTAX  Counter
            ACCESS  read-only
            STATUS  mandatory
            DESCRIPTION
                "LP-REI/REI-V Error Block"
            ::= { cFarEndLP-VTIntervEty 7 }

        frLpVtIntervBBEs  OBJECT-TYPE
            SYNTAX  Counter
            ACCESS  read-only
            STATUS  mandatory
            DESCRIPTION
                "LP-REI/REI-V Background Block Error"
            ::= { cFarEndLP-VTIntervEty 8 }

        frLpVtIntervESs  OBJECT-TYPE
            SYNTAX  Counter
            ACCESS  read-only
            STATUS  mandatory
            DESCRIPTION
                "LP-REI/REI-V Error Second"
            ::= { cFarEndLP-VTIntervEty 9 }

        frLpVtIntervBESs  OBJECT-TYPE
            SYNTAX  Counter
            ACCESS  read-only
            STATUS  mandatory
            DESCRIPTION
                "LP-REI/REI-V Background Error Second"
            ::= { cFarEndLP-VTIntervEty 10 }

        frLpVtIntervSESs  OBJECT-TYPE
            SYNTAX  Counter
            ACCESS  read-only
            STATUS  mandatory
            DESCRIPTION
                "LP-REI/REI-V Severly Error Second"
            ::= { cFarEndLP-VTIntervEty 11 }

        frLpVtIntervUASs  OBJECT-TYPE
            SYNTAX  Counter
            ACCESS  read-only
            STATUS  mandatory
            DESCRIPTION
                "LP-REI/REI-V Unavailable Second"
            ::= { cFarEndLP-VTIntervEty 12 }

--
--  Performance LP-REI/REI-V 7 Days Table
--
        cFarEndLP-VT7DaysTab  OBJECT-TYPE
            SYNTAX  SEQUENCE OF  CFarEndLP-VT7DaysEty
            ACCESS  not-accessible
            STATUS  mandatory
            DESCRIPTION
                "The LP-REI/REI-V 7 days table."
            ::= { perfDisplayTable 27 }

        cFarEndLP-VT7DaysEty  OBJECT-TYPE
            SYNTAX  CFarEndLP-VT7DaysEty
            ACCESS  not-accessible
            STATUS  mandatory
            DESCRIPTION
                "An entry in the LP-REI/REI-V 7 days table."
            INDEX { frLpVt7DaysXCUIndex , frLpVt7DaysPortIndex ,
                    frLpVt7DaysAug1Sts3Index , frLpVt7DaysVc3Sts1Index ,
                    frLpVt7DaysTU1xVtxIndex , frLpVt7DaysNumber }
            ::= { cFarEndLP-VT7DaysTab 1 }

        CFarEndLP-VT7DaysEty ::= SEQUENCE {
            frLpVt7DaysXCUIndex         XcuNum,
            frLpVt7DaysPortIndex        PortNum,
            frLpVt7DaysAug1Sts3Index    Aug1Sts3Num,
            frLpVt7DaysVc3Sts1Index     Vc3Sts1Num,
            frLpVt7DaysTU1xVtxIndex     TU1xVtxNum,
            frLpVt7DaysNumber           INTEGER (1..7),
            frLpVt7DaysDate             DisplayString (SIZE (0..255)),
            frLpVt7DaysEBs              Counter,
            frLpVt7DaysBBEs             Counter,
            frLpVt7DaysESs              Counter,
            frLpVt7DaysBESs             Counter,
            frLpVt7DaysSESs             Counter,
            frLpVt7DaysUASs             Counter
        }

        frLpVt7DaysXCUIndex  OBJECT-TYPE
            SYNTAX  XcuNum
            ACCESS  read-only
            STATUS  mandatory
            DESCRIPTION
                "XCU index"
            ::= { cFarEndLP-VT7DaysEty 1 }

        frLpVt7DaysPortIndex  OBJECT-TYPE
            SYNTAX  PortNum
            ACCESS  read-only
            STATUS  mandatory
            DESCRIPTION
                "PORT #1~#2"
            ::= { cFarEndLP-VT7DaysEty 2 }

        frLpVt7DaysAug1Sts3Index  OBJECT-TYPE
            SYNTAX  Aug1Sts3Num
            ACCESS  read-only
            STATUS  mandatory
            DESCRIPTION
                "AUG1/STS3 index"
            ::= { cFarEndLP-VT7DaysEty 3 }

        frLpVt7DaysVc3Sts1Index  OBJECT-TYPE
            SYNTAX  Vc3Sts1Num
            ACCESS  read-only
            STATUS  mandatory
            DESCRIPTION
                "VC3/STS1 index"
            ::= { cFarEndLP-VT7DaysEty 4 }

        frLpVt7DaysTU1xVtxIndex  OBJECT-TYPE
            SYNTAX  TU1xVtxNum
            ACCESS  read-only
            STATUS  mandatory
            DESCRIPTION
                "VC1x/Vtx index"
            ::= { cFarEndLP-VT7DaysEty 5 }

        frLpVt7DaysNumber  OBJECT-TYPE
            SYNTAX  INTEGER (1..7)
            ACCESS  read-only
            STATUS  mandatory
            DESCRIPTION
                "A number between 1 and 7"
            ::= { cFarEndLP-VT7DaysEty 6 }

        frLpVt7DaysDate  OBJECT-TYPE
            SYNTAX  DisplayString (SIZE (0..255))
            ACCESS  read-only
            STATUS  mandatory
            DESCRIPTION
                "Date"
            ::= { cFarEndLP-VT7DaysEty 7 }

        frLpVt7DaysEBs  OBJECT-TYPE
            SYNTAX  Counter
            ACCESS  read-only
            STATUS  mandatory
            DESCRIPTION
                "LP-REI/REI-V Error Block"
            ::= { cFarEndLP-VT7DaysEty 8 }

        frLpVt7DaysBBEs  OBJECT-TYPE
            SYNTAX  Counter
            ACCESS  read-only
            STATUS  mandatory
            DESCRIPTION
                "LP-REI/REI-V Background Block Error"
            ::= { cFarEndLP-VT7DaysEty 9 }

        frLpVt7DaysESs  OBJECT-TYPE
            SYNTAX  Counter
            ACCESS  read-only
            STATUS  mandatory
            DESCRIPTION
                "LP-REI/REI-V Error Second"
            ::= { cFarEndLP-VT7DaysEty 10 }

        frLpVt7DaysBESs  OBJECT-TYPE
            SYNTAX  Counter
            ACCESS  read-only
            STATUS  mandatory
            DESCRIPTION
                "LP-REI/REI-V Background Error Second"
            ::= { cFarEndLP-VT7DaysEty 11 }

        frLpVt7DaysSESs  OBJECT-TYPE
            SYNTAX  Counter
            ACCESS  read-only
            STATUS  mandatory
            DESCRIPTION
                "LP-REI/REI-V Severly Error Second"
            ::= { cFarEndLP-VT7DaysEty 12 }

        frLpVt7DaysUASs  OBJECT-TYPE
            SYNTAX  Counter
            ACCESS  read-only
            STATUS  mandatory
            DESCRIPTION
                "LP-REI/REI-V Unavailable Second"
            ::= { cFarEndLP-VT7DaysEty 13 }

--
--  Performance LP-REI/REI-V Total Table
--
        cFarEndLP-VTTotalTab  OBJECT-TYPE
            SYNTAX  SEQUENCE OF  CFarEndLP-VTTotalEty
            ACCESS  not-accessible
            STATUS  mandatory
            DESCRIPTION
                "The LP-REI/REI-V Total table."
            ::= { perfDisplayTable 28 }

        cFarEndLP-VTTotalEty  OBJECT-TYPE
            SYNTAX  CFarEndLP-VTTotalEty
            ACCESS  not-accessible
            STATUS  mandatory
            DESCRIPTION
                "An entry in the LP-REI/REI-V Total table."
            INDEX { frLpVtTotalXCUIndex , frLpVtTotalPortIndex ,
                    frLpVtTotalAug1Sts3Index , frLpVtTotalVc3Sts1Index ,
                    frLpVtTotalTU1xVtxIndex }
            ::= { cFarEndLP-VTTotalTab 1 }

        CFarEndLP-VTTotalEty ::= SEQUENCE {
            frLpVtTotalXCUIndex         XcuNum,
            frLpVtTotalPortIndex        PortNum,
            frLpVtTotalAug1Sts3Index    Aug1Sts3Num,
            frLpVtTotalVc3Sts1Index     Vc3Sts1Num,
            frLpVtTotalTU1xVtxIndex     TU1xVtxNum,
            frLpVtTotalEBs              Counter,
            frLpVtTotalBBEs             Counter,
            frLpVtTotalESs              Counter,
            frLpVtTotalBESs             Counter,
            frLpVtTotalSESs             Counter,
            frLpVtTotalUASs             Counter
        }

        frLpVtTotalXCUIndex  OBJECT-TYPE
            SYNTAX  XcuNum
            ACCESS  read-only
            STATUS  mandatory
            DESCRIPTION
                "XCU index"
            ::= { cFarEndLP-VTTotalEty 1 }

        frLpVtTotalPortIndex  OBJECT-TYPE
            SYNTAX  PortNum
            ACCESS  read-only
            STATUS  mandatory
            DESCRIPTION
                "PORT #1~#2"
            ::= { cFarEndLP-VTTotalEty 2 }

        frLpVtTotalAug1Sts3Index  OBJECT-TYPE
            SYNTAX  Aug1Sts3Num
            ACCESS  read-only
            STATUS  mandatory
            DESCRIPTION
                "AUG1/STS3 index"
            ::= { cFarEndLP-VTTotalEty 3 }

        frLpVtTotalVc3Sts1Index  OBJECT-TYPE
            SYNTAX  Vc3Sts1Num
            ACCESS  read-only
            STATUS  mandatory
            DESCRIPTION
                "VC3/STS1 index"
            ::= { cFarEndLP-VTTotalEty 4 }

        frLpVtTotalTU1xVtxIndex  OBJECT-TYPE
            SYNTAX  TU1xVtxNum
            ACCESS  read-only
            STATUS  mandatory
            DESCRIPTION
                "VC1x/Vtx index"
            ::= { cFarEndLP-VTTotalEty 5 }

        frLpVtTotalEBs  OBJECT-TYPE
            SYNTAX  Counter
            ACCESS  read-only
            STATUS  mandatory
            DESCRIPTION
                "LP-REI/REI-V Error Block"
            ::= { cFarEndLP-VTTotalEty 6 }

        frLpVtTotalBBEs  OBJECT-TYPE
            SYNTAX  Counter
            ACCESS  read-only
            STATUS  mandatory
            DESCRIPTION
                "LP-REI/REI-V Background Block Error"
            ::= { cFarEndLP-VTTotalEty 7 }

        frLpVtTotalESs  OBJECT-TYPE
            SYNTAX  Counter
            ACCESS  read-only
            STATUS  mandatory
            DESCRIPTION
                "LP-REI/REI-V Error Second"
            ::= { cFarEndLP-VTTotalEty 8 }

        frLpVtTotalBESs  OBJECT-TYPE
            SYNTAX  Counter
            ACCESS  read-only
            STATUS  mandatory
            DESCRIPTION
                "LP-REI/REI-V Background Error Second"
            ::= { cFarEndLP-VTTotalEty 9 }

        frLpVtTotalSESs  OBJECT-TYPE
            SYNTAX  Counter
            ACCESS  read-only
            STATUS  mandatory
            DESCRIPTION
                "LP-REI/REI-V Severly Error Second"
            ::= { cFarEndLP-VTTotalEty 10 }

        frLpVtTotalUASs  OBJECT-TYPE
            SYNTAX  Counter
            ACCESS  read-only
            STATUS  mandatory
            DESCRIPTION
                "LP-REI/REI-V Unavailable Second"
            ::= { cFarEndLP-VTTotalEty 11 }

--
--   Line/Section Performance Summary Hex Table
--
        lnSecPerfSummaryHexTab  OBJECT-TYPE
            SYNTAX  SEQUENCE OF  LnSecPerfSummaryHexEty
            ACCESS  not-accessible
            STATUS  mandatory
            DESCRIPTION
                "Line/Section Performance Summary HEX Table "
            ::= { perfDisplayTable 29 }

        lnSecPerfSummaryHexEty OBJECT-TYPE
            SYNTAX  LnSecPerfSummaryHexEty
            ACCESS  not-accessible
            STATUS  mandatory
            DESCRIPTION
                "An entry in the Line/Section Performance summary hex table."
            INDEX { lnSecSummXCUIdx , lnSecSummPortIdx }
            ::= { lnSecPerfSummaryHexTab 1 }

        LnSecPerfSummaryHexEty ::= SEQUENCE  {
            lnSecSummXCUIdx             XcuNum,
            lnSecSummPortIdx            PortNum,
            lnSecSummSummary            OCTET STRING
        }

        lnSecSummXCUIdx  OBJECT-TYPE
            SYNTAX  XcuNum
            ACCESS  read-only
            STATUS  mandatory
            DESCRIPTION
                "xcu index"
            ::= { lnSecPerfSummaryHexEty  1 }

        lnSecSummPortIdx  OBJECT-TYPE
            SYNTAX  PortNum
            ACCESS  read-only
            STATUS  mandatory
            DESCRIPTION
                "port index"
            ::= { lnSecPerfSummaryHexEty  2 }

        lnSecSummSummary  OBJECT-TYPE
            SYNTAX  OCTET STRING(SIZE(40))
            ACCESS  read-only
            STATUS  mandatory
            DESCRIPTION
                "Line/Section Perf Summary"
            ::= { lnSecPerfSummaryHexEty  3 }

--
--   HP/STS Performance Summary Hex Table
--
        hpStsPerfSummaryHexTab  OBJECT-TYPE
            SYNTAX  SEQUENCE OF  HpStsPerfSummaryHexEty
            ACCESS  not-accessible
            STATUS  mandatory
            DESCRIPTION
                "HP/STS Performance Summary HEX Table "
            ::= { perfDisplayTable 30 }

        hpStsPerfSummaryHexEty OBJECT-TYPE
            SYNTAX  HpStsPerfSummaryHexEty
            ACCESS  not-accessible
            STATUS  mandatory
            DESCRIPTION
                "An entry in the HP/STS Performance summary hex table."
            INDEX { hpStsSummXCUIdx , hpStsSummPortIdx , hpStsSummAug1Sts3Idx }
            ::= { hpStsPerfSummaryHexTab 1 }

        HpStsPerfSummaryHexEty ::= SEQUENCE  {
            hpStsSummXCUIdx             XcuNum,
            hpStsSummPortIdx            PortNum,
            hpStsSummAug1Sts3Idx        Aug1Sts3Num,
            hpStsSummSummary            OCTET STRING
        }

        hpStsSummXCUIdx  OBJECT-TYPE
            SYNTAX  XcuNum
            ACCESS  read-only
            STATUS  mandatory
            DESCRIPTION
                "xcu index"
            ::= { hpStsPerfSummaryHexEty  1 }

        hpStsSummPortIdx  OBJECT-TYPE
            SYNTAX  PortNum
            ACCESS  read-only
            STATUS  mandatory
            DESCRIPTION
                "port index"
            ::= { hpStsPerfSummaryHexEty  2 }

        hpStsSummAug1Sts3Idx  OBJECT-TYPE
            SYNTAX  Aug1Sts3Num
            ACCESS  read-only
            STATUS  mandatory
            DESCRIPTION
                "AUG1/STS3 index"
            ::= { hpStsPerfSummaryHexEty  3 }

        hpStsSummSummary  OBJECT-TYPE
            SYNTAX  OCTET STRING(SIZE(79))
            ACCESS  read-only
            STATUS  mandatory
            DESCRIPTION
                "HP/STS Perf Summary"
            ::= { hpStsPerfSummaryHexEty  4 }

--
--   LP/VT Performance Summary Hex Table
--
        lpVtPerfSummaryHexTab  OBJECT-TYPE
            SYNTAX  SEQUENCE OF  LpVtPerfSummaryHexEty
            ACCESS  not-accessible
            STATUS  mandatory
            DESCRIPTION
                "LP/VT Performance Summary HEX Table "
            ::= { perfDisplayTable 31 }

        lpVtPerfSummaryHexEty OBJECT-TYPE
            SYNTAX  LpVtPerfSummaryHexEty
            ACCESS  not-accessible
            STATUS  mandatory
            DESCRIPTION
                "An entry in the LP/VT Performance summary hex table."
            INDEX { lpVtSummXCUIdx , lpVtSummPortIdx , lpVtSummAug1Sts3Idx , lpVtSummVc3Sts1Idx }
            ::= { lpVtPerfSummaryHexTab 1 }

        LpVtPerfSummaryHexEty ::= SEQUENCE  {
            lpVtSummXCUIdx              XcuNum,
            lpVtSummPortIdx             PortNum,
            lpVtSummAug1Sts3Idx         Aug1Sts3Num,
            lpVtSummVc3Sts1Idx          Vc3Sts1Num,
            lpVtSummSummary             OCTET STRING
        }

        lpVtSummXCUIdx  OBJECT-TYPE
            SYNTAX  XcuNum
            ACCESS  read-only
            STATUS  mandatory
            DESCRIPTION
                "xcu index"
            ::= { lpVtPerfSummaryHexEty  1 }

        lpVtSummPortIdx  OBJECT-TYPE
            SYNTAX  PortNum
            ACCESS  read-only
            STATUS  mandatory
            DESCRIPTION
                "port index"
            ::= { lpVtPerfSummaryHexEty  2 }

        lpVtSummAug1Sts3Idx  OBJECT-TYPE
            SYNTAX  Aug1Sts3Num
            ACCESS  read-only
            STATUS  mandatory
            DESCRIPTION
                "AUG1/STS3 index"
            ::= { lpVtPerfSummaryHexEty  3 }

        lpVtSummVc3Sts1Idx  OBJECT-TYPE
            SYNTAX  Vc3Sts1Num
            ACCESS  read-only
            STATUS  mandatory
            DESCRIPTION
                "VC3/STS1 index"
            ::= { lpVtPerfSummaryHexEty  4 }

        lpVtSummSummary  OBJECT-TYPE
            SYNTAX  OCTET STRING(SIZE(729))
            ACCESS  read-only
            STATUS  mandatory
            DESCRIPTION
                "LP/VT Perf Summary"
            ::= { lpVtPerfSummaryHexEty  5 }

--
--   System Log Table
--
        systemLogTable  OBJECT-TYPE
            SYNTAX  SEQUENCE OF SystemLogEntry
            ACCESS  not-accessible
            STATUS  mandatory
            DESCRIPTION
                "System Log Table"
            ::= { system 32 }

        systemLogEntry  OBJECT-TYPE
            SYNTAX  SystemLogEntry
            ACCESS  not-accessible
            STATUS  mandatory
            DESCRIPTION
                "System Log entry"
            INDEX { systemLogIndex }
            ::= { systemLogTable 1 }

        SystemLogEntry ::= SEQUENCE {
            systemLogIndex              INTEGER (1..500),
            systemLogTimeStamp          DisplayString (SIZE(0..255)),
            systemLogMessage            DisplayString (SIZE(0..255))
        }

        systemLogIndex  OBJECT-TYPE
            SYNTAX  INTEGER (1..500)
            ACCESS  read-only
            STATUS  mandatory
            DESCRIPTION
                "System Log index"
            ::= { systemLogEntry 1 }

        systemLogTimeStamp  OBJECT-TYPE
            SYNTAX  DisplayString (SIZE(0..255))
            ACCESS  read-only
            STATUS  mandatory
            DESCRIPTION
                "System Log Time"
            ::= { systemLogEntry 2 }

        systemLogMessage  OBJECT-TYPE
            SYNTAX  DisplayString (SIZE(0..255))
            ACCESS  read-only
            STATUS  mandatory
            DESCRIPTION
                "System Log message"
            ::= { systemLogEntry 3 }

--
--  xcuInfomationTable      OBJECT IDENTIFIER  ::= { system 33 }
--
        xcuInfomationTable  OBJECT-TYPE
            SYNTAX  SEQUENCE OF XcuInfomationEntry
            ACCESS  not-accessible
            STATUS  mandatory
            DESCRIPTION
                "xcu information table"
            ::= { system 33 }

        xcuInfomationEntry  OBJECT-TYPE
            SYNTAX  XcuInfomationEntry
            ACCESS  not-accessible
            STATUS  mandatory
            DESCRIPTION
                "xcu information entry"
            INDEX { xcuInfoIndex }
            ::= { xcuInfomationTable 1 }

        XcuInfomationEntry ::= SEQUENCE {
            xcuInfoIndex                INTEGER,
            xcuInfoEquip                INTEGER,
            xcuInfoConnector            INTEGER,
            xcuInfoTransceiver          DisplayString,
            xcuInfoLinkLength           DisplayString,
            xcuInfoTechnology           DisplayString,
            xcuInfoEncoding             DisplayString,
            xcuInfoLen-9-125-um         DisplayString,
            xcuInfoLen-50-125-um        DisplayString,
            xcuInfoLen-62p5-125-um      DisplayString,
            xcuInfoLen-copper           DisplayString,
            xcuInfoTemperature          DisplayString,
            xcuInfoVcc                  DisplayString,
            xcuInfoTxBias               DisplayString,
            xcuInfoTxPower              DisplayString,
            xcuInfoRxPower              DisplayString,
            xcuInfoDateCode             DisplayString,
            xcuInfoVendorName           DisplayString,
            xcuInfoVendorOUI            DisplayString,
            xcuInfoVendorPN             DisplayString,
            xcuInfoVendorRev            DisplayString,
            xcuInfoWaveLength           DisplayString
        }

        xcuInfoIndex  OBJECT-TYPE
            SYNTAX  INTEGER {
                    xcu1-w-port1(1),
                    xcu1-w-port2(2),
                    xcu2-e-port1(3),
                    xcu2-e-port2(4)
                }
            ACCESS  read-only
            STATUS  mandatory
            DESCRIPTION
                "xcu and port number"
            ::= { xcuInfomationEntry 1 }

        xcuInfoEquip  OBJECT-TYPE
            SYNTAX  INTEGER {
                    unequipped(1),
                    equipped(2)
                }
            ACCESS  read-only
            STATUS  mandatory
            DESCRIPTION
                "xcu port equip or not"
            ::= { xcuInfomationEntry 2 }

        xcuInfoConnector  OBJECT-TYPE
            SYNTAX  INTEGER {
                    not-available(1),
                    sc(2),
                    fibre-channel-style-1-copper(3),
                    fibre-hannel-style-2-copper(4),
                    bnc-tnc(5),
                    fibre-channel-coaxial-header(6),
                    fiberJack(7),
                    lc(8),
                    mt-rj(9),
                    mu(10),
                    sg(11),
                    optcal-pigtail(12),
                    hssdc-ii(13),
                    copper-pigtail(14)
                }
            ACCESS  read-only
            STATUS  mandatory
            DESCRIPTION
                "xcu port connector"
            ::= { xcuInfomationEntry 3 }


        xcuInfoTransceiver  OBJECT-TYPE
            SYNTAX  DisplayString (SIZE (0..255) )
            ACCESS  read-only
            STATUS  mandatory
            DESCRIPTION
                "xcu port transceiver"
            ::= { xcuInfomationEntry 4 }

        xcuInfoLinkLength  OBJECT-TYPE
            SYNTAX  DisplayString (SIZE (0..255) )
            ACCESS  read-only
            STATUS  mandatory
            DESCRIPTION
                "xcu port link length"
            ::= { xcuInfomationEntry 5 }

        xcuInfoTechnology  OBJECT-TYPE
            SYNTAX  DisplayString (SIZE (0..255) )
            ACCESS  read-only
            STATUS  mandatory
            DESCRIPTION
                "xcu port technology"
            ::= { xcuInfomationEntry 6 }

        xcuInfoEncoding  OBJECT-TYPE
            SYNTAX  DisplayString (SIZE (0..255) )
            ACCESS  read-only
            STATUS  mandatory
            DESCRIPTION
                "xcu port encoding"
            ::= { xcuInfomationEntry 7 }

        xcuInfoLen-9-125-um  OBJECT-TYPE
            SYNTAX  DisplayString (SIZE (0..255) )
            ACCESS  read-only
            STATUS  mandatory
            DESCRIPTION
                "xcu port length for 9/125 um fiber"
            ::= { xcuInfomationEntry 8 }

        xcuInfoLen-50-125-um  OBJECT-TYPE
            SYNTAX  DisplayString (SIZE (0..255) )
            ACCESS  read-only
            STATUS  mandatory
            DESCRIPTION
                "xcu port length for 50/125 um fiber"
            ::= { xcuInfomationEntry 9 }

        xcuInfoLen-62p5-125-um  OBJECT-TYPE
            SYNTAX  DisplayString (SIZE (0..255) )
            ACCESS  read-only
            STATUS  mandatory
            DESCRIPTION
                "xcu port length for 62.5/125 um fiber"
            ::= { xcuInfomationEntry 10 }

        xcuInfoLen-copper  OBJECT-TYPE
            SYNTAX  DisplayString (SIZE (0..255) )
            ACCESS  read-only
            STATUS  mandatory
            DESCRIPTION
                "xcu port length for copper"
            ::= { xcuInfomationEntry 11 }

        xcuInfoTemperature  OBJECT-TYPE
            SYNTAX  DisplayString (SIZE (0..255) )
            ACCESS  read-only
            STATUS  mandatory
            DESCRIPTION
                "xcu port Temperature"
            ::= { xcuInfomationEntry 12 }

        xcuInfoVcc  OBJECT-TYPE
            SYNTAX  DisplayString (SIZE (0..255) )
            ACCESS  read-only
            STATUS  mandatory
            DESCRIPTION
                "xcu port Vcc"
            ::= { xcuInfomationEntry 13 }

        xcuInfoTxBias  OBJECT-TYPE
            SYNTAX  DisplayString (SIZE (0..255) )
            ACCESS  read-only
            STATUS  mandatory
            DESCRIPTION
                "xcu port Tx Bias current"
            ::= { xcuInfomationEntry 14 }

        xcuInfoTxPower  OBJECT-TYPE
            SYNTAX  DisplayString (SIZE (0..255) )
            ACCESS  read-only
            STATUS  mandatory
            DESCRIPTION
                "xcu port Tx power"
            ::= { xcuInfomationEntry 15 }

        xcuInfoRxPower  OBJECT-TYPE
            SYNTAX  DisplayString (SIZE (0..255) )
            ACCESS  read-only
            STATUS  mandatory
            DESCRIPTION
                "xcu port Rx power"
            ::= { xcuInfomationEntry 16 }

        xcuInfoDateCode  OBJECT-TYPE
            SYNTAX  DisplayString (SIZE (0..16) )
            ACCESS  read-only
            STATUS  mandatory
            DESCRIPTION
                "xcu port date code "
            ::= { xcuInfomationEntry 17 }

        xcuInfoVendorName  OBJECT-TYPE
            SYNTAX  DisplayString (SIZE (0..16) )
            ACCESS  read-only
            STATUS  mandatory
            DESCRIPTION
                "xcu port vendor name "
            ::= { xcuInfomationEntry 18 }

        xcuInfoVendorOUI  OBJECT-TYPE
            SYNTAX  DisplayString (SIZE (0..4) )
            ACCESS  read-only
            STATUS  mandatory
            DESCRIPTION
                "xcu port vendor OUI "
            ::= { xcuInfomationEntry 19 }

        xcuInfoVendorPN  OBJECT-TYPE
            SYNTAX  DisplayString (SIZE (0..16) )
            ACCESS  read-only
            STATUS  mandatory
            DESCRIPTION
                "xcu port vendor pn "
            ::= { xcuInfomationEntry 20 }

        xcuInfoVendorRev  OBJECT-TYPE
            SYNTAX  DisplayString (SIZE (0..4) )
            ACCESS  read-only
            STATUS  mandatory
            DESCRIPTION
                "xcu port vendor rev "
            ::= { xcuInfomationEntry 21 }

        xcuInfoWaveLength  OBJECT-TYPE
            SYNTAX  DisplayString (SIZE (0..2) )
            ACCESS  read-only
            STATUS  mandatory
            DESCRIPTION
                "xcu port wave length "
            ::= { xcuInfomationEntry 22 }


--
--   dccChannelTable
--
    dccChannelTable         OBJECT IDENTIFIER  ::= { system 34 }

        xcu1dcc1Channel  OBJECT-TYPE
            SYNTAX  INTEGER {
                    d1-d3(1),
                    d4-d12(2),
                    d1-d12(3),
--                                              section-3ch(1),
--                      line-9ch(2),
--                                              composite-12ch(3),
                    off(4)
                }
            ACCESS  read-write
            STATUS  mandatory
            DESCRIPTION
                "XCU1 dcc1(port1) channels"
            ::= { dccChannelTable 1 }

        xcu1dcc2Channel  OBJECT-TYPE
            SYNTAX  INTEGER {
                    d1-d3(1),
                    d4-d12(2),
                    d1-d12(3),
                    off(4)
                }
            ACCESS  read-write
            STATUS  mandatory
            DESCRIPTION
                "XCU1 dcc2 channels"
            ::= { dccChannelTable 2 }


        xcu2dcc1Channel  OBJECT-TYPE
            SYNTAX  INTEGER {
                    d1-d3(1),
                    d4-d12(2),
                    d1-d12(3),
                    off(4)
                }
            ACCESS  read-write
            STATUS  mandatory
            DESCRIPTION
                "XCU2 dcc1(port1) channels"
            ::= { dccChannelTable 4 }

        xcu2dcc2Channel  OBJECT-TYPE
            SYNTAX  INTEGER {
                    d1-d3(1),
                    d4-d12(2),
                    d1-d12(3),
                    off(4)
                }
            ACCESS  read-write
            STATUS  mandatory
            DESCRIPTION
                "XCU2 dcc2 channels"
            ::= { dccChannelTable 5 }


--
--  Trap Enable Table
--
    trapEnableTable         OBJECT IDENTIFIER ::= { system 35 }

        alarmTrapEnable   OBJECT-TYPE
            SYNTAX  INTEGER {
                    disable(1),
                    enable(2)
                }
            ACCESS  read-write
            STATUS  mandatory
            DESCRIPTION
                "alarm trap enable/disable"
            ::= { trapEnableTable 1 }

        ledTrapEnable   OBJECT-TYPE
            SYNTAX  INTEGER {
                    disable(1),
                    enable(2)
                }
            ACCESS  read-write
            STATUS  mandatory
            DESCRIPTION
                "led trap enable/disable"
            ::= { trapEnableTable 2 }

        severityChangeTrapEnable   OBJECT-TYPE
            SYNTAX  INTEGER {
                    disable(1),
                    enable(2)
                }
            ACCESS  read-write
            STATUS  mandatory
            DESCRIPTION
                "Severity change trap enable/disable"
            ::= { trapEnableTable 3 }

        trapCompWindow   OBJECT-TYPE
            SYNTAX  INTEGER (0..15)
            ACCESS  read-write
            STATUS  mandatory
            DESCRIPTION
                "trap compress window: 0=disable, or 1~15 min"
            ::= { trapEnableTable 4 }

        trapDelay    OBJECT-TYPE
            SYNTAX  INTEGER (0..60)
            ACCESS  read-write
            STATUS  mandatory
            DESCRIPTION
                "trap delay: 0=disable, or 1~60 seconds"
            ::= { trapEnableTable 5 }



--
--  LED Hand-waving Table
--
    handWavingLedTable         OBJECT IDENTIFIER ::= { system 36 }

        handWavingCommand   OBJECT-TYPE
            SYNTAX  INTEGER {
                    stop(1),
                    start(2)
                }
            ACCESS  read-write
            STATUS  mandatory
            DESCRIPTION
                "hand-waving LED flash stop/start"
            ::= { handWavingLedTable 1 }

        handWavingTimer   OBJECT-TYPE
            SYNTAX  INTEGER(0..99999)
            ACCESS  read-write
            STATUS  mandatory
            DESCRIPTION
                "hand-waving LED flash timer"
            ::= { handWavingLedTable 2 }

--
--  XCU SNCP/UPSR APS Table
--
        xcuSncpApsTab  OBJECT-TYPE
            SYNTAX  SEQUENCE OF  XcuSncpApsEty
            ACCESS  not-accessible
            STATUS  mandatory
            DESCRIPTION
                "XCU SNCP/UPSR APS table "
            ::= { system 37 }

        xcuSncpApsEty  OBJECT-TYPE
            SYNTAX  XcuSncpApsEty
            ACCESS  not-accessible
            STATUS  mandatory
            DESCRIPTION
                "XCU SNCP/UPSR APS entry"
            INDEX { xcuSncpXCUIdx ,
                    xcuSncpPort , xcuSncpAug1Sts3 ,
                    xcuSncpVc3Sts1 , xcuSncpTU1xVtx }
            ::= { xcuSncpApsTab 1 }

        XcuSncpApsEty ::= SEQUENCE {
            xcuSncpXCUIdx               XcuNum,
            xcuSncpPort                 PortID,
            xcuSncpAug1Sts3             Aug1Sts3Num,
            xcuSncpVc3Sts1              Vc3Sts1Num,
            xcuSncpTU1xVtx              TU1xVtxNum,
            xcuSncpCurrentPathSlot      XcSlot,
            xcuSncpCurrentPathPort      PortID,
            xcuSncpPrimaryPathSlot      XcSlot,
            xcuSncpPrimaryPathPort      PortID,
            xcuSncpPPType               XcType,
            xcuSncpCmd                  SncpUserCmd
        }

        xcuSncpXCUIdx  OBJECT-TYPE
            SYNTAX  XcuNum
            ACCESS  read-only
            STATUS  mandatory
            DESCRIPTION
                "XCU index"
            ::= { xcuSncpApsEty 1 }

        xcuSncpPort  OBJECT-TYPE
            SYNTAX  PortID
            ACCESS  read-only
            STATUS  mandatory
            DESCRIPTION
                "PORT #1~#2"
            ::= { xcuSncpApsEty 2 }

        xcuSncpAug1Sts3  OBJECT-TYPE
            SYNTAX  Aug1Sts3Num
            ACCESS  read-only
            STATUS  mandatory
            DESCRIPTION
                "AUG1/STS3 index"
            ::= { xcuSncpApsEty 3 }

        xcuSncpVc3Sts1  OBJECT-TYPE
            SYNTAX  Vc3Sts1Num
            ACCESS  read-only
            STATUS  mandatory
            DESCRIPTION
                "VC3/STS1 index"
            ::= { xcuSncpApsEty 4 }

        xcuSncpTU1xVtx  OBJECT-TYPE
            SYNTAX  TU1xVtxNum
            ACCESS  read-only
            STATUS  mandatory
            DESCRIPTION
                "VC1x/VTx index"
            ::= { xcuSncpApsEty 5 }

        xcuSncpCurrentPathSlot  OBJECT-TYPE
            SYNTAX  XcSlot
            ACCESS  read-only
            STATUS  mandatory
            DESCRIPTION
                "SNCP/UPSR current path"
            ::= { xcuSncpApsEty 6 }

        xcuSncpCurrentPathPort  OBJECT-TYPE
            SYNTAX  PortID
            ACCESS  read-only
            STATUS  mandatory
            DESCRIPTION
                "SNCP/UPSR current path"
            ::= { xcuSncpApsEty 7 }

        xcuSncpPrimaryPathSlot  OBJECT-TYPE
            SYNTAX  XcSlot
            ACCESS  read-only
            STATUS  mandatory
            DESCRIPTION
                "SNCP/UPSR primary path"
            ::= { xcuSncpApsEty 8 }

        xcuSncpPrimaryPathPort  OBJECT-TYPE
            SYNTAX  PortID
            ACCESS  read-only
            STATUS  mandatory
            DESCRIPTION
                "SNCP/UPSR primary path"
            ::= { xcuSncpApsEty 9 }

        xcuSncpPPType  OBJECT-TYPE
            SYNTAX  XcType
            ACCESS  read-only
            STATUS  mandatory
            DESCRIPTION
                "SNCP/UPSR path protection type"
            ::= { xcuSncpApsEty 10 }

        xcuSncpCmd  OBJECT-TYPE
            SYNTAX  SncpUserCmd
            ACCESS  read-write
            STATUS  mandatory
            DESCRIPTION
                "SNCP/UPSR APS command"
            ::= { xcuSncpApsEty 11 }

--
--  XCU MSP Aps Table
--
        xcuMspApsTab  OBJECT-TYPE
            SYNTAX  SEQUENCE OF  XcuMspApsEty
            ACCESS  not-accessible
            STATUS  mandatory
            DESCRIPTION
                "XCU MSP APS table"
            ::= { system 38 }

        xcuMspApsEty  OBJECT-TYPE
            SYNTAX  XcuMspApsEty
            ACCESS  not-accessible
            STATUS  mandatory
            DESCRIPTION
                "An entry in the XCU MSP APS table."
            INDEX { xcuMspApsGroup }
            ::= { xcuMspApsTab 1 }


        XcuMspApsEty ::= SEQUENCE  {
            xcuMspApsGroup              INTEGER,
            xcuMspApsActivePath         INTEGER,
            xcuMspApsCmd                INTEGER
        }

        xcuMspApsGroup  OBJECT-TYPE
            SYNTAX  INTEGER {
                    group-1(1),
                    group-2(2)
                }
            ACCESS  read-only
            STATUS  mandatory
            DESCRIPTION
                "GROUP #1~#2"
            ::= { xcuMspApsEty 1 }

        xcuMspApsActivePath  OBJECT-TYPE
            SYNTAX  INTEGER {
                    xcu1-w(1),
                    xcu2-e(2),
                    port-1(3),
                    port-2(4),
                    not-available(100)
                }
            ACCESS  read-only
            STATUS  mandatory
            DESCRIPTION
                "MSP active path"
            ::= { xcuMspApsEty 2 }

        xcuMspApsCmd  OBJECT-TYPE
            SYNTAX  INTEGER {
                    clear(1),
                    lockout-of-protection(2),
                    fs-to-primary(3),
                    fs-to-secondary(4),
                    ms-to-primary(5),
                    ms-to-secondary(6),
                    not-available(100)
                }
            ACCESS  read-write
            STATUS  mandatory
            DESCRIPTION
                "MSP APS command"
            ::= { xcuMspApsEty 3 }

--
--  XCU Customer Information Table
--
        xcuCustomerInfoTab  OBJECT-TYPE
            SYNTAX  SEQUENCE OF  XcuCustomerInfoEty
            ACCESS  not-accessible
            STATUS  mandatory
            DESCRIPTION
                "XCU Customer Information Table"
            ::= { system 39 }

        xcuCustomerInfoEty OBJECT-TYPE
            SYNTAX  XcuCustomerInfoEty
            ACCESS  not-accessible
            STATUS  mandatory
            DESCRIPTION
                "An entry in the XCU Custimer information table."
            INDEX { xcuCusInfoXcuIndex , xcuCusInfoPortIndex }
            ::= { xcuCustomerInfoTab 1 }

        XcuCustomerInfoEty ::= SEQUENCE  {
            xcuCusInfoXcuIndex          XcuNum,
            xcuCusInfoPortIndex         PortNum,
            xcuCusInfoString            DisplayString (SIZE (1..60))
        }

        xcuCusInfoXcuIndex  OBJECT-TYPE
            SYNTAX  XcuNum
            ACCESS  read-only
            STATUS  mandatory
            DESCRIPTION
                "XCU index"
            ::= { xcuCustomerInfoEty 1 }

        xcuCusInfoPortIndex  OBJECT-TYPE
            SYNTAX  PortNum
            ACCESS  read-only
            STATUS  mandatory
            DESCRIPTION
                "port index"
            ::= { xcuCustomerInfoEty 2 }

        xcuCusInfoString  OBJECT-TYPE
            SYNTAX  DisplayString (SIZE (1..60))
            ACCESS  read-write
            STATUS  mandatory
            DESCRIPTION
                "Customer Information String"
            ::= { xcuCustomerInfoEty 3 }

--
--  File Transfer Table
--
    fileTransferTable     OBJECT IDENTIFIER ::= { system 40 }

        tftpServerIP  OBJECT-TYPE
            SYNTAX  IpAddress
            ACCESS  read-write
            STATUS  mandatory
            DESCRIPTION
                " TFTP Server IP "
            ::= { fileTransferTable 1 }

        tftpFileName  OBJECT-TYPE
            SYNTAX  DisplayString (SIZE (1..56) )
            ACCESS  read-write
            STATUS  mandatory
            DESCRIPTION
                " TFTP file name "
            ::= { fileTransferTable 2 }

        fileTransferType  OBJECT-TYPE
            SYNTAX  INTEGER {
                    firmware-download(1),
                    current-config-download(2),
                    current-config-upload(3),
                    backup-config-download(4),
                    backup-config-upload(5),
                    uploadUnitFAEpackage(8),
                    uploadFAEpackage(9),
                    none(10),
                    download-b155-622-card(11),
                    download-e1t1-card(12),
                    download-e3t3-card(13),
                    download-enet-card(14),
                    download-7fom-card(15),
                    --downloadGeEosFW(16),
                    --downloadGeEosFPGA(17),
                    --downloadB2G5Card(20),
                    downloadGe8eos622Card(21),
                    downloadGe8eos622FPGA(22),
                    --downloadGe8eos2g5Card(23),
                    --downloadGe8eos2g5FPGA(24),

                    download-RTB-config(116),

                    upload-RTB-startup-config(126),
                    upload-RTB-working-config(127),

                    download-QE1-card(181),
                    download-GSHDSL-card(183),
                    download-DTEA-card(185),
                    download-8X50-card(188),
                    download-Conference-card(189),
                    download-3E1-card(190),
                    download-TDMoE-card(191),
                    download-8DBRA-card(194),
                    download-8UDTE-card(195),
                    download-RTB-firmware(200),
                    download-FXS-firmware(213),
                    download-FXO-firmware(214),
--                        download-MAG-firmware(215),
                    download-EM-firmware(216),
                    download-EM-FPGA(217),
                    download-FXO-FPGA(219),
                    download-RS232A-card(230),
                    download-TTA-firmware(231),
                    download-TTA-FPGA(232),
                    download-6UDTEA-card(233),
                    download-6CDA-firmware(234),
                    download-6CDA-FPGA(235)
                }
            ACCESS  read-write
            STATUS  mandatory
            DESCRIPTION
                " file transfer type "
            ::= { fileTransferTable 3 }

        fileTransferAction  OBJECT-TYPE
            SYNTAX  INTEGER {
                    start(1),
                    none(2)
                }
            ACCESS  read-write
            STATUS  mandatory
            DESCRIPTION
                " file transfer action "
            ::= { fileTransferTable 4 }

        fileTransferPercent  OBJECT-TYPE
            SYNTAX  DisplayString (SIZE (0..31) )
            ACCESS  read-only
            STATUS  mandatory
            DESCRIPTION
                " file transfer percentage "
            ::= { fileTransferTable 5 }

        fileTransferErrorCode  OBJECT-TYPE
            SYNTAX  INTEGER {
                    ok(1),
                    checksum-error(2),
                    timeout(3),
                    unknown-tftp-error(4),
                    file-not-found(5),
                    file-already-exists(6),
                    fail-to-read-flash(7),
                    fail-to-program-flash(8),
                    unmatch-firmware(9),
                    unmatch-config(10),
                    activating-current-config(11),
                    copy-to-redundant-fail(12),
                    send-firmware-to-card-fail(13),
                    in-prepare-config-data(16),
                    in-transmit(17),
                    in-send-to-card(18),
                    in-write-flash(19),
                    none(20),
                    prepare-config-data-fail(21),
                    -- 2012-11-12 add entry-22 below by Rukka
                    in-copy-to-redundant-card(22),
                    other(99)
                }
            ACCESS  read-only
            STATUS  mandatory
            DESCRIPTION
                " file transfer error code "
            ::= { fileTransferTable 6 }

        fileTransferUnit  OBJECT-TYPE
            SYNTAX  RealUnitID
            ACCESS  read-write
            STATUS  mandatory
            DESCRIPTION
                " file transfer unit selection "
            ::= { fileTransferTable 7 }

        tftpIPv6Server  OBJECT-TYPE
            SYNTAX  DisplayString (SIZE(2..40))
            ACCESS  read-write
            STATUS  mandatory
            DESCRIPTION
                "TFTP IPv6 server"
            ::= { fileTransferTable 8 }


--
-- T3 M13 Enable Table
--
        t3M13EnableTab  OBJECT-TYPE
            SYNTAX  SEQUENCE OF T3M13EnableEty
            ACCESS  not-accessible
            STATUS  mandatory
            DESCRIPTION
                "M13 Enable table"
            ::= { system 41 }

        t3M13EnableEty  OBJECT-TYPE
            SYNTAX  T3M13EnableEty
            ACCESS  not-accessible
            STATUS  mandatory
            DESCRIPTION
                "An entry in the M13 enable table"
            INDEX { t3M13EnableUnit }
            ::= { t3M13EnableTab 1 }

        T3M13EnableEty ::= SEQUENCE {
            t3M13EnableUnit             UnitID,
            t3M13EnableSerialNumber     INTEGER,
            t3M13EnableM13Function      INTEGER,
            t3M13EnableActKey           DisplayString (SIZE(0..12))
        }

        t3M13EnableUnit  OBJECT-TYPE
            SYNTAX  UnitID
            ACCESS  read-only
            STATUS  mandatory
            DESCRIPTION
            "unit 1 to 4."
            ::= { t3M13EnableEty 1 }

        t3M13EnableSerialNumber  OBJECT-TYPE
            SYNTAX  INTEGER
            ACCESS  read-only
            STATUS  mandatory
            DESCRIPTION
                "Unit Serial Number"
            ::= { t3M13EnableEty 2 }

        t3M13EnableM13Function  OBJECT-TYPE
            SYNTAX  INTEGER {
                    disable(1),
                    enable(2)
                }
            ACCESS  read-write
            STATUS  mandatory
            DESCRIPTION
                "T3 M13 Enable/Disable"
            ::= { t3M13EnableEty 3 }

        t3M13EnableActKey  OBJECT-TYPE
            SYNTAX  DisplayString (SIZE(0..12))
            ACCESS  read-write
            STATUS  mandatory
            DESCRIPTION
                "T3 M13 Activation Key"
            ::= { t3M13EnableEty 4 }
-- 2011-3-17 elvis add below
--
-- New System Mode Table
--
    new-systemModeTable   OBJECT IDENTIFIER ::= { system 42 }

        new-sysSdhSonetMode   OBJECT-TYPE
            SYNTAX  INTEGER {
                    sdh(1),
                    sonet(2)
                }
            ACCESS  read-write
            STATUS  mandatory
            DESCRIPTION
                "SDH/Sonet Mode."
            ::= { new-systemModeTable 1 }

        new-sysProtectGroup1Mode    OBJECT-TYPE
            SYNTAX  INTEGER {
                    msp-1plus1(1),
                    np(2)
--        mssp(3)
                }
            ACCESS  read-write
            STATUS  mandatory
            DESCRIPTION
                "Group 1 Application Mode."
            ::= { new-systemModeTable 2 }

        new-sysProtectGroup2Mode    OBJECT-TYPE
            SYNTAX  INTEGER {
                    msp-1plus1(1),
                    np(2)
--        mssp(3)
                }
            ACCESS  read-write
            STATUS  mandatory
            DESCRIPTION
                "Group 2 Application Mode."
            ::= { new-systemModeTable 3 }

        new-sysXcu1Port1Rate    OBJECT-TYPE
            SYNTAX  INTEGER {
                    stm1-oc3(1),
                    stm4-oc12(2),
                    stm16-oc48(3)
                }
            ACCESS  read-write
            STATUS  mandatory
            DESCRIPTION
                "XCU1(W) port 1 rate."
            ::= { new-systemModeTable 4 }

        new-sysXcu1Port2Rate    OBJECT-TYPE
            SYNTAX  INTEGER {
                    stm1-oc3(1),
                    stm4-oc12(2),
                    stm16-oc48(3)
                }
            ACCESS  read-write
            STATUS  mandatory
            DESCRIPTION
                "XCU1(W) port 2 rate."
            ::= { new-systemModeTable 5 }

        new-sysXcu2Port1Rate    OBJECT-TYPE
            SYNTAX  INTEGER {
                    stm1-oc3(1),
                    stm4-oc12(2),
                    stm16-oc48(3)
                }
            ACCESS  read-write
            STATUS  mandatory
            DESCRIPTION
                "XCU2(E) port 1 rate."
            ::= { new-systemModeTable 6 }

        new-sysXcu2Port2Rate    OBJECT-TYPE
            SYNTAX  INTEGER {
                    stm1-oc3(1),
                    stm4-oc12(2),
                    stm16-oc48(3)
                }
            ACCESS  read-write
            STATUS  mandatory
            DESCRIPTION
                "XCU2(E) port 2 rate."
            ::= { new-systemModeTable 7 }

        new-sysTpsg1Protection    OBJECT-TYPE
            SYNTAX  INTEGER {
                    off(1),
                    on(2)
                }
            ACCESS  read-only
            STATUS  mandatory
            DESCRIPTION
                "TPSG1 protection enable/disable."
            ::= { new-systemModeTable 8 }

        new-sysTpsg2Protection    OBJECT-TYPE
            SYNTAX  INTEGER {
                    off(1),
                    on(2)
                }
            ACCESS  read-only
            STATUS  mandatory
            DESCRIPTION
                "TPSG2 protection enable/disable."
            ::= { new-systemModeTable 9 }
        new-sysMspWtrTimer    OBJECT-TYPE
            SYNTAX  INTEGER (3..900)
            ACCESS  read-write
            STATUS  mandatory
            DESCRIPTION
                "MSP 1+1 WTR Timer."
            ::= { new-systemModeTable 12 }

        new-sysGroupingMode   OBJECT-TYPE
            SYNTAX  INTEGER {
                    horizontal(1),
                    vertical(2)
                }
            ACCESS  read-write
            STATUS  mandatory
            DESCRIPTION
                "System Grouping Mode."
            ::= { new-systemModeTable 13 }

        new-sysSncpMode   OBJECT-TYPE
            SYNTAX  INTEGER {
                    intrusive(1),
                    non-intrusive(2)
                }
            ACCESS  read-write
            STATUS  mandatory
            DESCRIPTION
                "SNCP/UPSR Mode."
            ::= { new-systemModeTable 14 }

        new-sysIdlePathAlarmInsert  OBJECT-TYPE
            SYNTAX  INTEGER {
                    ais(1),
                    uneq(2)
                }
            ACCESS  read-write
            STATUS  mandatory
            DESCRIPTION
                "Alarm inserted for idle path(without XC)."
            ::= { new-systemModeTable 15 }

        sysSncpWtrTimer     OBJECT-TYPE
            SYNTAX  INTEGER (1..60)
            ACCESS  read-write
            STATUS  mandatory
            DESCRIPTION
                "SNCP WTR Timer (range 1 ~ 60 stands for 10 ~ 600 seconds, and the deviation of WTR is 10 seconds)."
            ::= { new-systemModeTable 16 }

        sysSncpUneqpEn  OBJECT-TYPE
            SYNTAX  INTEGER {
                    disable(1),
                    enable(2)
                }
            ACCESS  read-write
            STATUS  mandatory
            DESCRIPTION
                "SNCP switch on UNEQP enable/disable under Non-Intrusive mode."
            ::= { new-systemModeTable 17 }

        sysSncpAISInsert  OBJECT-TYPE
            SYNTAX  INTEGER {
                    disable(1),
                    enable(2)
                }
            ACCESS  read-write
            STATUS  mandatory
            DESCRIPTION
                "SNCP AIS insert setup."
            ::= { new-systemModeTable 18 }

--
--  New System Protect Table
--
        new-sysProtectionTable  OBJECT-TYPE
            SYNTAX  SEQUENCE OF  NewSysProtectionEntry
            ACCESS  not-accessible
            STATUS  mandatory
            DESCRIPTION
                "System protection Table "
            ::= { system 43 }

        new-sysProtectionEntry OBJECT-TYPE
            SYNTAX  NewSysProtectionEntry
            ACCESS  not-accessible
            STATUS  mandatory
            DESCRIPTION
                "An entry in the System protection table."
            INDEX { new-protectGroupIndex }
            ::= { new-sysProtectionTable 1 }

        NewSysProtectionEntry ::= SEQUENCE  {
            new-protectGroupIndex       INTEGER,
            new-protectMspEnable        INTEGER,
            new-protectMspRevertive     INTEGER,
            new-protectMspDirection     INTEGER
        }

        new-protectGroupIndex  OBJECT-TYPE
            SYNTAX  INTEGER {
                    group-1(1),
                    group-2(2)
                }
            ACCESS  read-only
            STATUS  mandatory
            DESCRIPTION
                "Protect group index"
            ::= { new-sysProtectionEntry  1 }

        new-protectMspEnable  OBJECT-TYPE
            SYNTAX  INTEGER {
                    off(1),
                    on(2)
                }
            ACCESS  read-write
            STATUS  mandatory
            DESCRIPTION
                "MSP 1+1 OFF or ON"
            ::= { new-sysProtectionEntry 2 }

        new-protectMspRevertive  OBJECT-TYPE
            SYNTAX  INTEGER {
                    non-revertive(1),
                    revertive(2)
                }
            ACCESS  read-write
            STATUS  mandatory
            DESCRIPTION
                "MSP 1+1 revertive or non-revertive"
            ::= { new-sysProtectionEntry 3 }

        new-protectMspDirection  OBJECT-TYPE
            SYNTAX  INTEGER {
                    uni-directional(1),
                    bi-directional(2)
                }
            ACCESS  read-write
            STATUS  mandatory
            DESCRIPTION
                "MSP 1+1 direction"
            ::= { new-sysProtectionEntry 4 }

--
--  New XCU SNCP/UPSR APS Table
--
        new-xcuSncpApsTab  OBJECT-TYPE
            SYNTAX  SEQUENCE OF  NewXcuSncpApsEty
            ACCESS  not-accessible
            STATUS  mandatory
            DESCRIPTION
                "XCU SNCP/UPSR APS table "
            ::= { system 44 }

        new-xcuSncpApsEty  OBJECT-TYPE
            SYNTAX  NewXcuSncpApsEty
            ACCESS  not-accessible
            STATUS  mandatory
            DESCRIPTION
                "XCU SNCP/UPSR APS entry"
            INDEX { new-xcuSncpXCUIdx ,
                    new-xcuSncpPort , new-xcuSncpAug1Sts3 ,
                    new-xcuSncpVc3Sts1 , new-xcuSncpTU1xVtx }
            ::= { new-xcuSncpApsTab 1 }

        NewXcuSncpApsEty ::= SEQUENCE {
            new-xcuSncpXCUIdx           XcuNum,
            new-xcuSncpPort             PortID,
            new-xcuSncpAug1Sts3         Aug1Sts3Num,
            new-xcuSncpVc3Sts1          Vc3Sts1Num,
            new-xcuSncpTU1xVtx          TU1xVtxNum,
            new-xcuSncpCurrSlot         XcSlot,
            new-xcuSncpCurrPort         PortID,
            new-xcuSncpCurrChannel      ChannelNum,
            new-xcuSncpCurrAug1Sts3Path Aug1Sts3Num,
            new-xcuSncpCurrVc3Sts1Path  Vc3Sts1Num,
            new-xcuSncpCurrVc1xVtxPath  Vc1xVtxNum,
            new-xcuSncpPPType           XcType,
            new-xcuSncpCmd              SncpUserCmd,
            new-xcuSncpRevertive        INTEGER
        }

        new-xcuSncpXCUIdx  OBJECT-TYPE
            SYNTAX  XcuNum
            ACCESS  read-only
            STATUS  mandatory
            DESCRIPTION
                "XCU index"
            ::= { new-xcuSncpApsEty 1 }

        new-xcuSncpPort  OBJECT-TYPE
            SYNTAX  PortID
            ACCESS  read-only
            STATUS  mandatory
            DESCRIPTION
                "PORT #1~#2"
            ::= { new-xcuSncpApsEty 2 }

        new-xcuSncpAug1Sts3  OBJECT-TYPE
            SYNTAX  Aug1Sts3Num
            ACCESS  read-only
            STATUS  mandatory
            DESCRIPTION
                "AUG1/STS3 index"
            ::= { new-xcuSncpApsEty 3 }

        new-xcuSncpVc3Sts1  OBJECT-TYPE
            SYNTAX  Vc3Sts1Num
            ACCESS  read-only
            STATUS  mandatory
            DESCRIPTION
                "VC3/STS1 index"
            ::= { new-xcuSncpApsEty 4 }

        new-xcuSncpTU1xVtx  OBJECT-TYPE
            SYNTAX  TU1xVtxNum
            ACCESS  read-only
            STATUS  mandatory
            DESCRIPTION
                "VC1x/VTx index"
            ::= { new-xcuSncpApsEty 5 }

        new-xcuSncpCurrSlot  OBJECT-TYPE
            SYNTAX  XcSlot
            ACCESS  read-only
            STATUS  mandatory
            DESCRIPTION
                "SNCP/UPSR current slot"
            ::= { new-xcuSncpApsEty 6 }

        new-xcuSncpCurrPort  OBJECT-TYPE
            SYNTAX  PortID
            ACCESS  read-only
            STATUS  mandatory
            DESCRIPTION
                "SNCP/UPSR current port"
            ::= { new-xcuSncpApsEty 7 }

        new-xcuSncpCurrChannel  OBJECT-TYPE
            SYNTAX  ChannelNum
            ACCESS  read-only
            STATUS  mandatory
            DESCRIPTION
                "SNCP/UPSR current channel"
            ::= { new-xcuSncpApsEty 8 }

        new-xcuSncpCurrAug1Sts3Path  OBJECT-TYPE
            SYNTAX  Aug1Sts3Num
            ACCESS  read-only
            STATUS  mandatory
            DESCRIPTION
                "SNCP/UPSR current Aug1/Sts3"
            ::= { new-xcuSncpApsEty 9 }

        new-xcuSncpCurrVc3Sts1Path  OBJECT-TYPE
            SYNTAX  Vc3Sts1Num
            ACCESS  read-only
            STATUS  mandatory
            DESCRIPTION
                "SNCP/UPSR current Vc3/Sts1"
            ::= { new-xcuSncpApsEty 10 }

        new-xcuSncpCurrVc1xVtxPath  OBJECT-TYPE
            SYNTAX  Vc1xVtxNum
            ACCESS  read-only
            STATUS  mandatory
            DESCRIPTION
                "SNCP/UPSR current Vc1x/Vtx"
            ::= { new-xcuSncpApsEty 11 }

        new-xcuSncpPPType  OBJECT-TYPE
            SYNTAX  XcType
            ACCESS  read-only
            STATUS  mandatory
            DESCRIPTION
                "SNCP/UPSR path protection type"
            ::= { new-xcuSncpApsEty 12 }

        new-xcuSncpCmd  OBJECT-TYPE
            SYNTAX  SncpUserCmd
            ACCESS  read-write
            STATUS  mandatory
            DESCRIPTION
                "SNCP/UPSR APS command"
            ::= { new-xcuSncpApsEty 13 }

        new-xcuSncpRevertive  OBJECT-TYPE
            SYNTAX  INTEGER {
                    non-revertive(1),
                    revertive(2)
                }
            ACCESS  read-write
            STATUS  mandatory
            DESCRIPTION
                "SNCP/UPSR revertive or non-revertive"
            ::= { new-xcuSncpApsEty 14 }


-- 2011-3-17 elvis add above


--
-- radiusSetupTable
--
-- RIKER2014 NFS-14000245

    radiusSetupTable    OBJECT IDENTIFIER ::= { system 45 }

        radiusServer1Enable  OBJECT-TYPE
            SYNTAX  INTEGER {
                    disable(1),
                    enable(2)
                }
            ACCESS  read-write
            STATUS  mandatory
            DESCRIPTION
                "Radius Server1 Enable or Disable"
            ::= { radiusSetupTable 1 }

        radiusServer1IPaddress  OBJECT-TYPE
            SYNTAX  IpAddress
            ACCESS  read-write
            STATUS  mandatory
            DESCRIPTION
                "Radius Server1 IP address"
            ::= { radiusSetupTable 2 }

        radiusServer1Key  OBJECT-TYPE
            SYNTAX  DisplayString (SIZE (0..64) )
            ACCESS  read-write
            STATUS  mandatory
            DESCRIPTION
                "Radius Server1 Key"
            ::= { radiusSetupTable 3 }

        radiusServer1Port  OBJECT-TYPE
            SYNTAX  INTEGER (1..65535)
            ACCESS  read-write
            STATUS  mandatory
            DESCRIPTION
                "Radius Server1 Port"
            ::= { radiusSetupTable 4 }

        radiusServer2Enable  OBJECT-TYPE
            SYNTAX  INTEGER {
                    disable(1),
                    enable(2)
                }
            ACCESS  read-write
            STATUS  mandatory
            DESCRIPTION
                "Radius Server2 Enable or Disable"
            ::= { radiusSetupTable 5 }

        radiusServer2IPaddress  OBJECT-TYPE
            SYNTAX  IpAddress
            ACCESS  read-write
            STATUS  mandatory
            DESCRIPTION
                "Radius Server2 IP address"
            ::= { radiusSetupTable 6 }

        radiusServer2Key  OBJECT-TYPE
            SYNTAX  DisplayString (SIZE (0..24) )
            ACCESS  read-write
            STATUS  mandatory
            DESCRIPTION
                "Radius Server2 Key"
            ::= { radiusSetupTable 7 }

        radiusServer2Port  OBJECT-TYPE
            SYNTAX  INTEGER (1..65535)
            ACCESS  read-write
            STATUS  mandatory
            DESCRIPTION
                "Radius Server2 Port"
            ::= { radiusSetupTable 8 }

        operatorPrivilegeLevel  OBJECT-TYPE
            SYNTAX  INTEGER (0..255)
            ACCESS  read-write
            STATUS  mandatory
            DESCRIPTION
                "Operator Privilege Level"
            ::= { radiusSetupTable 9 }

        adminPrivilegeLevel  OBJECT-TYPE
            SYNTAX  INTEGER (0..255)
            ACCESS  read-write
            STATUS  mandatory
            DESCRIPTION
                "Admin Privilege Level"
            ::= { radiusSetupTable 10 }

        radiusIPv6Server1IP  OBJECT-TYPE
            SYNTAX  DisplayString (SIZE(2..40))
            ACCESS  read-write
            STATUS  mandatory
            DESCRIPTION
                "IP V6 mode address"
            ::= { radiusSetupTable 11 }

        radiusIPv6Server2IP  OBJECT-TYPE
            SYNTAX  DisplayString (SIZE(2..40))
            ACCESS  read-write
            STATUS  mandatory
            DESCRIPTION
                "IP V6 mode address"
            ::= { radiusSetupTable 12 }

        radiusVendorID  OBJECT-TYPE
            SYNTAX  Integer32
            ACCESS  read-write
            STATUS  mandatory
            DESCRIPTION
                "Vendor ID"
            ::= { radiusSetupTable 13 }



--Feature Activate Process

    featureActivation            OBJECT IDENTIFIER ::= { system 46 }

        hwInfoDisplayTable   OBJECT-TYPE
            SYNTAX  SEQUENCE OF HwInfoDisplayEntry
            ACCESS  not-accessible
            STATUS  mandatory
            DESCRIPTION
                "HW info display Table"
            ::= { featureActivation 1 }

        hwInfoDisplayEntry  OBJECT-TYPE
            SYNTAX  HwInfoDisplayEntry
            ACCESS  not-accessible
            STATUS  mandatory
            DESCRIPTION
                "HW info display Entry"
            INDEX { hwSlotIndex }
            ::= { hwInfoDisplayTable  1 }

        HwInfoDisplayEntry ::= SEQUENCE {
            hwSlotIndex                 ChassisSlot,
            hwCardModel                 CardModel,
            hwInfoJSON                  DisplayString
        }

        hwSlotIndex   OBJECT-TYPE
            SYNTAX  ChassisSlot
            ACCESS  read-only
            STATUS  mandatory
            DESCRIPTION
                "HW info slot"
            ::= { hwInfoDisplayEntry 1 }

        hwCardModel  OBJECT-TYPE
            SYNTAX  CardModel
            ACCESS  read-only
            STATUS  mandatory
            DESCRIPTION
                "HW info card model"
            ::= { hwInfoDisplayEntry 2 }

        hwInfoJSON  OBJECT-TYPE
            SYNTAX  DisplayString
            ACCESS  read-only
            STATUS  mandatory
            DESCRIPTION
                "HW info display in JSON format"
            ::= { hwInfoDisplayEntry 3 }

--============================

    licenseImport             OBJECT IDENTIFIER ::= { featureActivation 2 }

        licenseDataImport  OBJECT-TYPE
            SYNTAX  DisplayString (SIZE (0..4096) )
            ACCESS  read-write
            STATUS  mandatory
            DESCRIPTION
                "License file import"
            ::= { licenseImport 1 }

        importStatus    OBJECT-TYPE
            SYNTAX  INTEGER {
                    none(1),
                    ok(2),
                    decodeFail(3),
                    fileFormatIncorrect(4),
                    noMatchCard(5),
                    noMatchSN(6),
                    unknownError(99)
                }
            ACCESS  read-only
            STATUS  mandatory
            DESCRIPTION
                "Import status"
            ::= { licenseImport 2 }

--============================

    faTftp              OBJECT IDENTIFIER ::= { featureActivation 3 }

        faTftpServerIP  OBJECT-TYPE
            SYNTAX  DisplayString (SIZE(2..40))
            ACCESS  read-write
            STATUS  mandatory
            DESCRIPTION
                "IP address of tftp server, IPv4 or IPv6 format"
            ::= { faTftp 1 }

        faFileName  OBJECT-TYPE
            SYNTAX  DisplayString (SIZE (0..64) )
            ACCESS  read-write
            STATUS  mandatory
            DESCRIPTION
                "File name for upload/download"
            ::= { faTftp 2 }

        faSlot  OBJECT-TYPE
            SYNTAX  ChassisSlot
            ACCESS  read-write
            STATUS  mandatory
            DESCRIPTION
                "Upload/download slot"
            ::= { faTftp 3 }

        faAction  OBJECT-TYPE
            SYNTAX  INTEGER {
                    none(1),
                    uploadHWinfo(2),
                    downloadLicenseFile(3),
                    clearStatus(4)
                }
            ACCESS  read-write
            STATUS  mandatory
            DESCRIPTION
                "upload/download command"
            ::= { faTftp 4 }

        faResult  OBJECT-TYPE
            SYNTAX  INTEGER {
                    na(1),
                    ok(2),
                    fail(3)
                }
            ACCESS  read-only
            STATUS  mandatory
            DESCRIPTION
                "Result"
            ::= { faTftp 5 }

        faMessage  OBJECT-TYPE
            SYNTAX  DisplayString (SIZE (0..255) )
            ACCESS  read-only
            STATUS  mandatory
            DESCRIPTION
                "Message of transfer process"
            ::= { faTftp 6 }

--============================

        activationStatusTable    OBJECT-TYPE
            SYNTAX  SEQUENCE OF ActivationStatusEntry
            ACCESS  not-accessible
            STATUS  mandatory
            DESCRIPTION
                "activation status table"
            ::= { featureActivation 4 }

        activationStatusEntry  OBJECT-TYPE
            SYNTAX  ActivationStatusEntry
            ACCESS  not-accessible
            STATUS  mandatory
            DESCRIPTION
                "activation status entry"
            INDEX { actSlotIndex , actItemIndex }
            ::= { activationStatusTable  1 }

        ActivationStatusEntry ::= SEQUENCE {
            actSlotIndex                ChassisSlot,
            actItemIndex                INTEGER,
            actItemName                 DisplayString,
            actCardModel                CardModel,
            actStatus                   DisplayString
        }

        actSlotIndex   OBJECT-TYPE
            SYNTAX  ChassisSlot
            ACCESS  read-only
            STATUS  mandatory
            DESCRIPTION
                "activation slot"
            ::= { activationStatusEntry 1 }

        actItemIndex  OBJECT-TYPE
            SYNTAX  INTEGER
            ACCESS  read-only
            STATUS  mandatory
            DESCRIPTION
                "activation item"
            ::= { activationStatusEntry 2 }

        actItemName  OBJECT-TYPE
            SYNTAX  DisplayString (SIZE (0..32) )
            ACCESS  read-only
            STATUS  mandatory
            DESCRIPTION
                "activation name"
            ::= { activationStatusEntry 3 }

        actCardModel  OBJECT-TYPE
            SYNTAX  CardModel
            ACCESS  read-only
            STATUS  mandatory
            DESCRIPTION
                "model of slot"
            ::= { activationStatusEntry 4 }

        actStatus  OBJECT-TYPE
            SYNTAX  DisplayString (SIZE (0..32) )
            ACCESS  read-only
            STATUS  mandatory
            DESCRIPTION
                "activation status"
            ::= { activationStatusEntry 5 }

    iNETLCTActivationStatus               OBJECT IDENTIFIER ::= { featureActivation 6 }

        iNETLCTworkingXCU  OBJECT-TYPE
            SYNTAX  INTEGER {
                    no(1),
                    yes(2)
                }
            ACCESS  read-only
            STATUS  mandatory
            DESCRIPTION
                "iNET-LCT is enabled for working XCU"
            ::= { iNETLCTActivationStatus 1 }

        iNETLCTstandbyXCU  OBJECT-TYPE
            SYNTAX  INTEGER {
                    no(1),
                    yes(2),
                    unsyncOrNotExist(3)
                }
            ACCESS  read-only
            STATUS  mandatory
            DESCRIPTION
                "iNET-LCT is enabled for standby XCU"
            ::= { iNETLCTActivationStatus 2 }

--============================

--
-- RIKER2016 NFS-16000212
    overheadConnection   OBJECT IDENTIFIER ::= { system 47 }

        dccChannelSetupTable OBJECT-TYPE
            SYNTAX  SEQUENCE OF DccChannelSetupEntry
            ACCESS  not-accessible
            STATUS  mandatory
            DESCRIPTION
                "Dcc Channel Table"
            ::= { overheadConnection 1 }

        dccChannelSetupEntry  OBJECT-TYPE
            SYNTAX  DccChannelSetupEntry
            ACCESS  not-accessible
            STATUS  mandatory
            DESCRIPTION
                "Dcc Channel Entry."
            INDEX { dccChannelXcuIndex , dccChannelPortIndex }
            ::= { dccChannelSetupTable 1 }

        DccChannelSetupEntry ::= SEQUENCE {
            dccChannelXcuIndex          XcuNum,
            dccChannelPortIndex         PortNum,
            dccChannelD1D3              INTEGER,
            dccChannelD4D12             INTEGER,
            dccChannelDoCommand         INTEGER
        }

        dccChannelXcuIndex OBJECT-TYPE
            SYNTAX  XcuNum
            ACCESS  read-only
            STATUS  mandatory
            DESCRIPTION
                "The number of dcc Channel side index"
            ::= { dccChannelSetupEntry 1 }

        dccChannelPortIndex OBJECT-TYPE
            SYNTAX  PortNum
            ACCESS  read-only
            STATUS  mandatory
            DESCRIPTION
                "The number of dcc Channel port number index"
            ::= { dccChannelSetupEntry 2 }

        dccChannelD1D3  OBJECT-TYPE
            SYNTAX  INTEGER {
                    off(0),
                    connectXcu1P1(1),
                    connectXcu1P2(2),
                    connectXcu2P1(3),
                    connectXcu2P2(4),
                    connectCPU(5)
                }
            ACCESS  read-write
            STATUS  mandatory
            DESCRIPTION
                "Dcc Channel Mode of D1-D3"
            ::= { dccChannelSetupEntry  3 }

        dccChannelD4D12  OBJECT-TYPE
            SYNTAX  INTEGER {
                    off(0),
                    connectXcu1P1(1),
                    connectXcu1P2(2),
                    connectXcu2P1(3),
                    connectXcu2P2(4),
                    connectCPU(5)
                }
            ACCESS  read-write
            STATUS  mandatory
            DESCRIPTION
                "Dcc Channel Mode of D4-D12"
            ::= { dccChannelSetupEntry  4 }

        dccChannelDoCommand  OBJECT-TYPE
            SYNTAX  INTEGER {
                    none(0),
                    set(1)
                }
            ACCESS  read-write
            STATUS  mandatory
            DESCRIPTION
                "Dcc Channel Setting Command"
            ::= { dccChannelSetupEntry  5 }

--
-- console/telnet user list and password change
--

    consoleTelnetUser         OBJECT IDENTIFIER ::= { system 48 }

        userListTable  OBJECT-TYPE
            SYNTAX  SEQUENCE OF UserListEntry
            ACCESS  not-accessible
            STATUS  mandatory
            DESCRIPTION
                "user list table"
            ::= { consoleTelnetUser 1 }

        userListEntry OBJECT-TYPE
            SYNTAX  UserListEntry
            ACCESS  not-accessible
            STATUS  mandatory
            DESCRIPTION
                "user list entry"
            INDEX { userIndex }
            ::= { userListTable 1 }

        UserListEntry ::= SEQUENCE {
            userIndex     INTEGER,
            userName      DisplayString,
            userLevel     INTEGER
        }

        userIndex OBJECT-TYPE
            SYNTAX  INTEGER
            ACCESS  read-only
            STATUS  mandatory
            DESCRIPTION
                "user index"
            ::= { userListEntry 1 }

        userName  OBJECT-TYPE
            SYNTAX  DisplayString
            ACCESS  read-only
            STATUS  mandatory
            DESCRIPTION
                "user name"
            ::= { userListEntry 2 }

        userLevel  OBJECT-TYPE
            SYNTAX  INTEGER {
                    operator(1),
                    admin(2)
                }
            ACCESS  read-only
            STATUS  mandatory
            DESCRIPTION
                "user level"
            ::= { userListEntry 3 }


        userPasswordChange  OBJECT-TYPE
            SYNTAX  OCTET STRING (SIZE (10..127))
            ACCESS  read-write
            STATUS  mandatory
            DESCRIPTION
                "password change by NMS"
            ::= { consoleTelnetUser 2 }

        userPwChangeResponse  OBJECT-TYPE
            SYNTAX  DisplayString
            ACCESS  read-only
            STATUS  mandatory
            DESCRIPTION
                "password change response:
                USERNAME password changed!
                Format not correct!
                Password too long!
                User name not exist!"
            ::= { consoleTelnetUser 3 }


--IPv6
--
--  network interface setup table (V6)
--
        v6networkInterfaceTable  OBJECT-TYPE
            SYNTAX  SEQUENCE OF V6NetworkInterfaceEntry
            ACCESS  not-accessible
            STATUS  mandatory
            DESCRIPTION
                "V6 Network Interface Setup Table"
            ::= { system 51 }

        v6networkInterfaceEntry  OBJECT-TYPE
            SYNTAX  V6NetworkInterfaceEntry
            ACCESS  not-accessible
            STATUS  mandatory
            DESCRIPTION
                "An entry in Network Interface Setup table."
            INDEX { vsixinterfaceNI }
            ::= { v6networkInterfaceTable 1 }

        V6NetworkInterfaceEntry ::= SEQUENCE  {
            vsixinterfaceNI             NiIndex,
            vsixinterfaceMode           NiMode,
            vsixinterfaceRIP            INTEGER,
            vsixinterfaceIPAddress      DisplayString (SIZE(2..40)),
            vsixinterfacePrefix         INTEGER (0..128),
            vsixinterfaceFrame          INTEGER,
            vsixareaid                  IpAddress,
            vsixinterfaceActivate       INTEGER,
            vsixinterfaceResult         INTEGER,
            vsixInterfacePPPstat        INTEGER
        }

        vsixinterfaceNI  OBJECT-TYPE
            SYNTAX  NiIndex
            ACCESS  read-only
            STATUS  mandatory
            DESCRIPTION
                "V6 Network Interface Number"
            ::= { v6networkInterfaceEntry  1 }

        vsixinterfaceMode  OBJECT-TYPE
            SYNTAX  NiMode
            ACCESS  read-write
            STATUS  mandatory
            DESCRIPTION
                "V6 Network Interface Mode"
            ::= { v6networkInterfaceEntry  2 }

        vsixinterfaceRIP  OBJECT-TYPE
            SYNTAX  INTEGER {
                    off(1),
                    rip(2),
                    ospf(4)
                }
            ACCESS  read-write
            STATUS  mandatory
            DESCRIPTION
                "V6 Network Interface RIP Selection"
            ::= { v6networkInterfaceEntry  3 }

        vsixinterfaceIPAddress  OBJECT-TYPE
            SYNTAX  DisplayString (SIZE(2..40))
            ACCESS  read-write
            STATUS  mandatory
            DESCRIPTION
                "V6 Network Interface IP Address"
            ::= { v6networkInterfaceEntry  4 }

        vsixinterfacePrefix  OBJECT-TYPE
            SYNTAX  INTEGER (0..128)
            ACCESS  read-write
            STATUS  mandatory
            DESCRIPTION
                "V6 Network Interface Subnet Mask"
            ::= { v6networkInterfaceEntry  5 }

        vsixinterfaceFrame  OBJECT-TYPE
            SYNTAX   INTEGER {
                    ethernet(1),
                    hdlc(2),
                    ppp(3)
                }
            ACCESS  read-write
            STATUS  mandatory
            DESCRIPTION
                "V6 Network Interface Frame Setup"
            ::= { v6networkInterfaceEntry  6 }

        vsixareaid  OBJECT-TYPE
            SYNTAX  IpAddress
            ACCESS  read-write
            STATUS  mandatory
            DESCRIPTION
                "V6 Area ID"
            ::= { v6networkInterfaceEntry  7}


        vsixinterfaceActivate  OBJECT-TYPE
            SYNTAX   INTEGER {
                    no(1),
                    yes(2),
                    done(3),
                    waitForUser(4)
                }
            ACCESS  read-write
            STATUS  mandatory
            DESCRIPTION
                "V6 Network Interface Setting Activate"
            ::= { v6networkInterfaceEntry  8}

        vsixinterfaceResult  OBJECT-TYPE
            SYNTAX   INTEGER {
                    none(1),
                    fail(2),
                    success(3)
                }
            ACCESS  read-only
            STATUS  mandatory
            DESCRIPTION
                "V6 Network Interface Setting Result"
            ::= { v6networkInterfaceEntry  9}

        vsixInterfacePPPstat  OBJECT-TYPE
            SYNTAX   INTEGER {
                    na(1),
                    pppup(2),
                    pppdown(3)
                }
            ACCESS  read-only
            STATUS  current
            DESCRIPTION
                "V6 Network Interface ppp status"
            ::= { v6networkInterfaceEntry  10}

--
--  Static Route Setup table (V6)
--

        v6staticRouteTable  OBJECT-TYPE
            SYNTAX  SEQUENCE OF V6StaticRouteEntry
            ACCESS  not-accessible
            STATUS  mandatory
            DESCRIPTION
                "Static Route Setup Table"
            ::= { system 52 }

        v6staticRouteEntry  OBJECT-TYPE
            SYNTAX  V6StaticRouteEntry
            ACCESS  not-accessible
            STATUS  mandatory
            DESCRIPTION
                "An entry in Static Route Setup table."
            INDEX { vsixrouteIndex }
            ::= { v6staticRouteTable 1 }

        V6StaticRouteEntry ::= SEQUENCE  {
            vsixrouteIndex              INTEGER,
            vsixrouteNet-Destination    DisplayString (SIZE(2..40)),
            vsixrouteNet-Prefix         INTEGER (0..128),
            vsixrouteGateway            DisplayString (SIZE(2..40)),
            vsixrouteNI                 NiNum,
            vsixrouteActivate           INTEGER,
            vsixrouteResult             INTEGER
        }

        vsixrouteIndex  OBJECT-TYPE
            SYNTAX  INTEGER(1..21)
            ACCESS  read-only
            STATUS  mandatory
            DESCRIPTION
                "Static route Index"
            ::= { v6staticRouteEntry  1 }

        vsixrouteNet-Destination  OBJECT-TYPE
            SYNTAX  DisplayString (SIZE(2..40))
            ACCESS  read-write
            STATUS  mandatory
            DESCRIPTION
                "Static route Network Destination"
            ::= { v6staticRouteEntry  2 }

        vsixrouteNet-Prefix  OBJECT-TYPE
            SYNTAX  INTEGER (0..128)
            ACCESS  read-write
            STATUS  mandatory
            DESCRIPTION
                "Static route Network Mask"
            ::= { v6staticRouteEntry  3 }

        vsixrouteGateway   OBJECT-TYPE
            SYNTAX  DisplayString (SIZE(2..40))
            ACCESS  read-write
            STATUS  mandatory
            DESCRIPTION
                "Static Route Gateway"
            ::= { v6staticRouteEntry  4 }

        vsixrouteNI  OBJECT-TYPE
            SYNTAX  NiNum
            ACCESS  read-only
            STATUS  mandatory
            DESCRIPTION
                "Static Route Network Interface"
            ::= { v6staticRouteEntry  5 }


        vsixrouteActivate  OBJECT-TYPE
            SYNTAX   INTEGER {
                    no(1),
                    yes(2),
                    done(3)
                }
            ACCESS  read-write
            STATUS  mandatory
            DESCRIPTION
                "Static Route Setting Activate"
            ::= { v6staticRouteEntry  6}

        vsixrouteResult  OBJECT-TYPE
            SYNTAX   INTEGER {
                    none(1),
                    fail(2),
                    success(3)
                }
            ACCESS  read-only
            STATUS  mandatory
            DESCRIPTION
                "Static Route Setting Result"
            ::= { v6staticRouteEntry  7}

-- 2010-9-27 add above by-elvis

-- 2010-11-02 add below by-Sue

--
-- ospf Display Table
--
    ospfDisplayTable     OBJECT IDENTIFIER ::= { system 53 }

--
-- area Display Table
--
        areaDisplayTab  OBJECT-TYPE
            SYNTAX  SEQUENCE OF AreaDisplayEty
            ACCESS  not-accessible
            STATUS  mandatory
            DESCRIPTION
                "area display"
            ::= { ospfDisplayTable 1 }

        areaDisplayEty  OBJECT-TYPE
            SYNTAX  AreaDisplayEty
            ACCESS  not-accessible
            STATUS  mandatory
            DESCRIPTION
                "area display entry"
            INDEX { oadAreaIndex }
            ::= { areaDisplayTab 1 }

        AreaDisplayEty ::= SEQUENCE {
            oadAreaIndex                INTEGER,
            oadAreaId                   IpAddress,
            oadInterfaceCount           INTEGER,
            oadSPFExecutedTimes         INTEGER,
            oadStubMetric               INTEGER,
            oadRouterId                 IpAddress
        }

        oadAreaIndex  OBJECT-TYPE
            SYNTAX  INTEGER (1..42)
            ACCESS  read-only
            STATUS  mandatory
            DESCRIPTION
                "area 1 to 42, total 42 areas at most."
            ::= { areaDisplayEty 1 }

        oadAreaId  OBJECT-TYPE
            SYNTAX  IpAddress
            ACCESS  read-only
            STATUS  mandatory
            DESCRIPTION
                "area id"
            ::= { areaDisplayEty 2 }

        oadInterfaceCount  OBJECT-TYPE
-- 2010-12-13 modify below by-Sue
--             SYNTAX  INTEGER (1..21)
            SYNTAX  INTEGER (0..21)
-- 2010-12-13 modify above by-Sue
            ACCESS  read-only
            STATUS  mandatory
            DESCRIPTION
                "number of interface in this area"
            ::= { areaDisplayEty 3 }

        oadSPFExecutedTimes  OBJECT-TYPE
            SYNTAX  INTEGER
            ACCESS  read-only
            STATUS  mandatory
            DESCRIPTION
                "SPF algorithm executed times"
            ::= { areaDisplayEty 4 }

        oadStubMetric  OBJECT-TYPE
            SYNTAX  INTEGER
            ACCESS  read-only
            STATUS  mandatory
            DESCRIPTION
                "stub metric (for OSPFv3)"
            ::= { areaDisplayEty 5 }

         oadRouterId  OBJECT-TYPE
             SYNTAX  IpAddress
             ACCESS  read-only
             STATUS  mandatory
             DESCRIPTION
                "router id"
             ::= { areaDisplayEty 6 }

--
-- border router Display Table
--
        borderRouterDisplayTab  OBJECT-TYPE
            SYNTAX  SEQUENCE OF BorderRouterDisplayEty
            ACCESS  not-accessible
            STATUS  mandatory
            DESCRIPTION
                "border router display"
            ::= { ospfDisplayTable 2 }

        borderRouterDisplayEty  OBJECT-TYPE
            SYNTAX  BorderRouterDisplayEty
            ACCESS  not-accessible
            STATUS  mandatory
            DESCRIPTION
                "border router display entry"
            INDEX { brdIndex }
            ::= { borderRouterDisplayTab 1 }

        BorderRouterDisplayEty ::= SEQUENCE {
            brdIndex                    INTEGER,
            brdDestination              IpAddress,
            brdTOS                      INTEGER,
            brdType                     INTEGER,
            brdNextHop                  DisplayString,
            brdCost                     INTEGER,
            brdRtType                   INTEGER,
            brdAreaId                   IpAddress
        }

        brdIndex  OBJECT-TYPE
            SYNTAX  INTEGER
            ACCESS  read-only
            STATUS  mandatory
            DESCRIPTION
                "border router index"
            ::= { borderRouterDisplayEty 1 }

        brdDestination  OBJECT-TYPE
            SYNTAX  IpAddress
            ACCESS  read-only
            STATUS  mandatory
            DESCRIPTION
                "destination"
            ::= { borderRouterDisplayEty 2 }

        brdTOS  OBJECT-TYPE
            SYNTAX  INTEGER
            ACCESS  read-only
            STATUS  mandatory
            DESCRIPTION
                "TOS (for OSPF)"
            ::= { borderRouterDisplayEty 3 }

        brdType  OBJECT-TYPE
            SYNTAX  INTEGER {
                    unknown(1),
                    abr(2),
                    asbr(3)
                }
            ACCESS  read-only
            STATUS  mandatory
            DESCRIPTION
                "type"
            ::= { borderRouterDisplayEty 4 }

        brdNextHop  OBJECT-TYPE
            SYNTAX  DisplayString(SIZE(0..255))
            ACCESS  read-only
            STATUS  mandatory
            DESCRIPTION
                "NextHop"
            ::= { borderRouterDisplayEty 5 }

        brdCost  OBJECT-TYPE
            SYNTAX  INTEGER
            ACCESS  read-only
            STATUS  mandatory
            DESCRIPTION
                "cost"
            ::= { borderRouterDisplayEty 6 }

        brdRtType  OBJECT-TYPE
            SYNTAX  INTEGER {
                    intraArea(1),
                    interArea(2),
                    type1Ext(3),
                    type2Ext(4),
                    unknown(100)
                }
            ACCESS  read-only
            STATUS  mandatory
            DESCRIPTION
                "Rt.Type"
            ::= { borderRouterDisplayEty 7 }

        brdAreaId  OBJECT-TYPE
            SYNTAX  IpAddress
            ACCESS  read-only
            STATUS  mandatory
            DESCRIPTION
                "area id"
            ::= { borderRouterDisplayEty 8 }

--
-- interface Display table
--
        ospfInterfaceDisplayTab  OBJECT-TYPE
            SYNTAX  SEQUENCE OF OspfIfDisplayEntry
            ACCESS  not-accessible
            STATUS  mandatory
            DESCRIPTION
                "Ospf Interface Display Table"
            ::= { ospfDisplayTable 3 }

        ospfIfDisplayEntry  OBJECT-TYPE
            SYNTAX  OspfIfDisplayEntry
            ACCESS  not-accessible
            STATUS  mandatory
            DESCRIPTION
                "An entry in Ospf Interface Display table."
            INDEX { oidIfDisplayIndex }
            ::= { ospfInterfaceDisplayTab 1 }

        OspfIfDisplayEntry ::= SEQUENCE  {
            oidIfDisplayIndex           NiNum,
            oidInternetAddress          DisplayString,
            oidMask                     IpAddress,
            oidAreaId                   IpAddress,
            oidRouterId                 IpAddress,
            oidNetworkType              INTEGER,
            oidCost                     INTEGER,
            oidPriority                 INTEGER,
            oidDRId                     IpAddress,
            oidDRIfAddress              DisplayString,
            oidBDRId                    IpAddress,
            oidBDRIfAddress             DisplayString,
            oidHelloInterval            INTEGER,
            oidDeadInterval             INTEGER,
            oidRetransmit               INTEGER,
            oidHelloDueIn               INTEGER,
            oidAuthentication           INTEGER,
            oidNeighborCount            INTEGER,
            oidAdjNeighborCount         INTEGER
        }

        oidIfDisplayIndex  OBJECT-TYPE
            SYNTAX  NiNum
            ACCESS  read-only
            STATUS  mandatory
            DESCRIPTION
                "Interface Index"
            ::= { ospfIfDisplayEntry  1 }

        oidInternetAddress  OBJECT-TYPE
            SYNTAX  DisplayString(SIZE(0..255))
            ACCESS  read-only
            STATUS  mandatory
            DESCRIPTION
                "internet address"
            ::= { ospfIfDisplayEntry 2 }

        oidMask  OBJECT-TYPE
            SYNTAX  IpAddress
            ACCESS  read-only
            STATUS  mandatory
            DESCRIPTION
                "mask (for OSPF)"
            ::= { ospfIfDisplayEntry 3 }

        oidAreaId  OBJECT-TYPE
            SYNTAX  IpAddress
            ACCESS  read-only
            STATUS  mandatory
            DESCRIPTION
                "area id"
            ::= { ospfIfDisplayEntry 4 }

        oidRouterId  OBJECT-TYPE
            SYNTAX  IpAddress
            ACCESS  read-only
            STATUS  mandatory
            DESCRIPTION
                "router id"
            ::= { ospfIfDisplayEntry 5 }

        oidNetworkType  OBJECT-TYPE
            SYNTAX   INTEGER {
                    broadcast(1),
                    non-broadcast(2),
                    point-to-multipoint(3),
                    point-to-point(4),
                    unknown(100)
                }
            ACCESS  read-only
            STATUS  mandatory
            DESCRIPTION
                "network type"
            ::= { ospfIfDisplayEntry  6 }

        oidCost  OBJECT-TYPE
            SYNTAX  INTEGER
            ACCESS  read-only
            STATUS  mandatory
            DESCRIPTION
                "cost or metric"
            ::= { ospfIfDisplayEntry  7 }

        oidPriority  OBJECT-TYPE
            SYNTAX  INTEGER
            ACCESS  read-only
            STATUS  mandatory
            DESCRIPTION
                "priority"
            ::= { ospfIfDisplayEntry  8 }

        oidDRId  OBJECT-TYPE
            SYNTAX  IpAddress
            ACCESS  read-only
            STATUS  mandatory
            DESCRIPTION
                "Designated Router Id"
            ::= { ospfIfDisplayEntry 9 }

        oidDRIfAddress  OBJECT-TYPE
            SYNTAX  DisplayString(SIZE(0..255))
            ACCESS  read-only
            STATUS  mandatory
            DESCRIPTION
                "DR interface address"
            ::= { ospfIfDisplayEntry 10 }

        oidBDRId  OBJECT-TYPE
            SYNTAX  IpAddress
            ACCESS  read-only
            STATUS  mandatory
            DESCRIPTION
                "Backup Designated Router Id"
            ::= { ospfIfDisplayEntry 11 }

        oidBDRIfAddress  OBJECT-TYPE
            SYNTAX  DisplayString(SIZE(0..255))
            ACCESS  read-only
            STATUS  mandatory
            DESCRIPTION
                "BDR interface address"
            ::= { ospfIfDisplayEntry 12 }

        oidHelloInterval  OBJECT-TYPE
            SYNTAX  INTEGER
            ACCESS  read-only
            STATUS  mandatory
            DESCRIPTION
                "hello interval"
            ::= { ospfIfDisplayEntry  13 }

        oidDeadInterval  OBJECT-TYPE
            SYNTAX  INTEGER
            ACCESS  read-only
            STATUS  mandatory
            DESCRIPTION
                "dead interval"
            ::= { ospfIfDisplayEntry  14 }

        oidRetransmit    OBJECT-TYPE
            SYNTAX  INTEGER
            ACCESS  read-only
            STATUS  mandatory
            DESCRIPTION
                "retransmit interval"
            ::= { ospfIfDisplayEntry  15 }

        oidHelloDueIn    OBJECT-TYPE
            SYNTAX  INTEGER
            ACCESS  read-only
            STATUS  mandatory
            DESCRIPTION
                "hello due in (unit sec.)"
            ::= { ospfIfDisplayEntry  16 }

        oidAuthentication  OBJECT-TYPE
            SYNTAX   INTEGER {
                    none(1),
                    text(2),
                    md5(3),
                    unknown(99),
                    na(100)
                }
            ACCESS  read-only
            STATUS  mandatory
            DESCRIPTION
                "authentication (for OSPF)"
            ::= { ospfIfDisplayEntry  17 }

        oidNeighborCount  OBJECT-TYPE
            SYNTAX  INTEGER
            ACCESS  read-only
            STATUS  mandatory
            DESCRIPTION
                "neighbor count"
            ::= { ospfIfDisplayEntry  18 }

        oidAdjNeighborCount  OBJECT-TYPE
            SYNTAX  INTEGER
            ACCESS  read-only
            STATUS  mandatory
            DESCRIPTION
                "adjacent neighbor count (for OSPF)"
            ::= { ospfIfDisplayEntry  19 }

--
-- route Display Table
--
        routeDisplayTab  OBJECT-TYPE
            SYNTAX  SEQUENCE OF RouteDisplayEty
            ACCESS  not-accessible
            STATUS  mandatory
            DESCRIPTION
                "area display"
            ::= { ospfDisplayTable 4 }

        routeDisplayEty  OBJECT-TYPE
            SYNTAX  RouteDisplayEty
            ACCESS  not-accessible
            STATUS  mandatory
            DESCRIPTION
                "route display entry"
            INDEX { ordRouteIndex }
            ::= { routeDisplayTab 1 }

        RouteDisplayEty ::= SEQUENCE {
            ordRouteIndex               INTEGER,
            ordDestination              DisplayString,
            ordMask                     IpAddress,
            ordPrefixLength             INTEGER,
            ordTOS                      INTEGER,
            ordCost                     INTEGER,
            ordRtType                   INTEGER,
            ordAreaId                   IpAddress,
            ordNextHop                  DisplayString,
            ordInterface                NiNum
        }

        ordRouteIndex  OBJECT-TYPE
            SYNTAX  INTEGER
            ACCESS  read-only
            STATUS  mandatory
            DESCRIPTION
                "route index"
            ::= { routeDisplayEty 1 }

        ordDestination  OBJECT-TYPE
            SYNTAX  DisplayString(SIZE(0..255))
            ACCESS  read-only
            STATUS  mandatory
            DESCRIPTION
                "destination"
            ::= { routeDisplayEty 2 }

        ordMask  OBJECT-TYPE
            SYNTAX  IpAddress
            ACCESS  read-only
            STATUS  mandatory
            DESCRIPTION
                "mask (for OSPF)"
            ::= { routeDisplayEty 3 }

        ordPrefixLength  OBJECT-TYPE
            SYNTAX  INTEGER
            ACCESS  read-only
            STATUS  mandatory
            DESCRIPTION
                "Prefix-Length (for OSPFv3)"
            ::= { routeDisplayEty 4 }

        ordTOS  OBJECT-TYPE
            SYNTAX  INTEGER
            ACCESS  read-only
            STATUS  mandatory
            DESCRIPTION
                "TOS (for OSPF)"
            ::= { routeDisplayEty 5 }

        ordCost  OBJECT-TYPE
            SYNTAX  INTEGER
            ACCESS  read-only
            STATUS  mandatory
            DESCRIPTION
                "cost"
            ::= { routeDisplayEty 6 }

        ordRtType  OBJECT-TYPE
            SYNTAX  INTEGER {
                    intraArea(1),
                    interArea(2),
                    type1Ext(3),
                    type2Ext(4),
                    unknown(100)
                }
            ACCESS  read-only
            STATUS  mandatory
            DESCRIPTION
                "Rt.Type"
            ::= { routeDisplayEty 7 }

        ordAreaId  OBJECT-TYPE
            SYNTAX  IpAddress
            ACCESS  read-only
            STATUS  mandatory
            DESCRIPTION
                "area id"
            ::= { routeDisplayEty 8 }

        ordNextHop  OBJECT-TYPE
            SYNTAX  DisplayString(SIZE(0..255))
            ACCESS  read-only
            STATUS  mandatory
            DESCRIPTION
                "NextHop"
            ::= { routeDisplayEty 9 }

        ordInterface  OBJECT-TYPE
            SYNTAX  NiNum
            ACCESS  read-only
            STATUS  mandatory
            DESCRIPTION
                "Interface"
            ::= { routeDisplayEty  10 }

--
-- neighbor Display Table
--
        neighborDisplayTab  OBJECT-TYPE
            SYNTAX  SEQUENCE OF NeighborDisplayEty
            ACCESS  not-accessible
            STATUS  mandatory
            DESCRIPTION
                "neighbor display"
            ::= { ospfDisplayTable 5 }

        neighborDisplayEty  OBJECT-TYPE
            SYNTAX  NeighborDisplayEty
            ACCESS  not-accessible
            STATUS  mandatory
            DESCRIPTION
                "neighbor display entry"
            INDEX { ondNeighborIndex }
            ::= { neighborDisplayTab 1 }

        NeighborDisplayEty ::= SEQUENCE {
            ondNeighborIndex            INTEGER,
            ondNeighborId               IpAddress,
            ondAddress                  DisplayString,
            ondAreaId                   IpAddress,
            ondInterface                NiNum,
            ondPriority                 INTEGER,
            ondState                    INTEGER,
            ondDeadTime                 INTEGER,
            ondChangedStateCount        INTEGER,
            ondDR                       IpAddress,
            ondBDR                      IpAddress,
            ondOptions                  INTEGER,
            ondHelper                   INTEGER,
            ondHelperAge                INTEGER,
            ondHelperExistReason        INTEGER
        }

        ondNeighborIndex  OBJECT-TYPE
            SYNTAX  INTEGER
            ACCESS  read-only
            STATUS  mandatory
            DESCRIPTION
                "neighbor index"
            ::= { neighborDisplayEty 1 }

        ondNeighborId  OBJECT-TYPE
            SYNTAX  IpAddress
            ACCESS  read-only
            STATUS  mandatory
            DESCRIPTION
                "neighbor id"
            ::= { neighborDisplayEty 2 }

        ondAddress  OBJECT-TYPE
            SYNTAX  DisplayString(SIZE(0..255))
            ACCESS  read-only
            STATUS  mandatory
            DESCRIPTION
                "address"
            ::= { neighborDisplayEty 3 }

        ondAreaId  OBJECT-TYPE
            SYNTAX  IpAddress
            ACCESS  read-only
            STATUS  mandatory
            DESCRIPTION
                "area id (for OSPF)"
            ::= { neighborDisplayEty 4 }

        ondInterface  OBJECT-TYPE
            SYNTAX  NiNum
            ACCESS  read-only
            STATUS  mandatory
            DESCRIPTION
                "interface (for OSPF)"
            ::= { neighborDisplayEty 5 }

        ondPriority  OBJECT-TYPE
            SYNTAX  INTEGER
            ACCESS  read-only
            STATUS  mandatory
            DESCRIPTION
                "priority"
            ::= { neighborDisplayEty 6 }

        ondState  OBJECT-TYPE
            SYNTAX  INTEGER {
                    down(1),
                    attempt(2),
                    init(3),
                    two-way(4),
                    exstart(5),
                    exchange(6),
                    loading(7),
                    full(8),
                    unknown(100)
                }
            ACCESS  read-only
            STATUS  mandatory
            DESCRIPTION
                "state"
            ::= { neighborDisplayEty 7 }

        ondDeadTime  OBJECT-TYPE
            SYNTAX  INTEGER
            ACCESS  read-only
            STATUS  mandatory
            DESCRIPTION
                "dead time (for OSPFv3)"
            ::= { neighborDisplayEty 8 }

        ondChangedStateCount  OBJECT-TYPE
            SYNTAX  INTEGER
            ACCESS  read-only
            STATUS  mandatory
            DESCRIPTION
                "changed state count (for OSPF)"
            ::= { neighborDisplayEty 9 }

        ondDR  OBJECT-TYPE
            SYNTAX  IpAddress
            ACCESS  read-only
            STATUS  mandatory
            DESCRIPTION
                "Designated Router Id (for OSPF)"
            ::= { neighborDisplayEty  10 }

        ondBDR  OBJECT-TYPE
            SYNTAX  IpAddress
            ACCESS  read-only
            STATUS  mandatory
            DESCRIPTION
                "Backup Designated Rrouter Id (for OSPF)"
            ::= { neighborDisplayEty  11 }

        ondOptions  OBJECT-TYPE
            SYNTAX  INTEGER
            ACCESS  read-only
            STATUS  mandatory
            DESCRIPTION
                "options (for OSPF)"
            ::= { neighborDisplayEty 12 }

        ondHelper  OBJECT-TYPE
            SYNTAX  INTEGER {
                    not-helping(1),
                    helping(2),
                    unknown(100)
                }
            ACCESS  read-only
            STATUS  mandatory
            DESCRIPTION
                "helper (for OSPFv3)"
            ::= { neighborDisplayEty 13 }

        ondHelperAge  OBJECT-TYPE
            SYNTAX  INTEGER
            ACCESS  read-only
            STATUS  mandatory
            DESCRIPTION
                "helper age (for OSPFv3)"
            ::= { neighborDisplayEty 14 }

        ondHelperExistReason  OBJECT-TYPE
            SYNTAX  INTEGER {
                    none(1),
                    in-progress(2),
                    completed(3),
                    timed-out(4),
                    topology-change(5),
                    unknown(100)
                }
            ACCESS  read-only
            STATUS  mandatory
            DESCRIPTION
                "helper exist reason (for OSPFv3)"
            ::= { neighborDisplayEty 15 }

--
-- ospf Setup Table
--
    ospfSetupTable     OBJECT IDENTIFIER ::= { system 54 }

--
-- area Setup Table
--
    areaSetupTab       OBJECT IDENTIFIER ::= { ospfSetupTable 1 }

        oasAreaId  OBJECT-TYPE
            SYNTAX  IpAddress
            ACCESS  read-write
            STATUS  mandatory
            DESCRIPTION
                "area id"
            ::= { areaSetupTab 1 }

        oasType    OBJECT-TYPE
            SYNTAX  INTEGER {
                    normal(1),
                    stub(2),
-- 2011-01-07 modify below by-Sue
--                        stub-no-summary(3),
--                        unknown(100)
                    stub-no-summary(3)
-- 2011-01-07 modify above by-Sue
                }
            ACCESS  read-write
            STATUS  mandatory
            DESCRIPTION
                "type"
            ::= { areaSetupTab 2 }

        oasCostOrMetric    OBJECT-TYPE
            SYNTAX  INTEGER (0..16777215)
            ACCESS  read-write
            STATUS  mandatory
            DESCRIPTION
                "cost or metric"
            ::= { areaSetupTab 3 }

        oasCommand  OBJECT-TYPE
            SYNTAX  INTEGER {
                    none(1),
                    add(2),
                    modify(3),
                    delete(4)
                }
            ACCESS  read-write
            STATUS  mandatory
            DESCRIPTION
                "area setup command"
            ::= { areaSetupTab 4 }

        oasErrorCode  OBJECT-TYPE
            SYNTAX  INTEGER {
                    success(1),
                    no-more-area-space(2),
                    area-existed-already(3),
                    can-not-find-the-area(4),
                    area-is-used(5),
                    can-not-modify-the-area(6),
                    failure(7),
                    none(100)
                }
            ACCESS  read-only
            STATUS  mandatory
            DESCRIPTION
                "area setup error code"
            ::= { areaSetupTab 5 }

--
-- router id Setup Table
--
    routerIdSetupTab       OBJECT IDENTIFIER ::= { ospfSetupTable 2 }

        orsRouterId  OBJECT-TYPE
            SYNTAX  IpAddress
            ACCESS  read-write
            STATUS  mandatory
            DESCRIPTION
                "router id"
            ::= { routerIdSetupTab 1 }

-- 2010-11-29 add below by-Sue
        orsRouterType    OBJECT-TYPE
            SYNTAX  INTEGER {
                    non-asbr(1),
                    asbr(2)
                }
            ACCESS  read-write
            STATUS  mandatory
            DESCRIPTION
                "router type"
            ::= { routerIdSetupTab 2 }

        orsStaticOption    OBJECT-TYPE
            SYNTAX  INTEGER {
                    disable(1),
                    enable(2),
                    na(3)
                }
            ACCESS  read-write
            STATUS  mandatory
            DESCRIPTION
                "static option"
            ::= { routerIdSetupTab 3 }

        orsConnectedOption    OBJECT-TYPE
            SYNTAX  INTEGER {
                    disable(1),
                    enable(2),
                    na(3)
                }
            ACCESS  read-write
            STATUS  mandatory
            DESCRIPTION
                "connected option"
            ::= { routerIdSetupTab 4 }

        orsRipOption    OBJECT-TYPE
            SYNTAX  INTEGER {
                    disable(1),
                    enable(2),
                    na(3)
                }
            ACCESS  read-write
            STATUS  mandatory
            DESCRIPTION
                "rip option"
            ::= { routerIdSetupTab 5 }

        orsCommand  OBJECT-TYPE
            SYNTAX  INTEGER {
                    none(1),
                    set(2)
                }
            ACCESS  read-write
            STATUS  mandatory
            DESCRIPTION
                "router id setup command"
            ::= { routerIdSetupTab 6 }

        orsErrorCode  OBJECT-TYPE
            SYNTAX  INTEGER {
                    success(1),
                    failure(2),
                    none(100)
                }
            ACCESS  read-only
            STATUS  mandatory
            DESCRIPTION
                "router id setup error code"
            ::= { routerIdSetupTab 7 }
-- 2010-11-29 add above by-Sue

--
-- interface setup table
--
    ospfInterfaceSetupTab    OBJECT IDENTIFIER ::= { ospfSetupTable 3 }

        oisIfSetupIndex  OBJECT-TYPE
            SYNTAX  NiNum
            ACCESS  read-write
            STATUS  mandatory
            DESCRIPTION
                "Interface Index"
            ::= { ospfInterfaceSetupTab  1 }

        oisRetransmitInterval    OBJECT-TYPE
            SYNTAX  INTEGER (0..3600)
            ACCESS  read-write
            STATUS  mandatory
            DESCRIPTION
                "retransmit interval"
            ::= { ospfInterfaceSetupTab  2 }

        oisTransmitDelay  OBJECT-TYPE
            SYNTAX  INTEGER (0..3600)
            ACCESS  read-write
            STATUS  mandatory
            DESCRIPTION
                "transmit delay"
            ::= { ospfInterfaceSetupTab  3 }

        oisPriority  OBJECT-TYPE
            SYNTAX  INTEGER (0..255)
            ACCESS  read-write
            STATUS  mandatory
            DESCRIPTION
                "priority"
            ::= { ospfInterfaceSetupTab  4 }

        oisHelloInterval  OBJECT-TYPE
            SYNTAX  INTEGER (1..65535)
            ACCESS  read-write
            STATUS  mandatory
            DESCRIPTION
                "hello interval"
            ::= { ospfInterfaceSetupTab  5 }

        oisDeadInterval  OBJECT-TYPE
            SYNTAX  INTEGER (1..2147483647)
            ACCESS  read-write
            STATUS  mandatory
            DESCRIPTION
                "dead interval"
            ::= { ospfInterfaceSetupTab  6 }

        oisCostOrMetric  OBJECT-TYPE
            SYNTAX  INTEGER (1..65535)
            ACCESS  read-write
            STATUS  mandatory
            DESCRIPTION
                "cost or metric"
            ::= { ospfInterfaceSetupTab  7 }

        oisNetworkType  OBJECT-TYPE
            SYNTAX   INTEGER {
                    broadcast(1),
                    non-broadcast(2),
                    point-to-multipoint(3),
                    point-to-point(4),
                    unknown(100)
                }
            ACCESS  read-write
            STATUS  mandatory
            DESCRIPTION
                "network type"
            ::= { ospfInterfaceSetupTab  8 }

        oisAuthentication  OBJECT-TYPE
            SYNTAX   INTEGER {
                    none(1),
                    text(2),
                    md5(3),
                    na(100)
                }
            ACCESS  read-write
            STATUS  mandatory
            DESCRIPTION
                "authentication (for OSPF)"
            ::= { ospfInterfaceSetupTab  9 }

        oisTextKey  OBJECT-TYPE
            SYNTAX  DisplayString (SIZE (0..8))
            ACCESS  read-write
            STATUS  mandatory
            DESCRIPTION
                "text key string (for OSPF)"
            ::= { ospfInterfaceSetupTab  10 }

        oisMd5Key  OBJECT-TYPE
            SYNTAX  DisplayString (SIZE (0..16))
            ACCESS  read-write
            STATUS  mandatory
            DESCRIPTION
                "md5 key string (for OSPF)"
            ::= { ospfInterfaceSetupTab  11 }

        oisCommand  OBJECT-TYPE
            SYNTAX  INTEGER {
                    none(1),
                    set(2)
                }
            ACCESS  read-write
            STATUS  mandatory
            DESCRIPTION
                "interface setup command"
            ::= { ospfInterfaceSetupTab 12 }

        oisErrorCode  OBJECT-TYPE
            SYNTAX  INTEGER {
                    success(1),
                    fail-to-set(2),
                    none(100)
                }
            ACCESS  read-only
            STATUS  mandatory
            DESCRIPTION
                "interface setup error code"
            ::= { ospfInterfaceSetupTab 13 }

--IPv6

--
-- Software Info
--

-- In IPv4 version, there is an additional array called 'a_softwareInfoSummaryTable[ ]' to contain 'n_softawareInfoTable'.
-- So there is an extra layer called 'softwareInfoSummaryTable' to contain 'softawareInfoTable'.

        softawareInfoTable  OBJECT-TYPE
            SYNTAX  SEQUENCE OF SoftwareInfoEntry
            ACCESS  not-accessible
            STATUS  mandatory
            DESCRIPTION
                "Display unit sw info, active bank"
            ::= { system 60 }

        softwareInfoEntry  OBJECT-TYPE
            SYNTAX  SoftwareInfoEntry
            ACCESS  not-accessible
            STATUS  mandatory
            DESCRIPTION
                "unit model entry"
            INDEX { ccFwInfoIndex }
            ::= { softawareInfoTable 1 }

        SoftwareInfoEntry ::= SEQUENCE {
            ccFwInfoIndex               CardID,
            ccModelType                 CardModel,
            ccSwBank1Version            DisplayString,
            ccSwBank2Version            DisplayString,
            ccCurrentBank               INTEGER,
            ccNextBank                  INTEGER
        }

        ccFwInfoIndex  OBJECT-TYPE
            SYNTAX  CardID
            ACCESS  read-only
            STATUS  mandatory
            DESCRIPTION
                "xcu, and all units."
            ::= { softwareInfoEntry 1 }

        ccModelType  OBJECT-TYPE
            SYNTAX  CardModel
            ACCESS  read-only
            STATUS  mandatory
            DESCRIPTION
                "unit card model type"
            ::= { softwareInfoEntry 2 }

        ccSwBank1Version  OBJECT-TYPE
            SYNTAX  DisplayString
            ACCESS  read-only
            STATUS  mandatory
            DESCRIPTION
                "unit bank1 software version"
            ::= { softwareInfoEntry 3 }

        ccSwBank2Version  OBJECT-TYPE
            SYNTAX  DisplayString
            ACCESS  read-only
            STATUS  mandatory
            DESCRIPTION
                "unit bank2 software version"
            ::= { softwareInfoEntry 4 }

        ccCurrentBank  OBJECT-TYPE
            SYNTAX  INTEGER{
                    bank1(1),
                    bank2(2),
                    none(3)
                }
            ACCESS  read-only
            STATUS  mandatory
            DESCRIPTION
                "active bank version"
            ::= { softwareInfoEntry 5 }

        ccNextBank  OBJECT-TYPE
            SYNTAX  INTEGER{
                    bank1(1),
                    bank2(2),
                    none(3)
                }
            ACCESS  read-only
            STATUS  mandatory
            DESCRIPTION
                "next bank version"
            ::= { softwareInfoEntry 6 }


--
--      XCU Port Enable/Disable Table
--

        xcuPortEnableTable  OBJECT-TYPE
            SYNTAX  SEQUENCE OF XcuPortEnableEntry
            ACCESS  not-accessible
            STATUS  mandatory
            DESCRIPTION
                "XCU Port Enable Table"
            ::= { system 61 }

        xcuPortEnableEntry  OBJECT-TYPE
            SYNTAX  XcuPortEnableEntry
            ACCESS  not-accessible
            STATUS  mandatory
            DESCRIPTION
                "XCU Port Enable entry"
            INDEX { xcuPortEnableIndex ,
                    xcuPortEnablePortIndex }
            ::= { xcuPortEnableTable 1 }

        XcuPortEnableEntry ::= SEQUENCE {
            xcuPortEnableIndex      ChassisSlot,
            xcuPortEnablePortIndex  PortNum,
            xcuPortEnable           INTEGER
        }

        xcuPortEnableIndex  OBJECT-TYPE
            SYNTAX  ChassisSlot
            ACCESS  read-only
            STATUS  mandatory
            DESCRIPTION
                "xcu 1-2"
            ::= { xcuPortEnableEntry 1 }

        xcuPortEnablePortIndex   OBJECT-TYPE
            SYNTAX  PortNum
            ACCESS  read-only
            STATUS  mandatory
            DESCRIPTION
                "port 1-2"
            ::= { xcuPortEnableEntry 2 }

        xcuPortEnable   OBJECT-TYPE
            SYNTAX  INTEGER   {
                    disable(1),
                    enable(2)
                }
            ACCESS  read-write
            STATUS  mandatory
            DESCRIPTION
                "xcu port enable/disable"
            ::= { xcuPortEnableEntry 3 }


--
--  HD Port Enable Disable Table
--

         hdCardPortEnableTable  OBJECT-TYPE
             SYNTAX  SEQUENCE OF HdCardPortEnableEntry
             ACCESS  not-accessible
             STATUS  mandatory
             DESCRIPTION
                "Port enable/disable table"
             ::= { system 62 }

         hdCardPortEnableEntry  OBJECT-TYPE
             SYNTAX  HdCardPortEnableEntry
             ACCESS  not-accessible
             STATUS  mandatory
             DESCRIPTION
                "port enable/disable entry"
             INDEX  { hdCardIndex, hdPortIndex }
             ::= { hdCardPortEnableTable 1 }

         HdCardPortEnableEntry ::=
             SEQUENCE {
               hdCardIndex
                 UnitID,
               hdPortIndex
                 PortID,
               hdPortEnable
                 INTEGER
             }

         hdCardIndex  OBJECT-TYPE
             SYNTAX  UnitID
             ACCESS  read-only
             STATUS  mandatory
             DESCRIPTION
                "tributary card 1 to 8"
             ::= { hdCardPortEnableEntry 1 }
             
         hdPortIndex  OBJECT-TYPE
             SYNTAX  PortID
             ACCESS  read-only
             STATUS  mandatory
             DESCRIPTION
                "1 ~ 64 ports."
             ::= { hdCardPortEnableEntry 2 }             
         
         hdPortEnable  OBJECT-TYPE
             SYNTAX  INTEGER {
			             disable(1),
						 			 enable(2)
			         }
             ACCESS  read-write
             STATUS  mandatory
             DESCRIPTION
                "port enable/disable setting"
             ::= { hdCardPortEnableEntry 3 }   
    

--
--  B155/622 card MIB
--

--
--  B155/622 Granularity Table
--
        b155-622GranularityTab  OBJECT-TYPE
        SYNTAX  SEQUENCE OF  B155-622GranularityEty
            ACCESS  not-accessible
            STATUS  mandatory
            DESCRIPTION
                "B155/622 ho/lo mapping mode table"
            ::= { b155-622-card 1 }

        b155-622GranularityEty  OBJECT-TYPE
            SYNTAX  B155-622GranularityEty
            ACCESS  not-accessible
            STATUS  mandatory
            DESCRIPTION
                "An entry in the B155/622 ho/lo mapping mode table."
            INDEX { bGranularityUnit , bGranularityPort , bGranularityAug1Sts3 }
            ::= { b155-622GranularityTab 1 }


        B155-622GranularityEty ::= SEQUENCE  {
            bGranularityUnit            UnitID,
            bGranularityPort            PortID,
            bGranularityAug1Sts3        Aug1Sts3Num,
            bGranularityHo-Sts3         HoMappingType,
            bGranularityLo-Sts1-1       LoMappingType,
            bGranularityLo-Sts1-2       LoMappingType,
            bGranularityLo-Sts1-3       LoMappingType
        }

        bGranularityUnit  OBJECT-TYPE
            SYNTAX  UnitID
            ACCESS  read-only
            STATUS  mandatory
            DESCRIPTION
            "unit 1 to 4."
            ::= { b155-622GranularityEty  1 }

        bGranularityPort  OBJECT-TYPE
            SYNTAX  PortID
            ACCESS  read-only
            STATUS  mandatory
            DESCRIPTION
                "PORT #1~#2"
            ::= { b155-622GranularityEty  2 }

        bGranularityAug1Sts3  OBJECT-TYPE
            SYNTAX  Aug1Sts3Num
            ACCESS  read-only
            STATUS  mandatory
            DESCRIPTION
                "Stm1/Sts3 Path selection"
            ::= { b155-622GranularityEty  3 }

        bGranularityHo-Sts3  OBJECT-TYPE
            SYNTAX  HoMappingType
            ACCESS  read-write
            STATUS  mandatory
            DESCRIPTION
                "Ho-order mapping type selection"
            ::= { b155-622GranularityEty  4 }

        bGranularityLo-Sts1-1  OBJECT-TYPE
            SYNTAX  LoMappingType
            ACCESS  read-write
            STATUS  mandatory
            DESCRIPTION
                "Lo-order mapping type selection"
            ::= { b155-622GranularityEty  5 }

        bGranularityLo-Sts1-2  OBJECT-TYPE
            SYNTAX  LoMappingType
            ACCESS  read-write
            STATUS  mandatory
            DESCRIPTION
                "Lo-order mapping type selection"
            ::= { b155-622GranularityEty  6 }

        bGranularityLo-Sts1-3  OBJECT-TYPE
            SYNTAX  LoMappingType
            ACCESS  read-write
            STATUS  mandatory
            DESCRIPTION
                "Lo-order mapping type selection"
            ::= { b155-622GranularityEty  7 }

--
--  B155/622 Overhead Table
--
    b155-622OverheadTable  OBJECT IDENTIFIER ::= { b155-622-card 2 }

--
--  B155/622 Line Path Overhead setup
--
        bOverheadJ0Table OBJECT-TYPE
            SYNTAX  SEQUENCE OF BOverheadJ0Entry
            ACCESS  not-accessible
            STATUS  mandatory
            DESCRIPTION
                "B155/622 Overhead J0 Table"
            ::= { b155-622OverheadTable 1 }

        bOverheadJ0Entry  OBJECT-TYPE
            SYNTAX  BOverheadJ0Entry
            ACCESS  not-accessible
            STATUS  mandatory
            DESCRIPTION
                "An entry in the B155/622 Overhead J0 Table."
            INDEX { bJ0UnitIndex , bJ0PortIndex }
            ::= { bOverheadJ0Table 1 }

        BOverheadJ0Entry ::= SEQUENCE  {
            bJ0UnitIndex                UnitID,
            bJ0PortIndex                PortID,
            bOHJ0J0-Length              MsgLen,
            bOHJ0Expect-J0-Msg          DisplayString (SIZE(0..64)),
            bJ0Tx-J0-Msg                DisplayString (SIZE(0..64)),
            bJ0Rx-J0-Msg                DisplayString (SIZE(0..64)),
            bJ0Exp-J0-Msg-1Byte         INTEGER (0..255),
            bJ0Tx-J0-Msg-1Byte          INTEGER (0..255),
            bJ0Rx-J0-Msg-1Byte          INTEGER (0..255)
        }

        bJ0UnitIndex  OBJECT-TYPE
            SYNTAX  UnitID
            ACCESS  read-only
            STATUS  mandatory
            DESCRIPTION
            "unit 1 to 4."
            ::= { bOverheadJ0Entry  1 }

        bJ0PortIndex  OBJECT-TYPE
            SYNTAX  PortID
            ACCESS  read-only
            STATUS  mandatory
            DESCRIPTION
                "PORT #1~#2"
            ::= { bOverheadJ0Entry  2 }

        bOHJ0J0-Length  OBJECT-TYPE
            SYNTAX  MsgLen
            ACCESS  read-write
            STATUS  mandatory
            DESCRIPTION
                "The length of J0."
            ::= { bOverheadJ0Entry  3 }

        bOHJ0Expect-J0-Msg  OBJECT-TYPE
            SYNTAX  DisplayString (SIZE(0..64))
            ACCESS  read-write
            STATUS  mandatory
            DESCRIPTION
                "The expected J0 message."
            ::= { bOverheadJ0Entry  4 }

        bJ0Tx-J0-Msg  OBJECT-TYPE
            SYNTAX  DisplayString (SIZE(0..64))
            ACCESS  read-write
            STATUS  mandatory
            DESCRIPTION
                "The transmitted J0 message."
            ::= { bOverheadJ0Entry  5 }

        bJ0Rx-J0-Msg  OBJECT-TYPE
            SYNTAX  DisplayString (SIZE(0..64))
            ACCESS  read-only
            STATUS  mandatory
            DESCRIPTION
                "The received J0 message."
            ::= { bOverheadJ0Entry  6 }

        bJ0Exp-J0-Msg-1Byte  OBJECT-TYPE
            SYNTAX  INTEGER (0..255)
            ACCESS  read-write
            STATUS  mandatory
            DESCRIPTION
                "The expected J0 message (1Byte)."
            ::= { bOverheadJ0Entry  7 }

        bJ0Tx-J0-Msg-1Byte  OBJECT-TYPE
            SYNTAX  INTEGER (0..255)
            ACCESS  read-write
            STATUS  mandatory
            DESCRIPTION
                "The transmitted J0 message (1Byte)."
            ::= { bOverheadJ0Entry  8 }

        bJ0Rx-J0-Msg-1Byte  OBJECT-TYPE
            SYNTAX  INTEGER (0..255)
            ACCESS  read-only
            STATUS  mandatory
            DESCRIPTION
                "The received J0 message (1Byte)."
            ::= { bOverheadJ0Entry  9 }

--
--  B155/622 High Order Path Overhead J1 and C2 setup
--
        bOverheadJ1C2Table OBJECT-TYPE
            SYNTAX  SEQUENCE OF BJ1C2Entry
            ACCESS  not-accessible
            STATUS  mandatory
            DESCRIPTION
                "B155/622 Overhead J1 & C2 Table"
            ::= { b155-622OverheadTable 2 }

        bJ1C2Entry  OBJECT-TYPE
            SYNTAX  BJ1C2Entry
            ACCESS  not-accessible
            STATUS  mandatory
            DESCRIPTION
                "An entry in the B155/622 Overhead J1 &C2 Table."
            INDEX { bJ1C2UnitIndex , bJ1C2PortIndex ,
                    bJ1C2Aug1Sts3Index , bJ1C2Vc3Sts1Index }
            ::= { bOverheadJ1C2Table 1 }

        BJ1C2Entry ::= SEQUENCE  {
            bJ1C2UnitIndex              UnitID,
            bJ1C2PortIndex              PortID,
            bJ1C2Aug1Sts3Index          Aug1Sts3Num,
            bJ1C2Vc3Sts1Index           Vc3Sts1Num,
            b155-622OHJ1C2J1-Length     MsgLen,
            bJ1C2Expect-J1-Msg          DisplayString (SIZE(0..64)),
            bJ1C2Tx-J1-Msg              DisplayString (SIZE(0..64)),
            bJ1C2Rx-J1-Msg              DisplayString (SIZE(0..64)),
            bJ1C2C2-EPSL                INTEGER(0..255),
            bJ1C2Exp-J1-Msg-1Byte       INTEGER (0..255),
            bJ1C2Tx-J1-Msg-1Byte        INTEGER (0..255),
            bJ1C2Rx-J1-Msg-1Byte        INTEGER (0..255),
            bJ1C2C2-TxPSL               INTEGER(0..255),
            bJ1C2C2-RxPSL               INTEGER(0..255)

    }

        bJ1C2UnitIndex  OBJECT-TYPE
            SYNTAX  UnitID
            ACCESS  read-only
            STATUS  mandatory
            DESCRIPTION
            "unit 1 to 4."
            ::= { bJ1C2Entry  1 }

        bJ1C2PortIndex  OBJECT-TYPE
            SYNTAX  PortID
            ACCESS  read-only
            STATUS  mandatory
            DESCRIPTION
                "PORT #1~#2"
            ::= { bJ1C2Entry  2 }

        bJ1C2Aug1Sts3Index  OBJECT-TYPE
            SYNTAX  Aug1Sts3Num
            ACCESS  read-only
            STATUS  mandatory
            DESCRIPTION
                "AUG1/STS3 index"
            ::= { bJ1C2Entry  3 }

        bJ1C2Vc3Sts1Index  OBJECT-TYPE
            SYNTAX  Vc3Sts1Num
            ACCESS  read-only
            STATUS  mandatory
            DESCRIPTION
                "VC3/STS1 index"
            ::= { bJ1C2Entry  4 }

        b155-622OHJ1C2J1-Length  OBJECT-TYPE
            SYNTAX  MsgLen
            ACCESS  read-write
            STATUS  mandatory
            DESCRIPTION
                "The length of J1."
            ::= { bJ1C2Entry  5 }

        bJ1C2Expect-J1-Msg  OBJECT-TYPE
            SYNTAX  DisplayString (SIZE(0..64))
            ACCESS  read-write
            STATUS  mandatory
            DESCRIPTION
                "The expected J1 message."
            ::= { bJ1C2Entry  6 }

        bJ1C2Tx-J1-Msg  OBJECT-TYPE
            SYNTAX  DisplayString (SIZE(0..64))
            ACCESS  read-write
            STATUS  mandatory
            DESCRIPTION
                "The transmitted J1 message."
            ::= { bJ1C2Entry  7 }

        bJ1C2Rx-J1-Msg  OBJECT-TYPE
            SYNTAX  DisplayString (SIZE(0..64))
            ACCESS  read-only
            STATUS  mandatory
            DESCRIPTION
                "The received J1 message."
            ::= { bJ1C2Entry  8 }

        bJ1C2C2-EPSL  OBJECT-TYPE
            SYNTAX  INTEGER(0..255)
            ACCESS  read-write
            STATUS  mandatory
            DESCRIPTION
                "Expected PSL"
            ::= { bJ1C2Entry  9 }

        bJ1C2Exp-J1-Msg-1Byte  OBJECT-TYPE
            SYNTAX  INTEGER (0..255)
            ACCESS  read-write
            STATUS  mandatory
            DESCRIPTION
                "The expected J1 message (1Byte)."
            ::= { bJ1C2Entry  10 }

        bJ1C2Tx-J1-Msg-1Byte  OBJECT-TYPE
            SYNTAX  INTEGER (0..255)
            ACCESS  read-write
            STATUS  mandatory
            DESCRIPTION
                "The transmitted J1 message (1Byte)."
            ::= { bJ1C2Entry  11 }

        bJ1C2Rx-J1-Msg-1Byte  OBJECT-TYPE
            SYNTAX  INTEGER (0..255)
            ACCESS  read-only
            STATUS  mandatory
            DESCRIPTION
                "The received J1 message (1Byte)."
            ::= { bJ1C2Entry  12 }

        bJ1C2C2-TxPSL  OBJECT-TYPE
            SYNTAX  INTEGER(0..255)
            ACCESS  read-write
            STATUS  mandatory
            DESCRIPTION
                "The Tx PSL(C2)"
            ::= { bJ1C2Entry  13 }

        bJ1C2C2-RxPSL  OBJECT-TYPE
            SYNTAX  INTEGER(0..255)
            ACCESS  read-only
            STATUS  mandatory
            DESCRIPTION
                "The Rx PSL(C2)"
            ::= { bJ1C2Entry  14 }

--
--  B155/622 Dcc Channel Table
--
        b155-622DccChannelTab  OBJECT-TYPE
            SYNTAX  SEQUENCE OF  B155-622DccChannelEty
            ACCESS  not-accessible
            STATUS  mandatory
            DESCRIPTION
                "B155/622 ho/lo mapping mode table"
            ::= { b155-622-card 3 }

        b155-622DccChannelEty  OBJECT-TYPE
            SYNTAX  B155-622DccChannelEty
            ACCESS  not-accessible
            STATUS  mandatory
            DESCRIPTION
                "An entry in the B155/622 DCC channel table."
            INDEX { bDccChUnit , bDccChPort }
            ::= { b155-622DccChannelTab 1 }


        B155-622DccChannelEty ::= SEQUENCE  {
            bDccChUnit                  UnitID,
            bDccChPort                  PortID,
            bDccChDccChannels           INTEGER
        }

        bDccChUnit  OBJECT-TYPE
            SYNTAX  UnitID
            ACCESS  read-only
            STATUS  mandatory
            DESCRIPTION
            "unit 1 to 4."
            ::= { b155-622DccChannelEty  1 }

        bDccChPort  OBJECT-TYPE
            SYNTAX  PortID
            ACCESS  read-only
            STATUS  mandatory
            DESCRIPTION
                "PORT #1~#2"
            ::= { b155-622DccChannelEty  2 }

        bDccChDccChannels  OBJECT-TYPE
            SYNTAX  INTEGER {
                    d1-d3(1),
                    d4-d12(2),
                    d1-d12(3),
                    off(4)
                }
            ACCESS  read-write
            STATUS  mandatory
            DESCRIPTION
                "dcc channels"
            ::= { b155-622DccChannelEty  3 }

--
--  B155/622 Protection Table
--
        b155-622ProtectionTab  OBJECT-TYPE
            SYNTAX  SEQUENCE OF  B155-622ProtectionEty
            ACCESS  not-accessible
            STATUS  mandatory
            DESCRIPTION
                "B155/622 protection table"
            ::= { b155-622-card 4 }

        b155-622ProtectionEty  OBJECT-TYPE
            SYNTAX  B155-622ProtectionEty
            ACCESS  not-accessible
            STATUS  mandatory
            DESCRIPTION
                "An entry in the B155/622 Protection table."
            INDEX { bProtectUnit , bProtectPort }
            ::= { b155-622ProtectionTab 1 }


        B155-622ProtectionEty ::= SEQUENCE  {
            bProtectUnit                UnitID,
            bProtectPort                PortID,
            bProtectMspEnable           INTEGER,
            bProtectMspRevertive        INTEGER,
            bProtectMspDirection        INTEGER,
            bProtectSncpEnable          INTEGER,
            bProtectSncpRevertive       INTEGER,
            bProtectSncpMode            INTEGER
        }

        bProtectUnit  OBJECT-TYPE
            SYNTAX  UnitID
            ACCESS  read-only
            STATUS  mandatory
            DESCRIPTION
            "unit 1 to 4."
            ::= { b155-622ProtectionEty  1 }

        bProtectPort  OBJECT-TYPE
            SYNTAX  PortID
            ACCESS  read-only
            STATUS  mandatory
            DESCRIPTION
                "PORT #1~#2"
            ::= { b155-622ProtectionEty  2 }

        bProtectMspEnable  OBJECT-TYPE
            SYNTAX  INTEGER {
                    off(1),
                    on(2)
                }
            ACCESS  read-write
            STATUS  mandatory
            DESCRIPTION
                "MSP 1+1 OFF or ON"
            ::= { b155-622ProtectionEty 3 }

        bProtectMspRevertive  OBJECT-TYPE
            SYNTAX  INTEGER {
                    non-revertive(1),
                    revertive(2)
                }
            ACCESS  read-write
            STATUS  mandatory
            DESCRIPTION
                "MSP 1+1 revertive or non-revertive"
            ::= { b155-622ProtectionEty 4 }

        bProtectMspDirection  OBJECT-TYPE
            SYNTAX  INTEGER {
                    uni-directional(1),
                    bi-directional(2)
                }
            ACCESS  read-write
            STATUS  mandatory
            DESCRIPTION
                "MSP 1+1 direction"
            ::= { b155-622ProtectionEty 5 }

        bProtectSncpEnable  OBJECT-TYPE
            SYNTAX  INTEGER {
                    off(1),
                    on(2)
                }
            ACCESS  read-only
            STATUS  mandatory
            DESCRIPTION
                "SNCP/UPSR OFF or ON"
            ::= { b155-622ProtectionEty 6 }

        bProtectSncpRevertive  OBJECT-TYPE
            SYNTAX  INTEGER {
                    non-revertive(1),
                    revertive(2)
                }
            ACCESS  read-write
            STATUS  mandatory
            DESCRIPTION
                "SNCP/UPSR revertive or non-revertive"
            ::= { b155-622ProtectionEty 7 }

        bProtectSncpMode  OBJECT-TYPE
            SYNTAX  INTEGER {
                    intrusive(1),
                    non-intrusive(2)
                }
            ACCESS  read-write
            STATUS  mandatory
            DESCRIPTION
                "SNCP/UPSR mode"
            ::= { b155-622ProtectionEty 8 }

--
--  B155/622 MSP Aps Command Table
--
        b155-622MspApsCmdTab  OBJECT-TYPE
            SYNTAX  SEQUENCE OF  B155-622MspApsCmdEty
            ACCESS  not-accessible
            STATUS  mandatory
            DESCRIPTION
                "B155/622 protection table"
            ::= { b155-622-card 5 }

        b155-622MspApsCmdEty  OBJECT-TYPE
            SYNTAX  B155-622MspApsCmdEty
            ACCESS  not-accessible
            STATUS  mandatory
            DESCRIPTION
                "An entry in the B155/622 MSP aps command table."
            INDEX { bMspApsCmdUnit , bMspApsCmdPort }
            ::= { b155-622MspApsCmdTab 1 }


        B155-622MspApsCmdEty ::= SEQUENCE  {
            bMspApsCmdUnit              UnitID,
            bMspApsCmdPort              PortID,
            bMspApsCmdReqCmd            INTEGER
        }

        bMspApsCmdUnit  OBJECT-TYPE
            SYNTAX  UnitID
            ACCESS  read-only
            STATUS  mandatory
            DESCRIPTION
            "unit 1 to 4."
            ::= { b155-622MspApsCmdEty  1 }

        bMspApsCmdPort  OBJECT-TYPE
            SYNTAX  PortID
            ACCESS  read-only
            STATUS  mandatory
            DESCRIPTION
                "PORT #1~#2"
            ::= { b155-622MspApsCmdEty  2 }

        bMspApsCmdReqCmd  OBJECT-TYPE
            SYNTAX  INTEGER {
                    clear(1),
                    lockout-of-protection(2),
                    fs-to-unit-1(3),
                    fs-to-unit-2(4),
                    fs-to-unit-3(5),
                    fs-to-unit-4(6),
                    ms-to-unit-1(11),
                    ms-to-unit-2(12),
                    ms-to-unit-3(13),
                    ms-to-unit-4(14)
                }
            ACCESS  read-write
            STATUS  mandatory
            DESCRIPTION
                "MSP APS command request"
            ::= { b155-622MspApsCmdEty 3 }

--
--  B155/622 MSP Status Table
--
        b155-622MspStatusTab    OBJECT-TYPE
            SYNTAX  SEQUENCE OF  B155-622MspStatusEty
            ACCESS  not-accessible
            STATUS  mandatory
            DESCRIPTION
                "B155/622 Status table"
            ::= { b155-622-card 6 }

        b155-622MspStatusEty  OBJECT-TYPE
            SYNTAX  B155-622MspStatusEty
            ACCESS  not-accessible
            STATUS  mandatory
            DESCRIPTION
                "An entry in the B155/622 MSP status table."
            INDEX { bMspStatusUnit , bMspStatusPort }
            ::= { b155-622MspStatusTab 1 }


        B155-622MspStatusEty ::= SEQUENCE  {
            bMspStatusUnit              UnitID,
            bMspStatusPort              PortID,
            bMspStatusActivePath        INTEGER
        }

        bMspStatusUnit  OBJECT-TYPE
            SYNTAX  UnitID
            ACCESS  read-only
            STATUS  mandatory
            DESCRIPTION
            "unit 1 to 4."
            ::= { b155-622MspStatusEty  1 }

        bMspStatusPort  OBJECT-TYPE
            SYNTAX  PortID
            ACCESS  read-only
            STATUS  mandatory
            DESCRIPTION
                "PORT #1~#2"
            ::= { b155-622MspStatusEty  2 }

        bMspStatusActivePath  OBJECT-TYPE
            SYNTAX  INTEGER {
                    unit-1(1),
                    unit-2(2),
                    unit-3(3),
                    unit-4(4),
                    na(9)
                }
            ACCESS  read-only
            STATUS  mandatory
            DESCRIPTION
                "MSP active path"
            ::= { b155-622MspStatusEty 3 }

--
--  B155/622 Physical Layer Alarm Table
--

    b155-622AlarmSetupTable OBJECT IDENTIFIER ::= { b155-622-card 7 }

--
--  B155/622 Physical Layer Alarm Mask Table
--

    bPHYTable   OBJECT IDENTIFIER ::= { b155-622AlarmSetupTable 1 }

        bPHYMaskTable  OBJECT-TYPE
            SYNTAX  SEQUENCE OF BPHYMaskEntry
            ACCESS  not-accessible
            STATUS  mandatory
            DESCRIPTION
                "Physical layer Alarm Mask Table"
            ::= { bPHYTable 1 }

        bPHYMaskEntry  OBJECT-TYPE
            SYNTAX  BPHYMaskEntry
            ACCESS  not-accessible
            STATUS  mandatory
            DESCRIPTION
                "Physical Alarm Mask entry"
            INDEX { bPHYMaskUnitIndex , bPHYMaskPortIndex }
            ::= { bPHYMaskTable 1 }

        BPHYMaskEntry ::= SEQUENCE {
            bPHYMaskUnitIndex           UnitID,
            bPHYMaskPortIndex           PortNum,
            bPHYLayerMaskLOS            INTEGER
        }

        bPHYMaskUnitIndex  OBJECT-TYPE
            SYNTAX  UnitID
            ACCESS  read-only
            STATUS  mandatory
            DESCRIPTION
                "Alarm Mask Unit index"
            ::= { bPHYMaskEntry 1 }

        bPHYMaskPortIndex  OBJECT-TYPE
            SYNTAX  PortNum
            ACCESS  read-only
            STATUS  mandatory
            DESCRIPTION
                "Alarm Mask Port index"
            ::= { bPHYMaskEntry 2 }

        bPHYLayerMaskLOS  OBJECT-TYPE
            SYNTAX  INTEGER {
                    disable(1),
                    enable(2)
                }
            ACCESS  read-write
            STATUS  mandatory
            DESCRIPTION
                "Alarm Mask Enable/Disable"
            ::= { bPHYMaskEntry 3 }
--
--  B155/622 Physical Layer Alarm Relay Table
--
        bPHYRelayTable  OBJECT-TYPE
            SYNTAX  SEQUENCE OF BPHYRelayEntry
            ACCESS  not-accessible
            STATUS  mandatory
            DESCRIPTION
                "Physical layer Alarm Relay Table"
            ::= { bPHYTable 2 }

        bPHYRelayEntry  OBJECT-TYPE
            SYNTAX  BPHYRelayEntry
            ACCESS  not-accessible
            STATUS  mandatory
            DESCRIPTION
                "Physical Alarm entry"
            INDEX { bPHYRelayUnitIndex , bPHYRelayPortIndex }
            ::= { bPHYRelayTable 1 }

        BPHYRelayEntry ::= SEQUENCE {
            bPHYRelayUnitIndex          UnitID,
            bPHYRelayPortIndex          PortNum,
            bbPHYRelayLOS               INTEGER
        }

        bPHYRelayUnitIndex  OBJECT-TYPE
            SYNTAX  UnitID
            ACCESS  read-only
            STATUS  mandatory
            DESCRIPTION
                "Alarm Relay Unit index"
            ::= { bPHYRelayEntry 1 }

        bPHYRelayPortIndex  OBJECT-TYPE
            SYNTAX  PortNum
            ACCESS  read-only
            STATUS  mandatory
            DESCRIPTION
                "Alarm Relay Port index"
            ::= { bPHYRelayEntry 2 }

        bbPHYRelayLOS  OBJECT-TYPE
            SYNTAX  INTEGER {
                    disable(1),
                    enable(2)
                }
            ACCESS  read-write
            STATUS  mandatory
            DESCRIPTION
                "Alarm Relay Enable/Disable"
            ::= { bPHYRelayEntry 3 }

--
--  B155/622 Physical Layer Alarm Severity Table
--

        bPHYSvrityTable  OBJECT-TYPE
            SYNTAX  SEQUENCE OF BPHYSvrityEntry
            ACCESS  not-accessible
            STATUS  mandatory
            DESCRIPTION
                "Physical layer Alarm Severity Table"
            ::= { bPHYTable 3 }

        bPHYSvrityEntry  OBJECT-TYPE
            SYNTAX  BPHYSvrityEntry
            ACCESS  not-accessible
            STATUS  mandatory
            DESCRIPTION
                "Physical Alarm entry"
            INDEX { bPHYSvrityUnitIndex }
            ::= { bPHYSvrityTable 1 }

        BPHYSvrityEntry ::=  SEQUENCE {
            bPHYSvrityUnitIndex         UnitID,
            bPHYSvrityLOS               Severity
        }

        bPHYSvrityUnitIndex  OBJECT-TYPE
            SYNTAX  UnitID
            ACCESS  read-only
            STATUS  mandatory
            DESCRIPTION
                "Alarm Severity Unit index"
            ::= { bPHYSvrityEntry 1 }

        bPHYSvrityLOS  OBJECT-TYPE
            SYNTAX  Severity
            ACCESS  read-write
            STATUS  mandatory
            DESCRIPTION
                "Alarm Severity Type"
            ::= { bPHYSvrityEntry 2 }

--
--  B155/622 RS-Section Layer Alarm Mask Table
--

    bRS-SectionTable   OBJECT IDENTIFIER ::= { b155-622AlarmSetupTable 2 }

        bRS-SectionMaskTable  OBJECT-TYPE
            SYNTAX  SEQUENCE OF BRS-SectionMaskEntry
            ACCESS  not-accessible
            STATUS  mandatory
            DESCRIPTION
                "RS-Section layer Alarm Mask Table"
            ::= { bRS-SectionTable 1 }

        bRS-SectionMaskEntry  OBJECT-TYPE
            SYNTAX  BRS-SectionMaskEntry
            ACCESS  not-accessible
            STATUS  mandatory
            DESCRIPTION
                "RS-Section Alarm entry"
            INDEX { bRS-SectionMaskUnitIndex , bRS-SectionMaskPortIndex }
            ::= { bRS-SectionMaskTable 1 }

        BRS-SectionMaskEntry ::= SEQUENCE {
            bRS-SectionMaskUnitIndex    UnitID,
            bRS-SectionMaskPortIndex    PortNum,
            bRS-SectionMaskLOF          INTEGER,
            bRS-SectionMaskBIP          INTEGER,
            bRS-SectionMaskTIM          INTEGER
        }

        bRS-SectionMaskUnitIndex  OBJECT-TYPE
            SYNTAX  UnitID
            ACCESS  read-only
            STATUS  mandatory
            DESCRIPTION
                "Unit index"
            ::= { bRS-SectionMaskEntry 1 }

        bRS-SectionMaskPortIndex  OBJECT-TYPE
            SYNTAX  PortNum
            ACCESS  read-only
            STATUS  mandatory
            DESCRIPTION
                "Port index"
            ::= { bRS-SectionMaskEntry 2 }

        bRS-SectionMaskLOF  OBJECT-TYPE
            SYNTAX  INTEGER {
                    disable(1),
                    enable(2)
                }
            ACCESS  read-write
            STATUS  mandatory
            DESCRIPTION
                "LOF Alarm Mask Enable/Disable"
            ::= { bRS-SectionMaskEntry 3 }

        bRS-SectionMaskBIP  OBJECT-TYPE
            SYNTAX  INTEGER {
                    disable(1),
                    enable(2)
                }
            ACCESS  read-write
            STATUS  mandatory
            DESCRIPTION
                "BIP Alarm Mask Enable/Disable"
            ::= { bRS-SectionMaskEntry 4 }

        bRS-SectionMaskTIM  OBJECT-TYPE
            SYNTAX  INTEGER {
                    disable(1),
                    enable(2)
                }
            ACCESS  read-write
            STATUS  mandatory
            DESCRIPTION
                "TIM Alarm Mask Enable/Disable"
            ::= { bRS-SectionMaskEntry 5 }
--
--  B155/622 RS-Section Layer Alarm Relay Table
--
        bRS-SectionRelayTable  OBJECT-TYPE
            SYNTAX  SEQUENCE OF BRS-SectionRelayEntry
            ACCESS  not-accessible
            STATUS  mandatory
            DESCRIPTION
                "RS-Sectionsical layer Alarm Mask Table"
            ::= { bRS-SectionTable 2 }

        bRS-SectionRelayEntry  OBJECT-TYPE
            SYNTAX  BRS-SectionRelayEntry
            ACCESS  not-accessible
            STATUS  mandatory
            DESCRIPTION
                "RS-Sectionsical Alarm entry"
            INDEX { bRS-SectionRelayUnitIdx , bRS-SectionRelayPortIdx }
            ::= { bRS-SectionRelayTable 1 }

        BRS-SectionRelayEntry ::= SEQUENCE {
            bRS-SectionRelayUnitIdx     UnitID,
            bRS-SectionRelayPortIdx     PortNum,
            bRS-SectionRelayLOF         INTEGER,
            bRS-SectionRelayBIP         INTEGER,
            bRS-SectionRelayTIM         INTEGER
        }

        bRS-SectionRelayUnitIdx  OBJECT-TYPE
            SYNTAX  UnitID
            ACCESS  read-only
            STATUS  mandatory
            DESCRIPTION
                "Unit index"
            ::= { bRS-SectionRelayEntry 1 }

        bRS-SectionRelayPortIdx  OBJECT-TYPE
            SYNTAX  PortNum
            ACCESS  read-only
            STATUS  mandatory
            DESCRIPTION
                "Alarm Port index"
            ::= { bRS-SectionRelayEntry 2 }

        bRS-SectionRelayLOF  OBJECT-TYPE
            SYNTAX  INTEGER {
                    disable(1),
                    enable(2)
                }
            ACCESS  read-write
            STATUS  mandatory
            DESCRIPTION
                "LOF Alarm Relay Enable/Disable"
            ::= { bRS-SectionRelayEntry 3 }

        bRS-SectionRelayBIP  OBJECT-TYPE
            SYNTAX  INTEGER {
                    disable(1),
                    enable(2)
                }
            ACCESS  read-write
            STATUS  mandatory
            DESCRIPTION
                "BIP Alarm Relay Enable/Disable"
            ::= { bRS-SectionRelayEntry 4 }

        bRS-SectionRelayTIM  OBJECT-TYPE
            SYNTAX  INTEGER {
                    disable(1),
                    enable(2)
                }
            ACCESS  read-write
            STATUS  mandatory
            DESCRIPTION
                "TIM Alarm Relay Enable/Disable"
            ::= { bRS-SectionRelayEntry 5 }

--
--  B155/622 RS-Section Layer Alarm Severity Table
--

        bRS-SectionSvrityTable  OBJECT-TYPE
            SYNTAX  SEQUENCE OF BRS-SectionSvrityEntry
            ACCESS  not-accessible
            STATUS  mandatory
            DESCRIPTION
                "RS-Sectionsical layer Alarm Mask Table"
            ::= { bRS-SectionTable 3 }

        bRS-SectionSvrityEntry  OBJECT-TYPE
            SYNTAX  BRS-SectionSvrityEntry
            ACCESS  not-accessible
            STATUS  mandatory
            DESCRIPTION
                "RS-Sectionsical Alarm entry"
            INDEX { bRS-SectionSvrityUnitIdx }
            ::= { bRS-SectionSvrityTable 1 }

        BRS-SectionSvrityEntry ::= SEQUENCE {
            bRS-SectionSvrityUnitIdx    UnitID,
            bRS-SectionSvrityLOF        Severity,
            bRS-SectionSvrityBIP        Severity,
            bRS-SectionSvrityTIM        Severity
        }

        bRS-SectionSvrityUnitIdx  OBJECT-TYPE
            SYNTAX  UnitID
            ACCESS  read-only
            STATUS  mandatory
            DESCRIPTION
                "Unit index"
            ::= { bRS-SectionSvrityEntry 1 }

        bRS-SectionSvrityLOF  OBJECT-TYPE
            SYNTAX  Severity
            ACCESS  read-write
            STATUS  mandatory
            DESCRIPTION
                "LOF Alarm Severity Selection"
            ::= { bRS-SectionSvrityEntry 2 }

        bRS-SectionSvrityBIP  OBJECT-TYPE
            SYNTAX  Severity
            ACCESS  read-write
            STATUS  mandatory
            DESCRIPTION
                "BIP Alarm Severity Selection"
            ::= { bRS-SectionSvrityEntry 3 }

        bRS-SectionSvrityTIM  OBJECT-TYPE
            SYNTAX  Severity
            ACCESS  read-write
            STATUS  mandatory
            DESCRIPTION
                "TIM Alarm Severity Selection"
            ::= { bRS-SectionSvrityEntry 4 }

--
--  B155/622 MS-Line Layer Alarm Mask Table
--

    bMS-LineTable   OBJECT IDENTIFIER ::= { b155-622AlarmSetupTable 3 }

        bMS-LineMaskTable  OBJECT-TYPE
            SYNTAX  SEQUENCE OF BMS-LineMaskEntry
            ACCESS  not-accessible
            STATUS  mandatory
            DESCRIPTION
                "MS-Line layer Alarm Mask Table"
            ::= { bMS-LineTable 1 }

        bMS-LineMaskEntry  OBJECT-TYPE
            SYNTAX  BMS-LineMaskEntry
            ACCESS  not-accessible
            STATUS  mandatory
            DESCRIPTION
                "MS-Linesical Alarm entry"
            INDEX { bMS-LineMaskUnitIdx , bMS-LineMaskPortIdx }
            ::= { bMS-LineMaskTable 1 }

        BMS-LineMaskEntry ::= SEQUENCE {
            bMS-LineMaskUnitIdx         UnitID,
            bMS-LineMaskPortIdx         PortNum,
            bMS-LineMaskAIS             INTEGER,
            bMS-LineMaskRDI             INTEGER,
            bMS-LineMaskBIP             INTEGER,
            bMS-LineMaskREI             INTEGER,
            bMS-LineMaskSD              INTEGER,
            bMS-LineMaskSF              INTEGER
        }

        bMS-LineMaskUnitIdx  OBJECT-TYPE
            SYNTAX  UnitID
            ACCESS  read-only
            STATUS  mandatory
            DESCRIPTION
                "Unit index"
            ::= { bMS-LineMaskEntry 1 }

        bMS-LineMaskPortIdx  OBJECT-TYPE
            SYNTAX  PortNum
            ACCESS  read-only
            STATUS  mandatory
            DESCRIPTION
                "Port index"
            ::= { bMS-LineMaskEntry 2 }

        bMS-LineMaskAIS  OBJECT-TYPE
            SYNTAX  INTEGER {
                    disable(1),
                    enable(2)
                }
            ACCESS  read-write
            STATUS  mandatory
            DESCRIPTION
                "AIS Alarm Mask Enable/Disable"
            ::= { bMS-LineMaskEntry 3 }

        bMS-LineMaskRDI  OBJECT-TYPE
            SYNTAX  INTEGER {
                    disable(1),
                    enable(2)
                }
            ACCESS  read-write
            STATUS  mandatory
            DESCRIPTION
                "RDI Alarm Mask Enable/Disable"
            ::= { bMS-LineMaskEntry 4 }

        bMS-LineMaskBIP  OBJECT-TYPE
            SYNTAX  INTEGER {
                    disable(1),
                    enable(2)
                }
            ACCESS  read-write
            STATUS  mandatory
            DESCRIPTION
                "BIP Alarm Mask Enable/Disable"
            ::= { bMS-LineMaskEntry 5 }

        bMS-LineMaskREI  OBJECT-TYPE
            SYNTAX  INTEGER {
                    disable(1),
                    enable(2)
                }
            ACCESS  read-write
            STATUS  mandatory
            DESCRIPTION
                "REI Alarm Mask Enable/Disable"
            ::= { bMS-LineMaskEntry 6 }

        bMS-LineMaskSD  OBJECT-TYPE
            SYNTAX  INTEGER {
                    disable(1),
                    enable(2)
                }
            ACCESS  read-write
            STATUS  mandatory
            DESCRIPTION
                "SD Alarm Mask Enable/Disable"
            ::= { bMS-LineMaskEntry 7 }

        bMS-LineMaskSF  OBJECT-TYPE
            SYNTAX  INTEGER {
                    disable(1),
                    enable(2)
                }
            ACCESS  read-write
            STATUS  mandatory
            DESCRIPTION
                "SF Alarm Mask Enable/Disable"
            ::= { bMS-LineMaskEntry 8 }
--
--  B155/622 MS-Line Layer Alarm Relay Table
--
        bMS-LineRelayTable  OBJECT-TYPE
            SYNTAX  SEQUENCE OF BMS-LineRelayEntry
            ACCESS  not-accessible
            STATUS  mandatory
            DESCRIPTION
                "MS-Line layer Alarm Mask Table"
            ::= { bMS-LineTable 2 }

        bMS-LineRelayEntry  OBJECT-TYPE
            SYNTAX  BMS-LineRelayEntry
            ACCESS  not-accessible
            STATUS  mandatory
            DESCRIPTION
                "MS-Line Alarm entry"
            INDEX { bMS-LineRelayUnitIdx , bMS-LineRelayPortIdx }
            ::= { bMS-LineRelayTable 1 }

        BMS-LineRelayEntry ::= SEQUENCE {
            bMS-LineRelayUnitIdx        UnitID,
            bMS-LineRelayPortIdx        PortNum,
            bMS-LineRelayAIS            INTEGER,
            bMS-LineRelayRDI            INTEGER,
            bMS-LineRelayBIP            INTEGER,
            bMS-LineRelayREI            INTEGER,
            bMS-LineRelaySD             INTEGER,
            bMS-LineRelaySF             INTEGER
        }

        bMS-LineRelayUnitIdx  OBJECT-TYPE
            SYNTAX  UnitID
            ACCESS  read-only
            STATUS  mandatory
            DESCRIPTION
                "Unit index"
            ::= { bMS-LineRelayEntry 1 }

        bMS-LineRelayPortIdx  OBJECT-TYPE
            SYNTAX  PortNum
            ACCESS  read-only
            STATUS  mandatory
            DESCRIPTION
                "Port index"
            ::= { bMS-LineRelayEntry 2 }

        bMS-LineRelayAIS  OBJECT-TYPE
            SYNTAX  INTEGER {
                    disable(1),
                    enable(2)
                }
            ACCESS  read-write
            STATUS  mandatory
            DESCRIPTION
                "AIS Alarm Relay Enable/Disable"
            ::= { bMS-LineRelayEntry 3 }

        bMS-LineRelayRDI  OBJECT-TYPE
            SYNTAX  INTEGER {
                    disable(1),
                    enable(2)
                }
            ACCESS  read-write
            STATUS  mandatory
            DESCRIPTION
                "RDI Alarm Relay Enable/Disable"
            ::= { bMS-LineRelayEntry 4 }

        bMS-LineRelayBIP  OBJECT-TYPE
            SYNTAX  INTEGER {
                    disable(1),
                    enable(2)
                }
            ACCESS  read-write
            STATUS  mandatory
            DESCRIPTION
                "BIP Alarm Relay Enable/Disable"
            ::= { bMS-LineRelayEntry 5 }

        bMS-LineRelayREI  OBJECT-TYPE
            SYNTAX  INTEGER {
                    disable(1),
                    enable(2)
                }
            ACCESS  read-write
            STATUS  mandatory
            DESCRIPTION
                "REI Alarm Relay Enable/Disable"
            ::= { bMS-LineRelayEntry 6 }

        bMS-LineRelaySD  OBJECT-TYPE
            SYNTAX  INTEGER {
                    disable(1),
                    enable(2)
                }
            ACCESS  read-write
            STATUS  mandatory
            DESCRIPTION
                "SD Alarm Relay Enable/Disable"
            ::= { bMS-LineRelayEntry 7 }

        bMS-LineRelaySF  OBJECT-TYPE
            SYNTAX  INTEGER {
                    disable(1),
                    enable(2)
                }
            ACCESS  read-write
            STATUS  mandatory
            DESCRIPTION
                "SF Alarm Relay Enable/Disable"
            ::= { bMS-LineRelayEntry 8 }

--
--  B155/622 MS-Line Layer Alarm Severity Table
--

        bMS-LineSvrityTable  OBJECT-TYPE
            SYNTAX  SEQUENCE OF BMS-LineSvrityEntry
            ACCESS  not-accessible
            STATUS  mandatory
            DESCRIPTION
                "MS-Line layer Alarm Severity Table"
            ::= { bMS-LineTable 3 }

        bMS-LineSvrityEntry  OBJECT-TYPE
            SYNTAX  BMS-LineSvrityEntry
            ACCESS  not-accessible
            STATUS  mandatory
            DESCRIPTION
                "MS-Line Alarm entry"
            INDEX { bMS-LineSvrityUnitIdx }
            ::= { bMS-LineSvrityTable 1 }

        BMS-LineSvrityEntry ::= SEQUENCE {
            bMS-LineSvrityUnitIdx       UnitID,
            bMS-LineSvrityAIS           Severity,
            bMS-LineSvrityRDI           Severity,
            bMS-LineSvrityBIP           Severity,
            bMS-LineSvrityREI           Severity,
            bMS-LineSvritySD            Severity,
            bMS-LineSvritySF            Severity
        }

        bMS-LineSvrityUnitIdx  OBJECT-TYPE
            SYNTAX  UnitID
            ACCESS  read-only
            STATUS  mandatory
            DESCRIPTION
                "Unit index"
            ::= { bMS-LineSvrityEntry 1 }

        bMS-LineSvrityAIS  OBJECT-TYPE
            SYNTAX  Severity
            ACCESS  read-write
            STATUS  mandatory
            DESCRIPTION
                "AIS Alarm Severity Selection"
            ::= { bMS-LineSvrityEntry 2 }

        bMS-LineSvrityRDI  OBJECT-TYPE
            SYNTAX  Severity
            ACCESS  read-write
            STATUS  mandatory
            DESCRIPTION
                "RDI Alarm Severity Selection"
            ::= { bMS-LineSvrityEntry 3 }

        bMS-LineSvrityBIP  OBJECT-TYPE
            SYNTAX  Severity
            ACCESS  read-write
            STATUS  mandatory
            DESCRIPTION
                "BIP Alarm Severity Selection"
            ::= { bMS-LineSvrityEntry 4 }

        bMS-LineSvrityREI  OBJECT-TYPE
            SYNTAX  Severity
            ACCESS  read-write
            STATUS  mandatory
            DESCRIPTION
                "REI Alarm Severity Selection"
            ::= { bMS-LineSvrityEntry 5 }

        bMS-LineSvritySD  OBJECT-TYPE
            SYNTAX  Severity
            ACCESS  read-write
            STATUS  mandatory
            DESCRIPTION
                "SD Alarm Severity Selection"
            ::= { bMS-LineSvrityEntry 6 }

        bMS-LineSvritySF  OBJECT-TYPE
            SYNTAX  Severity
            ACCESS  read-write
            STATUS  mandatory
            DESCRIPTION
                "SF Alarm Severity Selection"
            ::= { bMS-LineSvrityEntry 7 }

--
--  B155/622 HoPath-STSPath Layer Alarm Mask Table
--

    bHo-STSPathTable   OBJECT IDENTIFIER ::= { b155-622AlarmSetupTable 4 }

        bHo-STSMaskTable  OBJECT-TYPE
            SYNTAX  SEQUENCE OF BHo-STSMaskEntry
            ACCESS  not-accessible
            STATUS  mandatory
            DESCRIPTION
                "HoPath-STSPath layer Alarm Mask Table"
            ::= { bHo-STSPathTable 1 }

        bHo-STSMaskEntry  OBJECT-TYPE
            SYNTAX  BHo-STSMaskEntry
            ACCESS  not-accessible
            STATUS  mandatory
            DESCRIPTION
                "HoPath-STSPathsical Alarm entry"
            INDEX { bHo-STSMaskUnitIdx , bHo-STSMaskPortIdx , bHo-STSMaskAUG1STS3Idx , bHo-STSMaskVC3STS1Idx }
            ::= { bHo-STSMaskTable 1 }

        BHo-STSMaskEntry ::= SEQUENCE {
            bHo-STSMaskUnitIdx          UnitID,
            bHo-STSMaskPortIdx          PortNum,
            bHo-STSMaskAUG1STS3Idx      Aug1Sts3Num,
            bHo-STSMaskVC3STS1Idx       Vc3Sts1Num,
            bHo-STSMaskLOP              INTEGER,
            bHo-STSMaskAIS              INTEGER,
            bHo-STSMaskTIM              INTEGER,
            bHo-STSMaskRDI-S            INTEGER,
            bHo-STSMaskRDI-C            INTEGER,
            bHo-STSMaskRDI-P            INTEGER,
            bHo-STSMaskBIP              INTEGER,
            bHo-STSMaskREI              INTEGER,
            bHo-STSMaskPLM              INTEGER,
            bHo-STSMaskUNEQ             INTEGER,
            bHo-STSMaskLOM              INTEGER,
            bHo-STSMaskSD               INTEGER,
            bHo-STSMaskSF               INTEGER
        }

        bHo-STSMaskUnitIdx  OBJECT-TYPE
            SYNTAX  UnitID
            ACCESS  read-only
            STATUS  mandatory
            DESCRIPTION
                "Unit1 Port-1 Optical Line Alarm Mask index"
            ::= { bHo-STSMaskEntry 1 }

        bHo-STSMaskPortIdx  OBJECT-TYPE
            SYNTAX  PortNum
            ACCESS  read-only
            STATUS  mandatory
            DESCRIPTION
                "Alarm Port index"
            ::= { bHo-STSMaskEntry 2 }

        bHo-STSMaskAUG1STS3Idx  OBJECT-TYPE
            SYNTAX  Aug1Sts3Num
            ACCESS  read-only
            STATUS  mandatory
            DESCRIPTION
                "AUG1/STS3 index"
            ::= { bHo-STSMaskEntry 3 }

        bHo-STSMaskVC3STS1Idx  OBJECT-TYPE
            SYNTAX  Vc3Sts1Num
            ACCESS  read-only
            STATUS  mandatory
            DESCRIPTION
                "VC3/STS1 index"
            ::= { bHo-STSMaskEntry 4 }

        bHo-STSMaskLOP  OBJECT-TYPE
            SYNTAX  INTEGER {
                    disable(1),
                    enable(2)
                }
            ACCESS  read-write
            STATUS  mandatory
            DESCRIPTION
                "LOP Alarm Mask Enable/Disable"
            ::= { bHo-STSMaskEntry 5 }

        bHo-STSMaskAIS  OBJECT-TYPE
            SYNTAX  INTEGER {
                    disable(1),
                    enable(2)
                }
            ACCESS  read-write
            STATUS  mandatory
            DESCRIPTION
                "AIS Alarm Mask Enable/Disable"
            ::= { bHo-STSMaskEntry 6 }

        bHo-STSMaskTIM  OBJECT-TYPE
            SYNTAX  INTEGER {
                    disable(1),
                    enable(2)
                }
            ACCESS  read-write
            STATUS  mandatory
            DESCRIPTION
                "TIM Alarm Mask Enable/Disable"
            ::= { bHo-STSMaskEntry 7 }

        bHo-STSMaskRDI-S  OBJECT-TYPE
            SYNTAX  INTEGER {
                    disable(1),
                    enable(2)
                }
            ACCESS  read-write
            STATUS  mandatory
            DESCRIPTION
                "RDI-S Alarm Mask Enable/Disable"
            ::= { bHo-STSMaskEntry 8 }

        bHo-STSMaskRDI-C  OBJECT-TYPE
            SYNTAX  INTEGER {
                    disable(1),
                    enable(2)
                }
            ACCESS  read-write
            STATUS  mandatory
            DESCRIPTION
                "RDI-C Alarm Mask Enable/Disable"
            ::= { bHo-STSMaskEntry 9 }

        bHo-STSMaskRDI-P  OBJECT-TYPE
            SYNTAX  INTEGER {
                    disable(1),
                    enable(2)
                }
            ACCESS  read-write
            STATUS  mandatory
            DESCRIPTION
                "RDI-P Alarm Mask Enable/Disable"
            ::= { bHo-STSMaskEntry 10 }

        bHo-STSMaskBIP  OBJECT-TYPE
            SYNTAX  INTEGER {
                    disable(1),
                    enable(2)
                }
            ACCESS  read-write
            STATUS  mandatory
            DESCRIPTION
                "BIP Alarm Mask Enable/Disable"
            ::= { bHo-STSMaskEntry 11 }

        bHo-STSMaskREI  OBJECT-TYPE
            SYNTAX  INTEGER {
                    disable(1),
                    enable(2)
                }
            ACCESS  read-write
            STATUS  mandatory
            DESCRIPTION
                "REI Alarm Mask Enable/Disable"
            ::= { bHo-STSMaskEntry 12 }

        bHo-STSMaskPLM  OBJECT-TYPE
            SYNTAX  INTEGER {
                    disable(1),
                    enable(2)
                }
            ACCESS  read-write
            STATUS  mandatory
            DESCRIPTION
                "PLM Alarm Mask Enable/Disable"
            ::= { bHo-STSMaskEntry 13 }

        bHo-STSMaskUNEQ  OBJECT-TYPE
            SYNTAX  INTEGER {
                    disable(1),
                    enable(2)
                }
            ACCESS  read-write
            STATUS  mandatory
            DESCRIPTION
                "UNEQ Alarm Mask Enable/Disable"
            ::= { bHo-STSMaskEntry 14 }

        bHo-STSMaskLOM  OBJECT-TYPE
            SYNTAX  INTEGER {
                    disable(1),
                    enable(2)
                }
            ACCESS  read-write
            STATUS  mandatory
            DESCRIPTION
                "LOM Alarm Mask Enable/Disable"
            ::= { bHo-STSMaskEntry 15 }

        bHo-STSMaskSD  OBJECT-TYPE
            SYNTAX  INTEGER {
                    disable(1),
                    enable(2)
                }
            ACCESS  read-write
            STATUS  mandatory
            DESCRIPTION
                "SD Alarm Mask Enable/Disable"
            ::= { bHo-STSMaskEntry 16 }

        bHo-STSMaskSF  OBJECT-TYPE
            SYNTAX  INTEGER {
                    disable(1),
                    enable(2)
                }
            ACCESS  read-write
            STATUS  mandatory
            DESCRIPTION
                "SF Alarm Mask Enable/Disable"
            ::= { bHo-STSMaskEntry 17 }
--
--  B155/622 HoPath-STSPath Layer Alarm Relay Table
--
        bHo-STSRelayTable  OBJECT-TYPE
            SYNTAX  SEQUENCE OF BHo-STSRelayEntry
            ACCESS  not-accessible
            STATUS  mandatory
            DESCRIPTION
                "HoPath-STS Path layer Alarm Mask Table"
            ::= { bHo-STSPathTable 2 }

        bHo-STSRelayEntry  OBJECT-TYPE
            SYNTAX  BHo-STSRelayEntry
            ACCESS  not-accessible
            STATUS  mandatory
            DESCRIPTION
                "HoPath-STSPathsical Alarm entry"
            INDEX { bHo-STSRelayUnitIdx , bHo-STSRelayPortIdx , bHo-STSRelayAUG1STS3Idx , bHo-STSRelayVC3STS1Idx }
            ::= { bHo-STSRelayTable 1 }

        BHo-STSRelayEntry ::= SEQUENCE {
            bHo-STSRelayUnitIdx         UnitID,
            bHo-STSRelayPortIdx         PortNum,
            bHo-STSRelayAUG1STS3Idx     Aug1Sts3Num,
            bHo-STSRelayVC3STS1Idx      Vc3Sts1Num,
            bHo-STSRelayLOP             INTEGER,
            bHo-STSRelayAIS             INTEGER,
            bHo-STSRelayTIM             INTEGER,
            bHo-STSRelayRDI-S           INTEGER,
            bHo-STSRelayRDI-C           INTEGER,
            bHo-STSRelayRDI-P           INTEGER,
            bHo-STSRelayBIP             INTEGER,
            bHo-STSRelayREI             INTEGER,
            bHo-STSRelayPLM             INTEGER,
            bHo-STSRelayUNEQ            INTEGER,
            bHo-STSRelayLOM             INTEGER,
            bHo-STSRelaySD              INTEGER,
            bHo-STSRelaySF              INTEGER
        }

        bHo-STSRelayUnitIdx  OBJECT-TYPE
            SYNTAX  UnitID
            ACCESS  read-only
            STATUS  mandatory
            DESCRIPTION
                "Unit index"
            ::= { bHo-STSRelayEntry 1 }

        bHo-STSRelayPortIdx  OBJECT-TYPE
            SYNTAX  PortNum
            ACCESS  read-only
            STATUS  mandatory
            DESCRIPTION
                "Port index"
            ::= { bHo-STSRelayEntry 2 }

        bHo-STSRelayAUG1STS3Idx  OBJECT-TYPE
            SYNTAX  Aug1Sts3Num
            ACCESS  read-only
            STATUS  mandatory
            DESCRIPTION
                "AUG1/STS3 index"
            ::= { bHo-STSRelayEntry 3 }

        bHo-STSRelayVC3STS1Idx  OBJECT-TYPE
            SYNTAX  Vc3Sts1Num
            ACCESS  read-only
            STATUS  mandatory
            DESCRIPTION
                "VC3/STS1 index"
            ::= { bHo-STSRelayEntry 4 }

        bHo-STSRelayLOP  OBJECT-TYPE
            SYNTAX  INTEGER {
                    disable(1),
                    enable(2)
                }
            ACCESS  read-write
            STATUS  mandatory
            DESCRIPTION
                "LOP Alarm Relay Enable/Disable"
            ::= { bHo-STSRelayEntry 5 }

        bHo-STSRelayAIS  OBJECT-TYPE
            SYNTAX  INTEGER {
                    disable(1),
                    enable(2)
                }
            ACCESS  read-write
            STATUS  mandatory
            DESCRIPTION
                "AIS Alarm Relay Enable/Disable"
            ::= { bHo-STSRelayEntry 6 }

        bHo-STSRelayTIM  OBJECT-TYPE
            SYNTAX  INTEGER {
                    disable(1),
                    enable(2)
                }
            ACCESS  read-write
            STATUS  mandatory
            DESCRIPTION
                "TIM Alarm Relay Enable/Disable"
            ::= { bHo-STSRelayEntry 7 }

        bHo-STSRelayRDI-S  OBJECT-TYPE
            SYNTAX  INTEGER {
                    disable(1),
                    enable(2)
                }
            ACCESS  read-write
            STATUS  mandatory
            DESCRIPTION
                "RDI-S Alarm Relay Enable/Disable"
            ::= { bHo-STSRelayEntry 8 }

        bHo-STSRelayRDI-C  OBJECT-TYPE
            SYNTAX  INTEGER {
                    disable(1),
                    enable(2)
                }
            ACCESS  read-write
            STATUS  mandatory
            DESCRIPTION
                "RDI-C Alarm Relay Enable/Disable"
            ::= { bHo-STSRelayEntry 9 }

        bHo-STSRelayRDI-P  OBJECT-TYPE
            SYNTAX  INTEGER {
                    disable(1),
                    enable(2)
                }
            ACCESS  read-write
            STATUS  mandatory
            DESCRIPTION
                "RDI-P Alarm Relay Enable/Disable"
            ::= { bHo-STSRelayEntry 10 }

        bHo-STSRelayBIP  OBJECT-TYPE
            SYNTAX  INTEGER {
                    disable(1),
                    enable(2)
                }
            ACCESS  read-write
            STATUS  mandatory
            DESCRIPTION
                "BIP Alarm Relay Enable/Disable"
            ::= { bHo-STSRelayEntry 11 }

        bHo-STSRelayREI  OBJECT-TYPE
            SYNTAX  INTEGER {
                    disable(1),
                    enable(2)
                }
            ACCESS  read-write
            STATUS  mandatory
            DESCRIPTION
                "REI Alarm Relay Enable/Disable"
            ::= { bHo-STSRelayEntry 12 }

        bHo-STSRelayPLM  OBJECT-TYPE
            SYNTAX  INTEGER {
                    disable(1),
                    enable(2)
                }
            ACCESS  read-write
            STATUS  mandatory
            DESCRIPTION
                "PLM Alarm Relay Enable/Disable"
            ::= { bHo-STSRelayEntry 13 }

        bHo-STSRelayUNEQ  OBJECT-TYPE
            SYNTAX  INTEGER {
                    disable(1),
                    enable(2)
                }
            ACCESS  read-write
            STATUS  mandatory
            DESCRIPTION
                "UNEQ Alarm Relay Enable/Disable"
            ::= { bHo-STSRelayEntry 14 }

        bHo-STSRelayLOM  OBJECT-TYPE
            SYNTAX  INTEGER {
                    disable(1),
                    enable(2)
                }
            ACCESS  read-write
            STATUS  mandatory
            DESCRIPTION
                "LOM Alarm Relay Enable/Disable"
            ::= { bHo-STSRelayEntry 15 }

        bHo-STSRelaySD  OBJECT-TYPE
            SYNTAX  INTEGER {
                    disable(1),
                    enable(2)
                }
            ACCESS  read-write
            STATUS  mandatory
            DESCRIPTION
                "SD Alarm Relay Enable/Disable"
            ::= { bHo-STSRelayEntry 16 }

        bHo-STSRelaySF  OBJECT-TYPE
            SYNTAX  INTEGER {
                    disable(1),
                    enable(2)
                }
            ACCESS  read-write
            STATUS  mandatory
            DESCRIPTION
                "SF Alarm Relay Enable/Disable"
            ::= { bHo-STSRelayEntry 17 }
--
--  B155/622 HoPath-STSPath Layer Alarm Severity Table
--

        bHo-STSSvrityTable  OBJECT-TYPE
            SYNTAX  SEQUENCE OF BHo-STSSvrityEntry
            ACCESS  not-accessible
            STATUS  mandatory
            DESCRIPTION
                "HoPath-STSPath layer Alarm Severity Table"
            ::= { bHo-STSPathTable 3 }

        bHo-STSSvrityEntry  OBJECT-TYPE
            SYNTAX  BHo-STSSvrityEntry
            ACCESS  not-accessible
            STATUS  mandatory
            DESCRIPTION
                "HoPath-STS Path Alarm entry"
            INDEX { bHo-STSSvrityUnitIndex }
            ::= { bHo-STSSvrityTable 1 }

        BHo-STSSvrityEntry ::= SEQUENCE {
            bHo-STSSvrityUnitIndex      UnitID,
            bHo-STSSvrityLOP            Severity,
            bHo-STSSvrityAIS            Severity,
            bHo-STSSvrityTIM            Severity,
            bHo-STSSvrityRDI-S          Severity,
            bHo-STSSvrityRDI-C          Severity,
            bHo-STSSvrityRDI-P          Severity,
            bHo-STSSvrityBIP            Severity,
            bHo-STSSvrityREI            Severity,
            bHo-STSSvrityPLM            Severity,
            bHo-STSSvrityUNEQ           Severity,
            bHo-STSSvrityLOM            Severity,
            bHo-STSSvritySD             Severity,
            bHo-STSSvritySF             Severity
        }

        bHo-STSSvrityUnitIndex  OBJECT-TYPE
            SYNTAX  UnitID
            ACCESS  read-only
            STATUS  mandatory
            DESCRIPTION
                "Unit index"
            ::= { bHo-STSSvrityEntry 1 }

        bHo-STSSvrityLOP  OBJECT-TYPE
            SYNTAX  Severity
            ACCESS  read-write
            STATUS  mandatory
            DESCRIPTION
                "LOP Alarm Severity Selection"
            ::= { bHo-STSSvrityEntry 2 }

        bHo-STSSvrityAIS  OBJECT-TYPE
            SYNTAX  Severity
            ACCESS  read-write
            STATUS  mandatory
            DESCRIPTION
                "AIS Alarm Severity Selection"
            ::= { bHo-STSSvrityEntry 3 }

        bHo-STSSvrityTIM  OBJECT-TYPE
            SYNTAX  Severity
            ACCESS  read-write
            STATUS  mandatory
            DESCRIPTION
                "TIM Alarm Severity Selection"
            ::= { bHo-STSSvrityEntry 4 }

        bHo-STSSvrityRDI-S  OBJECT-TYPE
            SYNTAX  Severity
            ACCESS  read-write
            STATUS  mandatory
            DESCRIPTION
                "RDI-S Alarm Severity Selection"
            ::= { bHo-STSSvrityEntry 5 }

        bHo-STSSvrityRDI-C  OBJECT-TYPE
            SYNTAX  Severity
            ACCESS  read-write
            STATUS  mandatory
            DESCRIPTION
                "RDI-C Alarm Severity Selection"
            ::= { bHo-STSSvrityEntry 6 }

        bHo-STSSvrityRDI-P  OBJECT-TYPE
            SYNTAX  Severity
            ACCESS  read-write
            STATUS  mandatory
            DESCRIPTION
                "RDI-P Alarm Severity Selection"
            ::= { bHo-STSSvrityEntry 7 }

        bHo-STSSvrityBIP  OBJECT-TYPE
            SYNTAX  Severity
            ACCESS  read-write
            STATUS  mandatory
            DESCRIPTION
                "BIP Alarm Severity Selection"
            ::= { bHo-STSSvrityEntry 8 }

        bHo-STSSvrityREI  OBJECT-TYPE
            SYNTAX  Severity
            ACCESS  read-write
            STATUS  mandatory
            DESCRIPTION
                "REI Alarm Severity Selection"
            ::= { bHo-STSSvrityEntry 9 }

        bHo-STSSvrityPLM  OBJECT-TYPE
            SYNTAX  Severity
            ACCESS  read-write
            STATUS  mandatory
            DESCRIPTION
                "PLM Alarm Severity Selection"
            ::= { bHo-STSSvrityEntry 10 }

        bHo-STSSvrityUNEQ  OBJECT-TYPE
            SYNTAX  Severity
            ACCESS  read-write
            STATUS  mandatory
            DESCRIPTION
                "UNEQ Alarm Severity Selection"
            ::= { bHo-STSSvrityEntry 11 }

        bHo-STSSvrityLOM  OBJECT-TYPE
            SYNTAX  Severity
            ACCESS  read-write
            STATUS  mandatory
            DESCRIPTION
                "LOM Alarm Severity Selection"
            ::= { bHo-STSSvrityEntry 12 }

        bHo-STSSvritySD  OBJECT-TYPE
            SYNTAX  Severity
            ACCESS  read-write
            STATUS  mandatory
            DESCRIPTION
                "SD Alarm Severity Selection"
            ::= { bHo-STSSvrityEntry 13 }

        bHo-STSSvritySF  OBJECT-TYPE
            SYNTAX  Severity
            ACCESS  read-write
            STATUS  mandatory
            DESCRIPTION
                "SF Alarm Severity Selection"
            ::= { bHo-STSSvrityEntry 14 }

--
--  B155/622 LoPath-VTPath Layer Alarm Mask Table
--

    bLo-VTPathTable   OBJECT IDENTIFIER ::= { b155-622AlarmSetupTable 5 }

        bLo-VTMaskTable  OBJECT-TYPE
            SYNTAX  SEQUENCE OF BLo-VTMaskEntry
            ACCESS  not-accessible
            STATUS  mandatory
            DESCRIPTION
                "LoPath-VTPath layer Alarm Mask Table"
            ::= { bLo-VTPathTable 1 }

        bLo-VTMaskEntry  OBJECT-TYPE
            SYNTAX  BLo-VTMaskEntry
            ACCESS  not-accessible
            STATUS  mandatory
            DESCRIPTION
                "LoPath-VTPath Alarm entry"
            INDEX { bLo-VTMaskUnitIdx , bLo-VTMaskPortIdx , bLo-VTMaskAUG1STS3Idx , bLo-VTMaskVC3STS1Idx , bLo-VTMaskTU1xVTxIdx }
            ::= { bLo-VTMaskTable 1 }

        BLo-VTMaskEntry ::= SEQUENCE {
            bLo-VTMaskUnitIdx           UnitID,
            bLo-VTMaskPortIdx           PortNum,
            bLo-VTMaskAUG1STS3Idx       Aug1Sts3Num,
            bLo-VTMaskVC3STS1Idx        Vc3Sts1Num,
            bLo-VTMaskTU1xVTxIdx        TU1xVtxNum,
            bLo-VTMaskLOP               INTEGER,
            bLo-VTMaskAIS               INTEGER,
            bLo-VTMaskTIM               INTEGER,
            bLo-VTMaskRDI-S             INTEGER,
            bLo-VTMaskRDI-C             INTEGER,
            bLo-VTMaskRDI-P             INTEGER,
            bLo-VTMaskBIP               INTEGER,
            bLo-VTMaskREI               INTEGER,
            bLo-VTMaskPLM               INTEGER,
            bLo-VTMaskUNEQ              INTEGER,
            bLo-VTMaskSD                INTEGER,
            bLo-VTMaskSF                INTEGER
        }

        bLo-VTMaskUnitIdx  OBJECT-TYPE
            SYNTAX  UnitID
            ACCESS  read-only
            STATUS  mandatory
            DESCRIPTION
                "Unit index"
            ::= { bLo-VTMaskEntry 1 }

        bLo-VTMaskPortIdx  OBJECT-TYPE
            SYNTAX  PortNum
            ACCESS  read-only
            STATUS  mandatory
            DESCRIPTION
                "Port index"
            ::= { bLo-VTMaskEntry 2 }

        bLo-VTMaskAUG1STS3Idx  OBJECT-TYPE
            SYNTAX  Aug1Sts3Num
            ACCESS  read-only
            STATUS  mandatory
            DESCRIPTION
                "AUG1/STS3 index"
            ::= { bLo-VTMaskEntry 3 }

        bLo-VTMaskVC3STS1Idx  OBJECT-TYPE
            SYNTAX  Vc3Sts1Num
            ACCESS  read-only
            STATUS  mandatory
            DESCRIPTION
                "VC3/STS1 or Tug3 index"
            ::= { bLo-VTMaskEntry 4 }

        bLo-VTMaskTU1xVTxIdx  OBJECT-TYPE
            SYNTAX  TU1xVtxNum
            ACCESS  read-only
            STATUS  mandatory
            DESCRIPTION
                "VC1x/VTx index"
            ::= { bLo-VTMaskEntry 5 }

        bLo-VTMaskLOP  OBJECT-TYPE
            SYNTAX  INTEGER {
                    disable(1),
                    enable(2)
                }
            ACCESS  read-write
            STATUS  mandatory
            DESCRIPTION
                "LOP Alarm Mask Enable/Disable"
            ::= { bLo-VTMaskEntry 6 }

        bLo-VTMaskAIS  OBJECT-TYPE
            SYNTAX  INTEGER {
                    disable(1),
                    enable(2)
                }
            ACCESS  read-write
            STATUS  mandatory
            DESCRIPTION
                "AIS Alarm Mask Enable/Disable"
            ::= { bLo-VTMaskEntry 7 }

        bLo-VTMaskTIM  OBJECT-TYPE
            SYNTAX  INTEGER {
                    disable(1),
                    enable(2)
                }
            ACCESS  read-write
            STATUS  mandatory
            DESCRIPTION
                "TIM Alarm Mask Enable/Disable"
            ::= { bLo-VTMaskEntry 8 }

        bLo-VTMaskRDI-S  OBJECT-TYPE
            SYNTAX  INTEGER {
                    disable(1),
                    enable(2)
                }
            ACCESS  read-write
            STATUS  mandatory
            DESCRIPTION
                "RDI-S Alarm Mask Enable/Disable"
            ::= { bLo-VTMaskEntry 9 }

        bLo-VTMaskRDI-C  OBJECT-TYPE
            SYNTAX  INTEGER {
                    disable(1),
                    enable(2)
                }
            ACCESS  read-write
            STATUS  mandatory
            DESCRIPTION
                "RDI-C Alarm Mask Enable/Disable"
            ::= { bLo-VTMaskEntry 10 }

        bLo-VTMaskRDI-P  OBJECT-TYPE
            SYNTAX  INTEGER {
                    disable(1),
                    enable(2)
                }
            ACCESS  read-write
            STATUS  mandatory
            DESCRIPTION
                "RDI-P Alarm Mask Enable/Disable"
            ::= { bLo-VTMaskEntry 11 }

        bLo-VTMaskBIP  OBJECT-TYPE
            SYNTAX  INTEGER {
                    disable(1),
                    enable(2)
                }
            ACCESS  read-write
            STATUS  mandatory
            DESCRIPTION
                "BIP Alarm Mask Enable/Disable"
            ::= { bLo-VTMaskEntry 12 }

        bLo-VTMaskREI  OBJECT-TYPE
            SYNTAX  INTEGER {
                    disable(1),
                    enable(2)
                }
            ACCESS  read-write
            STATUS  mandatory
            DESCRIPTION
                "REI Alarm Mask Enable/Disable"
            ::= { bLo-VTMaskEntry 13 }

        bLo-VTMaskPLM  OBJECT-TYPE
            SYNTAX  INTEGER {
                    disable(1),
                    enable(2)
                }
            ACCESS  read-write
            STATUS  mandatory
            DESCRIPTION
                "PLM Alarm Mask Enable/Disable"
            ::= { bLo-VTMaskEntry 14 }

        bLo-VTMaskUNEQ  OBJECT-TYPE
            SYNTAX  INTEGER {
                    disable(1),
                    enable(2)
                }
            ACCESS  read-write
            STATUS  mandatory
            DESCRIPTION
                "UNEQ Alarm Mask Enable/Disable"
            ::= { bLo-VTMaskEntry 15 }

        bLo-VTMaskSD  OBJECT-TYPE
            SYNTAX  INTEGER {
                    disable(1),
                    enable(2)
                }
            ACCESS  read-write
            STATUS  mandatory
            DESCRIPTION
                "SD Alarm Mask Enable/Disable"
            ::= { bLo-VTMaskEntry 16 }

        bLo-VTMaskSF  OBJECT-TYPE
            SYNTAX  INTEGER {
                    disable(1),
                    enable(2)
                }
            ACCESS  read-write
            STATUS  mandatory
            DESCRIPTION
                "SF Alarm Mask Enable/Disable"
            ::= { bLo-VTMaskEntry 17 }
--
--  B155/622 LoPath-VTPath Layer Alarm Relay Table
--
        bLo-VTRelayTable  OBJECT-TYPE
            SYNTAX  SEQUENCE OF BLo-VTRelayEntry
            ACCESS  not-accessible
            STATUS  mandatory
            DESCRIPTION
                "LoPath-VTPath layer Alarm Mask Table"
            ::= { bLo-VTPathTable 2 }

        bLo-VTRelayEntry  OBJECT-TYPE
            SYNTAX  BLo-VTRelayEntry
            ACCESS  not-accessible
            STATUS  mandatory
            DESCRIPTION
                "LoPath-VTPath Alarm entry"
            INDEX { bLo-VTRelayUnitIdx , bLo-VTRelayPortIdx , bLo-VTRelayAUG1STS3Idx , bLo-VTRelayVC3STS1Idx , bLo-VTRelayTU1xVTxIdx }
            ::= { bLo-VTRelayTable 1 }

        BLo-VTRelayEntry ::= SEQUENCE {
            bLo-VTRelayUnitIdx          UnitID,
            bLo-VTRelayPortIdx          PortNum,
            bLo-VTRelayAUG1STS3Idx      Aug1Sts3Num,
            bLo-VTRelayVC3STS1Idx       Vc3Sts1Num,
            bLo-VTRelayTU1xVTxIdx       TU1xVtxNum,
            bLo-VTRelayLOP              INTEGER,
            bLo-VTRelayAIS              INTEGER,
            bLo-VTRelayTIM              INTEGER,
            bLo-VTRelayRDI-S            INTEGER,
            bLo-VTRelayRDI-C            INTEGER,
            bLo-VTRelayRDI-P            INTEGER,
            bLo-VTRelayBIP              INTEGER,
            bLo-VTRelayREI              INTEGER,
            bLo-VTRelayPLM              INTEGER,
            bLo-VTRelayUNEQ             INTEGER,
            bLo-VTRelaySD               INTEGER,
            bLo-VTRelaySF               INTEGER
        }

        bLo-VTRelayUnitIdx  OBJECT-TYPE
            SYNTAX  UnitID
            ACCESS  read-only
            STATUS  mandatory
            DESCRIPTION
                "Unit index"
            ::= { bLo-VTRelayEntry 1 }

        bLo-VTRelayPortIdx  OBJECT-TYPE
            SYNTAX  PortNum
            ACCESS  read-only
            STATUS  mandatory
            DESCRIPTION
                "Port index"
            ::= { bLo-VTRelayEntry 2 }

        bLo-VTRelayAUG1STS3Idx  OBJECT-TYPE
            SYNTAX  Aug1Sts3Num
            ACCESS  read-only
            STATUS  mandatory
            DESCRIPTION
                "AUG1/STS3 index"
            ::= { bLo-VTRelayEntry 3 }

        bLo-VTRelayVC3STS1Idx  OBJECT-TYPE
            SYNTAX  Vc3Sts1Num
            ACCESS  read-only
            STATUS  mandatory
            DESCRIPTION
                "VC3/STS1 or Tug3 index"
            ::= { bLo-VTRelayEntry 4 }

        bLo-VTRelayTU1xVTxIdx  OBJECT-TYPE
            SYNTAX  TU1xVtxNum
            ACCESS  read-only
            STATUS  mandatory
            DESCRIPTION
                "VC1x/VTx index"
            ::= { bLo-VTRelayEntry 5 }

        bLo-VTRelayLOP  OBJECT-TYPE
            SYNTAX  INTEGER {
                    disable(1),
                    enable(2)
                }
            ACCESS  read-write
            STATUS  mandatory
            DESCRIPTION
                "LOP Alarm Relay Enable/Disable"
            ::= { bLo-VTRelayEntry 6 }

        bLo-VTRelayAIS  OBJECT-TYPE
            SYNTAX  INTEGER {
                    disable(1),
                    enable(2)
                }
            ACCESS  read-write
            STATUS  mandatory
            DESCRIPTION
                "AIS Alarm Relay Enable/Disable"
            ::= { bLo-VTRelayEntry 7 }

        bLo-VTRelayTIM  OBJECT-TYPE
            SYNTAX  INTEGER {
                    disable(1),
                    enable(2)
                }
            ACCESS  read-write
            STATUS  mandatory
            DESCRIPTION
                "TIM Alarm Relay Enable/Disable"
            ::= { bLo-VTRelayEntry 8 }

        bLo-VTRelayRDI-S  OBJECT-TYPE
            SYNTAX  INTEGER {
                    disable(1),
                    enable(2)
                }
            ACCESS  read-write
            STATUS  mandatory
            DESCRIPTION
                "RDI-S Alarm Relay Enable/Disable"
            ::= { bLo-VTRelayEntry 9 }

        bLo-VTRelayRDI-C  OBJECT-TYPE
            SYNTAX  INTEGER {
                    disable(1),
                    enable(2)
                }
            ACCESS  read-write
            STATUS  mandatory
            DESCRIPTION
                "RDI-C Alarm Relay Enable/Disable"
            ::= { bLo-VTRelayEntry 10 }

        bLo-VTRelayRDI-P  OBJECT-TYPE
            SYNTAX  INTEGER {
                    disable(1),
                    enable(2)
                }
            ACCESS  read-write
            STATUS  mandatory
            DESCRIPTION
                "RDI-P Alarm Relay Enable/Disable"
            ::= { bLo-VTRelayEntry 11 }

        bLo-VTRelayBIP  OBJECT-TYPE
            SYNTAX  INTEGER {
                    disable(1),
                    enable(2)
                }
            ACCESS  read-write
            STATUS  mandatory
            DESCRIPTION
                "BIP Alarm Relay Enable/Disable"
            ::= { bLo-VTRelayEntry 12 }

        bLo-VTRelayREI  OBJECT-TYPE
            SYNTAX  INTEGER {
                    disable(1),
                    enable(2)
                }
            ACCESS  read-write
            STATUS  mandatory
            DESCRIPTION
                "REI Alarm Relay Enable/Disable"
            ::= { bLo-VTRelayEntry 13 }

        bLo-VTRelayPLM  OBJECT-TYPE
            SYNTAX  INTEGER {
                    disable(1),
                    enable(2)
                }
            ACCESS  read-write
            STATUS  mandatory
            DESCRIPTION
                "PLM Alarm Relay Enable/Disable"
            ::= { bLo-VTRelayEntry 14 }

        bLo-VTRelayUNEQ  OBJECT-TYPE
            SYNTAX  INTEGER {
                    disable(1),
                    enable(2)
                }
            ACCESS  read-write
            STATUS  mandatory
            DESCRIPTION
                "UNEQ Alarm Relay Enable/Disable"
            ::= { bLo-VTRelayEntry 15 }

        bLo-VTRelaySD  OBJECT-TYPE
            SYNTAX  INTEGER {
                    disable(1),
                    enable(2)
                }
            ACCESS  read-write
            STATUS  mandatory
            DESCRIPTION
                "SD Alarm Relay Enable/Disable"
            ::= { bLo-VTRelayEntry 16 }

        bLo-VTRelaySF  OBJECT-TYPE
            SYNTAX  INTEGER {
                    disable(1),
                    enable(2)
                }
            ACCESS  read-write
            STATUS  mandatory
            DESCRIPTION
                "SF Alarm Relay Enable/Disable"
            ::= { bLo-VTRelayEntry 17 }
--
--  B155/622 LoPath-VTPath Layer Alarm Severity Table
--

        bLo-VTSvrityTable  OBJECT-TYPE
            SYNTAX  SEQUENCE OF BLo-VTSvrityEntry
            ACCESS  not-accessible
            STATUS  mandatory
            DESCRIPTION
                "LoPath-VTPath layer Alarm Severity Table"
            ::= { bLo-VTPathTable 3 }

        bLo-VTSvrityEntry  OBJECT-TYPE
            SYNTAX  BLo-VTSvrityEntry
            ACCESS  not-accessible
            STATUS  mandatory
            DESCRIPTION
                "LoPath-VTPath Alarm entry"
            INDEX { bLo-VTSvrityUnitIdx }
            ::= { bLo-VTSvrityTable 1 }

        BLo-VTSvrityEntry ::= SEQUENCE {
            bLo-VTSvrityUnitIdx         UnitID,
            bLo-VTSvrityLOP             Severity,
            bLo-VTSvrityAIS             Severity,
            bLo-VTSvrityTIM             Severity,
            bLo-VTSvrityRDI-S           Severity,
            bLo-VTSvrityRDI-C           Severity,
            bLo-VTSvrityRDI-P           Severity,
            bLo-VTSvrityBIP             Severity,
            bLo-VTSvrityREI             Severity,
            bLo-VTSvrityPLM             Severity,
            bLo-VTSvrityUNEQ            Severity,
            bLo-VTSvritySD              Severity,
            bLo-VTSvritySF              Severity
        }

        bLo-VTSvrityUnitIdx  OBJECT-TYPE
            SYNTAX  UnitID
            ACCESS  read-only
            STATUS  mandatory
            DESCRIPTION
                "Unit index"
            ::= { bLo-VTSvrityEntry 1 }

        bLo-VTSvrityLOP  OBJECT-TYPE
            SYNTAX  Severity
            ACCESS  read-write
            STATUS  mandatory
            DESCRIPTION
                "Alarm Severity Selection"
            ::= { bLo-VTSvrityEntry 2 }

        bLo-VTSvrityAIS  OBJECT-TYPE
            SYNTAX  Severity
            ACCESS  read-write
            STATUS  mandatory
            DESCRIPTION
                "AIS Alarm Severity Selection"
            ::= { bLo-VTSvrityEntry 3 }

        bLo-VTSvrityTIM  OBJECT-TYPE
            SYNTAX  Severity
            ACCESS  read-write
            STATUS  mandatory
            DESCRIPTION
                "TIM Alarm Severity Selection"
            ::= { bLo-VTSvrityEntry 4 }

        bLo-VTSvrityRDI-S  OBJECT-TYPE
            SYNTAX  Severity
            ACCESS  read-write
            STATUS  mandatory
            DESCRIPTION
                "RDI-S Alarm Severity Selection"
            ::= { bLo-VTSvrityEntry 5 }

        bLo-VTSvrityRDI-C  OBJECT-TYPE
            SYNTAX  Severity
            ACCESS  read-write
            STATUS  mandatory
            DESCRIPTION
                "RDI-C Alarm Severity Selection"
            ::= { bLo-VTSvrityEntry 6 }

        bLo-VTSvrityRDI-P  OBJECT-TYPE
            SYNTAX  Severity
            ACCESS  read-write
            STATUS  mandatory
            DESCRIPTION
                "RDI-P Alarm Severity Selection"
            ::= { bLo-VTSvrityEntry 7 }

        bLo-VTSvrityBIP  OBJECT-TYPE
            SYNTAX  Severity
            ACCESS  read-write
            STATUS  mandatory
            DESCRIPTION
                "BIP Alarm Severity Selection"
            ::= { bLo-VTSvrityEntry 8 }

        bLo-VTSvrityREI  OBJECT-TYPE
            SYNTAX  Severity
            ACCESS  read-write
            STATUS  mandatory
            DESCRIPTION
                "REI Alarm Severity Selection"
            ::= { bLo-VTSvrityEntry 9 }

        bLo-VTSvrityPLM  OBJECT-TYPE
            SYNTAX  Severity
            ACCESS  read-write
            STATUS  mandatory
            DESCRIPTION
                "PLM Alarm Severity Selection"
            ::= { bLo-VTSvrityEntry 10 }

        bLo-VTSvrityUNEQ  OBJECT-TYPE
            SYNTAX  Severity
            ACCESS  read-write
            STATUS  mandatory
            DESCRIPTION
                "UNEQ Alarm Severity Selection"
            ::= { bLo-VTSvrityEntry 11 }


        bLo-VTSvritySD  OBJECT-TYPE
            SYNTAX  Severity
            ACCESS  read-write
            STATUS  mandatory
            DESCRIPTION
                "SD Alarm Severity Selection"
            ::= { bLo-VTSvrityEntry 12 }

        bLo-VTSvritySF  OBJECT-TYPE
            SYNTAX  Severity
            ACCESS  read-write
            STATUS  mandatory
            DESCRIPTION
                "SF Alarm Severity Selection"
            ::= { bLo-VTSvrityEntry 13 }


--
--  B155/622 Alarm Setup Hex Table
--

        b155-622alarmSetupHexTab  OBJECT-TYPE
            SYNTAX  SEQUENCE OF  BalarmSetupHexEntry
            ACCESS  not-accessible
            STATUS  mandatory
            DESCRIPTION
                "B155/622 Line/HP/LP HEX Table "
            ::= { b155-622AlarmSetupTable 6 }

        balarmSetupHexEntry OBJECT-TYPE
            SYNTAX  BalarmSetupHexEntry
            ACCESS  not-accessible
            STATUS  mandatory
            DESCRIPTION
                "An entry in the B155/622 Line/HP/LP HEX table."
            INDEX { balarmSetupHexUnitIdx }
            ::= { b155-622alarmSetupHexTab 1 }

        BalarmSetupHexEntry ::= SEQUENCE  {
            balarmSetupHexUnitIdx       UnitID,
            blineAlarmMaskHex           OCTET STRING,
            blineAlarmRelayHex          OCTET STRING,
            blineAlarmSeverityHex       OCTET STRING,
            bhpAlarmMaskHex             OCTET STRING,
            bhpAlarmRelayHex            OCTET STRING,
            bhpAlarmSeverityHex         OCTET STRING,
            blpPort1AlarmMaskHex        OCTET STRING,
            blpPort2AlarmMaskHex        OCTET STRING,
            blpPort1AlarmRelayHex       OCTET STRING,
            blpPort2AlarmRelayHex       OCTET STRING,
            blpAlarmSeverityHex         OCTET STRING
        }

        balarmSetupHexUnitIdx  OBJECT-TYPE
            SYNTAX  UnitID
            ACCESS  read-only
            STATUS  mandatory
            DESCRIPTION
                "Unit index"
            ::= { balarmSetupHexEntry 1 }

        blineAlarmMaskHex  OBJECT-TYPE
            SYNTAX  OCTET STRING(SIZE(17))
            ACCESS  read-only
            STATUS  mandatory
            DESCRIPTION
                "Line alarm mask in Hex"
            ::= { balarmSetupHexEntry 2 }

        blineAlarmRelayHex  OBJECT-TYPE
            SYNTAX  OCTET STRING(SIZE(17))
            ACCESS  read-only
            STATUS  mandatory
            DESCRIPTION
                "Line alarm Relay in Hex"
            ::= { balarmSetupHexEntry 3 }

        blineAlarmSeverityHex  OBJECT-TYPE
            SYNTAX  OCTET STRING(SIZE(24))
            ACCESS  read-only
            STATUS  mandatory
            DESCRIPTION
                "Line alarm Relay in Hex"
            ::= { balarmSetupHexEntry 4 }

        bhpAlarmMaskHex  OBJECT-TYPE
            SYNTAX  OCTET STRING(SIZE(97))
            ACCESS  read-only
            STATUS  mandatory
            DESCRIPTION
                "hp alarm mask in Hex"
            ::= { balarmSetupHexEntry 5 }

        bhpAlarmRelayHex  OBJECT-TYPE
            SYNTAX  OCTET STRING(SIZE(97))
            ACCESS  read-only
            STATUS  mandatory
            DESCRIPTION
                "hp alarm Relay in Hex"
            ::= { balarmSetupHexEntry 6 }

        bhpAlarmSeverityHex  OBJECT-TYPE
            SYNTAX  OCTET STRING(SIZE(24))
            ACCESS  read-only
            STATUS  mandatory
            DESCRIPTION
                "hp alarm Severity in Hex"
            ::= { balarmSetupHexEntry 7 }

        blpPort1AlarmMaskHex  OBJECT-TYPE
            SYNTAX  OCTET STRING(SIZE(673))
            ACCESS  read-only
            STATUS  mandatory
            DESCRIPTION
                "Port#1 lp alarm mask in Hex"
            ::= { balarmSetupHexEntry 8 }

        blpPort2AlarmMaskHex  OBJECT-TYPE
            SYNTAX  OCTET STRING(SIZE(673))
            ACCESS  read-only
            STATUS  mandatory
            DESCRIPTION
                "Port#2 lp alarm mask in Hex"
            ::= { balarmSetupHexEntry 9 }

        blpPort1AlarmRelayHex  OBJECT-TYPE
            SYNTAX  OCTET STRING(SIZE(673))
            ACCESS  read-only
            STATUS  mandatory
            DESCRIPTION
                "Port#1 lp alarm Relay in Hex"
            ::= { balarmSetupHexEntry 10 }

        blpPort2AlarmRelayHex  OBJECT-TYPE
            SYNTAX  OCTET STRING(SIZE(673))
            ACCESS  read-only
            STATUS  mandatory
            DESCRIPTION
                "Port#2 lp alarm Relay in Hex"
            ::= { balarmSetupHexEntry 11 }

        blpAlarmSeverityHex  OBJECT-TYPE
            SYNTAX  OCTET STRING(SIZE(24))
            ACCESS  read-only
            STATUS  mandatory
            DESCRIPTION
                "lp alarm Severity in Hex"
            ::= { balarmSetupHexEntry 12 }

--
-- B155/622 Current Alarm Status Table
--

    b155-622CurrAlmStTable     OBJECT IDENTIFIER ::= { b155-622-card 8 }

--
--  Physical Layer Alarm Status Table
--

    bPHYCurrStatusTable             OBJECT IDENTIFIER ::= { b155-622CurrAlmStTable 1 }


        bPHYStatusTable  OBJECT-TYPE
            SYNTAX  SEQUENCE OF BPHYStatusEntry
            ACCESS  not-accessible
            STATUS  mandatory
            DESCRIPTION
                "Physical layer Alarm Status Table"
            ::= { bPHYCurrStatusTable 1 }

        bPHYStatusEntry  OBJECT-TYPE
            SYNTAX  BPHYStatusEntry
            ACCESS  not-accessible
            STATUS  mandatory
            DESCRIPTION
                "Physical Alarm entry"
            INDEX { bPHYStatusUnitIdx , bPHYStatusPortIdx }
            ::= { bPHYStatusTable 1 }

        BPHYStatusEntry ::= SEQUENCE {
            bPHYStatusUnitIdx           UnitID,
            bPHYStatusPortIdx           PortNum,
            bbPHYStatusLOS              AlmStatus
        }

        bPHYStatusUnitIdx  OBJECT-TYPE
            SYNTAX  UnitID
            ACCESS  read-only
            STATUS  mandatory
            DESCRIPTION
                "Unit index"
            ::= { bPHYStatusEntry 1 }

        bPHYStatusPortIdx  OBJECT-TYPE
            SYNTAX  PortNum
            ACCESS  read-only
            STATUS  mandatory
            DESCRIPTION
                "Port index"
            ::= { bPHYStatusEntry 2 }

        bbPHYStatusLOS  OBJECT-TYPE
            SYNTAX  AlmStatus
            ACCESS  read-only
            STATUS  mandatory
            DESCRIPTION
                "Alarm Status"
            ::= { bPHYStatusEntry 3 }

--
--  RS-Section Layer Alarm Status Table
--

    bRS-SectionCurrStTable        OBJECT IDENTIFIER ::= { b155-622CurrAlmStTable 2 }

        bRS-SectionStatusTable  OBJECT-TYPE
            SYNTAX  SEQUENCE OF BRS-SectionStatusEntry
            ACCESS  not-accessible
            STATUS  mandatory
            DESCRIPTION
                "RS-Section layer Alarm Status Table"
            ::= { bRS-SectionCurrStTable 1 }

        bRS-SectionStatusEntry  OBJECT-TYPE
            SYNTAX  BRS-SectionStatusEntry
            ACCESS  not-accessible
            STATUS  mandatory
            DESCRIPTION
                "RS-Section layer Alarm entry"
            INDEX { bRS-SectionStUnitIdx , bRS-SectionStPortIdx }
            ::= { bRS-SectionStatusTable 1 }

        BRS-SectionStatusEntry ::= SEQUENCE {
            bRS-SectionStUnitIdx        UnitID,
            bRS-SectionStPortIdx        PortNum,
            bRS-SectionStatusLOF        AlmStatus,
            bRS-SectionStatusBIP        AlmStatus,
            bRS-SectionStatusTIM        AlmStatus
        }

        bRS-SectionStUnitIdx  OBJECT-TYPE
            SYNTAX  UnitID
            ACCESS  read-only
            STATUS  mandatory
            DESCRIPTION
                "Alarm Unit index"
            ::= { bRS-SectionStatusEntry 1 }

        bRS-SectionStPortIdx  OBJECT-TYPE
            SYNTAX  PortNum
            ACCESS  read-only
            STATUS  mandatory
            DESCRIPTION
                "Alarm Port index"
            ::= { bRS-SectionStatusEntry 2 }

        bRS-SectionStatusLOF  OBJECT-TYPE
            SYNTAX  AlmStatus
            ACCESS  read-only
            STATUS  mandatory
            DESCRIPTION
                "Alarm Status"
            ::= { bRS-SectionStatusEntry 3 }

        bRS-SectionStatusTIM  OBJECT-TYPE
            SYNTAX  AlmStatus
            ACCESS  read-only
            STATUS  mandatory
            DESCRIPTION
                "Alarm Status"
            ::= { bRS-SectionStatusEntry 4 }

        bRS-SectionStatusBIP  OBJECT-TYPE
            SYNTAX  AlmStatus
            ACCESS  read-only
            STATUS  mandatory
            DESCRIPTION
                "Alarm Status"
            ::= { bRS-SectionStatusEntry 5 }

--
--  MS-Line Layer Alarm Status Table
--


    bMS-LineCurrStTable        OBJECT IDENTIFIER ::= { b155-622CurrAlmStTable 3 }

        bMS-LineStatusTable  OBJECT-TYPE
            SYNTAX  SEQUENCE OF BMS-LineStatusEntry
            ACCESS  not-accessible
            STATUS  mandatory
            DESCRIPTION
                "MS-Line layer Alarm Status Table"
            ::= { bMS-LineCurrStTable 1 }

        bMS-LineStatusEntry  OBJECT-TYPE
            SYNTAX  BMS-LineStatusEntry
            ACCESS  not-accessible
            STATUS  mandatory
            DESCRIPTION
                "MS-Linesical Alarm entry"
            INDEX { bMS-LineStUnitIdx , bMS-LineStPortIdx }
            ::= { bMS-LineStatusTable 1 }

        BMS-LineStatusEntry ::= SEQUENCE {
            bMS-LineStUnitIdx           UnitID,
            bMS-LineStPortIdx           PortNum,
            bMS-LineStatusSD            AlmStatus,
            bMS-LineStatusSF            AlmStatus,
            bMS-LineStatusAIS           AlmStatus,
            bMS-LineStatusRDI           AlmStatus,
            bMS-LineStatusBIP           AlmStatus,
            bMS-LineStatusREI           AlmStatus
        }

        bMS-LineStUnitIdx  OBJECT-TYPE
            SYNTAX  UnitID
            ACCESS  read-only
            STATUS  mandatory
            DESCRIPTION
                "Alarm Unit Index"
            ::= { bMS-LineStatusEntry 1 }

        bMS-LineStPortIdx  OBJECT-TYPE
            SYNTAX  PortNum
            ACCESS  read-only
            STATUS  mandatory
            DESCRIPTION
                "Alarm Port Index"
            ::= { bMS-LineStatusEntry 2 }

        bMS-LineStatusSD  OBJECT-TYPE
            SYNTAX  AlmStatus
            ACCESS  read-only
            STATUS  mandatory
            DESCRIPTION
                "Alarm Status"
            ::= { bMS-LineStatusEntry 3 }

        bMS-LineStatusSF  OBJECT-TYPE
            SYNTAX  AlmStatus
            ACCESS  read-only
            STATUS  mandatory
            DESCRIPTION
                "Alarm Status"
            ::= { bMS-LineStatusEntry 4 }

        bMS-LineStatusAIS  OBJECT-TYPE
            SYNTAX  AlmStatus
            ACCESS  read-only
            STATUS  mandatory
            DESCRIPTION
                "Alarm Status"
            ::= { bMS-LineStatusEntry 5 }

        bMS-LineStatusRDI  OBJECT-TYPE
            SYNTAX  AlmStatus
            ACCESS  read-only
            STATUS  mandatory
            DESCRIPTION
                "Alarm Status"
            ::= { bMS-LineStatusEntry 6 }

        bMS-LineStatusBIP  OBJECT-TYPE
            SYNTAX  AlmStatus
            ACCESS  read-only
            STATUS  mandatory
            DESCRIPTION
                "Alarm Status"
            ::= { bMS-LineStatusEntry 7 }

        bMS-LineStatusREI  OBJECT-TYPE
            SYNTAX  AlmStatus
            ACCESS  read-only
            STATUS  mandatory
            DESCRIPTION
                "Alarm Status"
            ::= { bMS-LineStatusEntry 8 }

--
--  HoPath-STSPath Layer Alarm Status Table
--

    bHo-STSPathCurrStTable  OBJECT IDENTIFIER ::= { b155-622CurrAlmStTable 4 }

        bHo-STSStatusTable  OBJECT-TYPE
            SYNTAX  SEQUENCE OF BHo-STSStatusEntry
            ACCESS  not-accessible
            STATUS  mandatory
            DESCRIPTION
                "HoPath-STSPath layer Alarm Status Table"
            ::= { bHo-STSPathCurrStTable 1 }

        bHo-STSStatusEntry  OBJECT-TYPE
            SYNTAX  BHo-STSStatusEntry
            ACCESS  not-accessible
            STATUS  mandatory
            DESCRIPTION
                "HoPath-STSPath Alarm entry"
            INDEX { bHo-STSStatusUnitIdx , bHo-STSStatusPortIdx ,
                    bHo-STSStatusAug1Sts3Idx , bHo-STSStatusVc3Sts1Idx }
            ::= { bHo-STSStatusTable 1 }

        BHo-STSStatusEntry ::= SEQUENCE {
            bHo-STSStatusUnitIdx        UnitID,
            bHo-STSStatusPortIdx        PortNum,
            bHo-STSStatusAug1Sts3Idx    Aug1Sts3Num,
            bHo-STSStatusVc3Sts1Idx     Vc3Sts1Num,
            bHo-STSStatusMappingType    HoMappingType,
            bHo-STSStatusLOP            AlmStatus,
            bHo-STSStatusAIS            AlmStatus,
            bHo-STSStatusSD             AlmStatus,
            bHo-STSStatusSF             AlmStatus,
            bHo-STSStatusTIM            AlmStatus,
            bHo-STSStatusUNEQ           AlmStatus,
            bHo-STSStatusPLM            AlmStatus,
            bHo-STSStatusRDI-S          AlmStatus,
            bHo-STSStatusRDI-C          AlmStatus,
            bHo-STSStatusRDI-P          AlmStatus,
            bHo-STSStatusBIP            AlmStatus,
            bHo-STSStatusREI            AlmStatus,
            bHo-STSStatusLOM            AlmStatus,
            bHo-STSStatusPJ             INTEGER,
            bHo-STSStatusNJ             INTEGER
        }

        bHo-STSStatusUnitIdx  OBJECT-TYPE
            SYNTAX  UnitID
            ACCESS  read-only
            STATUS  mandatory
            DESCRIPTION
                "Alarm Unit index"
            ::= { bHo-STSStatusEntry 1 }

        bHo-STSStatusPortIdx  OBJECT-TYPE
            SYNTAX  PortNum
            ACCESS  read-only
            STATUS  mandatory
            DESCRIPTION
                "Alarm Port index"
            ::= { bHo-STSStatusEntry 2 }

        bHo-STSStatusAug1Sts3Idx  OBJECT-TYPE
            SYNTAX  Aug1Sts3Num
            ACCESS  read-only
            STATUS  mandatory
            DESCRIPTION
                "line stm1/sts3 index"
            ::= { bHo-STSStatusEntry 3 }

        bHo-STSStatusVc3Sts1Idx  OBJECT-TYPE
            SYNTAX  Vc3Sts1Num
            ACCESS  read-only
            STATUS  mandatory
            DESCRIPTION
                "line au3/sts1/tug3 index"
            ::= { bHo-STSStatusEntry 4 }

        bHo-STSStatusMappingType  OBJECT-TYPE
            SYNTAX  HoMappingType
            ACCESS  read-only
            STATUS  mandatory
            DESCRIPTION
                "Alarm Status Mapping Type"
            ::= { bHo-STSStatusEntry 5 }

        bHo-STSStatusLOP  OBJECT-TYPE
            SYNTAX  AlmStatus
            ACCESS  read-only
            STATUS  mandatory
            DESCRIPTION
                "Alarm Status"
            ::= { bHo-STSStatusEntry 6 }

        bHo-STSStatusAIS  OBJECT-TYPE
            SYNTAX  AlmStatus
            ACCESS  read-only
            STATUS  mandatory
            DESCRIPTION
                "Alarm Status"
            ::= { bHo-STSStatusEntry 7 }

        bHo-STSStatusSD  OBJECT-TYPE
            SYNTAX  AlmStatus
            ACCESS  read-only
            STATUS  mandatory
            DESCRIPTION
                "Alarm Status"
            ::= { bHo-STSStatusEntry 8 }

        bHo-STSStatusSF  OBJECT-TYPE
            SYNTAX  AlmStatus
            ACCESS  read-only
            STATUS  mandatory
            DESCRIPTION
                "Alarm Status"
            ::= { bHo-STSStatusEntry 9 }

        bHo-STSStatusTIM  OBJECT-TYPE
            SYNTAX  AlmStatus
            ACCESS  read-only
            STATUS  mandatory
            DESCRIPTION
                "Alarm Status"
            ::= { bHo-STSStatusEntry 10 }

        bHo-STSStatusUNEQ  OBJECT-TYPE
            SYNTAX  AlmStatus
            ACCESS  read-only
            STATUS  mandatory
            DESCRIPTION
                "Alarm Status"
            ::= { bHo-STSStatusEntry 11 }

        bHo-STSStatusPLM  OBJECT-TYPE
            SYNTAX  AlmStatus
            ACCESS  read-only
            STATUS  mandatory
            DESCRIPTION
                "Alarm Status"
            ::= { bHo-STSStatusEntry 12 }

        bHo-STSStatusRDI-S  OBJECT-TYPE
            SYNTAX  AlmStatus
            ACCESS  read-only
            STATUS  mandatory
            DESCRIPTION
                "Alarm Status"
            ::= { bHo-STSStatusEntry 13 }

        bHo-STSStatusRDI-C  OBJECT-TYPE
            SYNTAX  AlmStatus
            ACCESS  read-only
            STATUS  mandatory
            DESCRIPTION
                "Alarm Status"
            ::= { bHo-STSStatusEntry 14 }

        bHo-STSStatusRDI-P  OBJECT-TYPE
            SYNTAX  AlmStatus
            ACCESS  read-only
            STATUS  mandatory
            DESCRIPTION
                "Alarm Status"
            ::= { bHo-STSStatusEntry 15 }

        bHo-STSStatusBIP  OBJECT-TYPE
            SYNTAX  AlmStatus
            ACCESS  read-only
            STATUS  mandatory
            DESCRIPTION
                "Alarm Status"
            ::= { bHo-STSStatusEntry 16 }

        bHo-STSStatusREI  OBJECT-TYPE
            SYNTAX  AlmStatus
            ACCESS  read-only
            STATUS  mandatory
            DESCRIPTION
                "Alarm Status"
            ::= { bHo-STSStatusEntry 17 }

        bHo-STSStatusLOM  OBJECT-TYPE
            SYNTAX  AlmStatus
            ACCESS  read-only
            STATUS  mandatory
            DESCRIPTION
                "Alarm Status"
            ::= { bHo-STSStatusEntry 18 }

        bHo-STSStatusPJ  OBJECT-TYPE
            SYNTAX  INTEGER
            ACCESS  read-only
            STATUS  mandatory
            DESCRIPTION
                "Alarm Status"
            ::= { bHo-STSStatusEntry 19 }

        bHo-STSStatusNJ  OBJECT-TYPE
            SYNTAX  INTEGER
            ACCESS  read-only
            STATUS  mandatory
            DESCRIPTION
                "Alarm Status"
            ::= { bHo-STSStatusEntry 20 }

--
--  LoPath-VTPath Layer Alarm Status Table
--

    bLo-VTPathCurrStTable   OBJECT IDENTIFIER ::= { b155-622CurrAlmStTable 5 }

        bLo-VTStatusTable  OBJECT-TYPE
            SYNTAX  SEQUENCE OF BLo-VTStatusEntry
            ACCESS  not-accessible
            STATUS  mandatory
            DESCRIPTION
                "LoPath-VTPath layer Alarm Status Table"
            ::= { bLo-VTPathCurrStTable 1 }

        bLo-VTStatusEntry  OBJECT-TYPE
            SYNTAX  BLo-VTStatusEntry
            ACCESS  not-accessible
            STATUS  mandatory
            DESCRIPTION
                "LoPath-VTPath Alarm entry"
            INDEX { bLo-VTStatusUnitIdx , bLo-VTStatusPortIdx ,
                    bLo-VTStatusAug1Sts3Idx , bLo-VTStatusVc3Sts1Idx , bLo-VTStatusTU1xVTxIdx }
            ::= { bLo-VTStatusTable 1 }

        BLo-VTStatusEntry ::= SEQUENCE {
            bLo-VTStatusUnitIdx         UnitID,
            bLo-VTStatusPortIdx         PortNum,
            bLo-VTStatusAug1Sts3Idx     Aug1Sts3Num,
            bLo-VTStatusVc3Sts1Idx      Vc3Sts1Num,
            bLo-VTStatusTU1xVTxIdx      TU1xVtxNum,
            bLo-VTStatusMappingType     LoMappingType,
            bLo-VTStatusLOP             AlmStatus,
            bLo-VTStatusAIS             AlmStatus,
            bLo-VTStatusSD              AlmStatus,
            bLo-VTStatusSF              AlmStatus,
            bLo-VTStatusTIM             AlmStatus,
            bLo-VTStatusUNEQ            AlmStatus,
            bLo-VTStatusPLM             AlmStatus,
            bLo-VTStatusRDI-S           AlmStatus,
            bLo-VTStatusRDI-C           AlmStatus,
            bLo-VTStatusRDI-P           AlmStatus,
            bLo-VTStatusBIP             AlmStatus,
            bLo-VTStatusREI             AlmStatus,
            bLo-VTStatusPJ              INTEGER,
            bLo-VTStatusNJ              INTEGER
        }

        bLo-VTStatusUnitIdx  OBJECT-TYPE
            SYNTAX  UnitID
            ACCESS  read-only
            STATUS  mandatory
            DESCRIPTION
                "Alarm Port Index"
            ::= { bLo-VTStatusEntry 1 }

        bLo-VTStatusPortIdx  OBJECT-TYPE
            SYNTAX  PortNum
            ACCESS  read-only
            STATUS  mandatory
            DESCRIPTION
                "Alarm Port Index"
            ::= { bLo-VTStatusEntry 2 }

        bLo-VTStatusAug1Sts3Idx  OBJECT-TYPE
            SYNTAX  Aug1Sts3Num
            ACCESS  read-only
            STATUS  mandatory
            DESCRIPTION
                "line stm1/sts3 index"
            ::= { bLo-VTStatusEntry 3 }

        bLo-VTStatusVc3Sts1Idx  OBJECT-TYPE
            SYNTAX  Vc3Sts1Num
            ACCESS  read-only
            STATUS  mandatory
            DESCRIPTION
                "line au3/sts1/tug3 index"
            ::= { bLo-VTStatusEntry 4 }

        bLo-VTStatusTU1xVTxIdx  OBJECT-TYPE
            SYNTAX  TU1xVtxNum
            ACCESS  read-only
            STATUS  mandatory
            DESCRIPTION
                "line au3/sts1/tug3 index"
            ::= { bLo-VTStatusEntry 5 }

        bLo-VTStatusMappingType  OBJECT-TYPE
            SYNTAX  LoMappingType
            ACCESS  read-only
            STATUS  mandatory
            DESCRIPTION
                "Alarm Status mapping type"
            ::= { bLo-VTStatusEntry 6 }

        bLo-VTStatusLOP  OBJECT-TYPE
            SYNTAX  AlmStatus
            ACCESS  read-only
            STATUS  mandatory
            DESCRIPTION
                "Alarm Status "
            ::= { bLo-VTStatusEntry 7 }

        bLo-VTStatusAIS  OBJECT-TYPE
            SYNTAX  AlmStatus
            ACCESS  read-only
            STATUS  mandatory
            DESCRIPTION
                "Alarm Status"
            ::= { bLo-VTStatusEntry 8 }

        bLo-VTStatusSD  OBJECT-TYPE
            SYNTAX  AlmStatus
            ACCESS  read-only
            STATUS  mandatory
            DESCRIPTION
                "Alarm Status "
            ::= { bLo-VTStatusEntry 9 }

        bLo-VTStatusSF  OBJECT-TYPE
            SYNTAX  AlmStatus
            ACCESS  read-only
            STATUS  mandatory
            DESCRIPTION
                "Alarm Status "
            ::= { bLo-VTStatusEntry 10 }

        bLo-VTStatusTIM  OBJECT-TYPE
            SYNTAX  AlmStatus
            ACCESS  read-only
            STATUS  mandatory
            DESCRIPTION
                "Alarm Status "
            ::= { bLo-VTStatusEntry 11 }

        bLo-VTStatusUNEQ  OBJECT-TYPE
            SYNTAX  AlmStatus
            ACCESS  read-only
            STATUS  mandatory
            DESCRIPTION
                "Alarm Status"
            ::= { bLo-VTStatusEntry 12 }

        bLo-VTStatusPLM  OBJECT-TYPE
            SYNTAX  AlmStatus
            ACCESS  read-only
            STATUS  mandatory
            DESCRIPTION
                "Alarm Status "
            ::= { bLo-VTStatusEntry 13 }

        bLo-VTStatusRDI-S  OBJECT-TYPE
            SYNTAX  AlmStatus
            ACCESS  read-only
            STATUS  mandatory
            DESCRIPTION
                "Alarm Status "
            ::= { bLo-VTStatusEntry 14 }

        bLo-VTStatusRDI-C  OBJECT-TYPE
            SYNTAX  AlmStatus
            ACCESS  read-only
            STATUS  mandatory
            DESCRIPTION
                "Alarm Status "
            ::= { bLo-VTStatusEntry 15 }

        bLo-VTStatusRDI-P  OBJECT-TYPE
            SYNTAX  AlmStatus
            ACCESS  read-only
            STATUS  mandatory
            DESCRIPTION
                "Alarm Status "
            ::= { bLo-VTStatusEntry 16 }

        bLo-VTStatusBIP  OBJECT-TYPE
            SYNTAX  AlmStatus
            ACCESS  read-only
            STATUS  mandatory
            DESCRIPTION
                "Alarm Status "
            ::= { bLo-VTStatusEntry 17 }

        bLo-VTStatusREI  OBJECT-TYPE
            SYNTAX  AlmStatus
            ACCESS  read-only
            STATUS  mandatory
            DESCRIPTION
                "Alarm Status "
            ::= { bLo-VTStatusEntry 18 }

        bLo-VTStatusPJ  OBJECT-TYPE
            SYNTAX  INTEGER
            ACCESS  read-only
            STATUS  mandatory
            DESCRIPTION
                "Alarm Status "
            ::= { bLo-VTStatusEntry 19 }

        bLo-VTStatusNJ  OBJECT-TYPE
            SYNTAX  INTEGER
            ACCESS  read-only
            STATUS  mandatory
            DESCRIPTION
                "Alarm Status "
            ::= { bLo-VTStatusEntry 20 }

--
--  B155/622 Alarm Status Hex Table
--

        b155-622alarmStHexTable  OBJECT-TYPE
            SYNTAX  SEQUENCE OF  BalarmStHexEntry
            ACCESS  not-accessible
            STATUS  mandatory
            DESCRIPTION
                "B155/622 Line/HP/LP HEX Table "
            ::= { b155-622CurrAlmStTable 6 }

        balarmStHexEntry OBJECT-TYPE
            SYNTAX  BalarmStHexEntry
            ACCESS  not-accessible
            STATUS  mandatory
            DESCRIPTION
                "An entry in the B155/622 Line/HP/LP HEX table."
            INDEX { balarmStHexUnitIdx }
            ::= { b155-622alarmStHexTable 1 }

        BalarmStHexEntry ::= SEQUENCE  {
            balarmStHexUnitIdx          UnitID,
            blineAlarmStatusHex         OCTET STRING,
            bhpAlarmStatusHex           OCTET STRING,
            blpPort1AlarmStatusHex      OCTET STRING,
            blpPort2AlarmStatusHex      OCTET STRING
        }

        balarmStHexUnitIdx  OBJECT-TYPE
            SYNTAX  UnitID
            ACCESS  read-only
            STATUS  mandatory
            DESCRIPTION
                "Unit index"
            ::= { balarmStHexEntry 1 }

        blineAlarmStatusHex  OBJECT-TYPE
            SYNTAX  OCTET STRING(SIZE(17))
            ACCESS  read-only
            STATUS  mandatory
            DESCRIPTION
                "Line alarm status in Hex"
            ::= { balarmStHexEntry 2 }

        bhpAlarmStatusHex  OBJECT-TYPE
            SYNTAX  OCTET STRING(SIZE(97))
            ACCESS  read-only
            STATUS  mandatory
            DESCRIPTION
                "hp alarm mask in Hex"
            ::= { balarmStHexEntry 3 }

        blpPort1AlarmStatusHex  OBJECT-TYPE
            SYNTAX  OCTET STRING(SIZE(673))
            ACCESS  read-only
            STATUS  mandatory
            DESCRIPTION
                "Port#1 lp alarm status in Hex"
            ::= { balarmStHexEntry 4 }

        blpPort2AlarmStatusHex  OBJECT-TYPE
            SYNTAX  OCTET STRING(SIZE(673))
            ACCESS  read-only
            STATUS  mandatory
            DESCRIPTION
                "Port#2 lp alarm status in Hex"
            ::= { balarmStHexEntry 5 }

--
--  Current Active Alarm Summary Table
--
        b155-622CurrActAlmTable  OBJECT-TYPE
            SYNTAX  SEQUENCE OF BCurrentActiveAlarmEntry
            ACCESS  not-accessible
            STATUS  mandatory
            DESCRIPTION
                "Current Active Alarm Summary(CAAS) Table"
            ::= { b155-622-card 9 }

        bCurrentActiveAlarmEntry  OBJECT-TYPE
            SYNTAX  BCurrentActiveAlarmEntry
            ACCESS  not-accessible
            STATUS  mandatory
            DESCRIPTION
                "Current Active Alarm Table entry"
            INDEX { bActiveAlmUnit , bActiveAlmIndex }
            ::= { b155-622CurrActAlmTable 1 }

        BCurrentActiveAlarmEntry ::= SEQUENCE {
            bActiveAlmUnit              UnitID,
            bActiveAlmIndex             INTEGER (1..10000),
            bActiveAlmString            DisplayString (SIZE(0..255)),
            bActiveAlmCardModel         CardModel,
            bActiveAlmPortNum           PortID,
            bActiveAlmVcChan            INTEGER,
            bActiveAlmAlmNum            AlarmNum,
            bActiveAlmVC43STS31Type     Au4Au3Type,
            bActiveAlmTU1xVTxType       Tu1xVtxType,
            bActiveAlmAUG1STS3          Aug1Sts3Num,
            bActiveAlmTUG3              INTEGER,
            bActiveAlmTUG2VTG           INTEGER,
            bActiveAlmTU1xVTx           INTEGER,
            bActiveAlmStatus            AlmStatus,
            bActiveAlmSeverity          Severity
        }

        bActiveAlmUnit  OBJECT-TYPE
            SYNTAX  UnitID
            ACCESS  read-only
            STATUS  mandatory
            DESCRIPTION
            "unit 1 to 4."
            ::= { bCurrentActiveAlarmEntry 1 }

        bActiveAlmIndex  OBJECT-TYPE
            SYNTAX  INTEGER (1..10000)
            ACCESS  read-only
            STATUS  mandatory
            DESCRIPTION
                "Current Active Alarm Summary(CAAS) Index"
            ::= { bCurrentActiveAlarmEntry 2 }

        bActiveAlmString  OBJECT-TYPE
            SYNTAX  DisplayString (SIZE (0..255))
            ACCESS  read-only
            STATUS  mandatory
            DESCRIPTION
                "Current Active Alarm Summary String"
            ::= { bCurrentActiveAlarmEntry 3 }

        bActiveAlmCardModel  OBJECT-TYPE
            SYNTAX  CardModel
            ACCESS  read-only
            STATUS  mandatory
            DESCRIPTION
                "Card Model"
            ::= { bCurrentActiveAlarmEntry 4 }

        bActiveAlmPortNum  OBJECT-TYPE
            SYNTAX  PortID
            ACCESS  read-only
            STATUS  mandatory
            DESCRIPTION
                "Port number"
            ::= { bCurrentActiveAlarmEntry 5 }

        bActiveAlmVcChan  OBJECT-TYPE
            SYNTAX  INTEGER
            ACCESS  read-only
            STATUS  mandatory
            DESCRIPTION
                "VC Channel"
            ::= { bCurrentActiveAlarmEntry 6 }

        bActiveAlmAlmNum  OBJECT-TYPE
            SYNTAX  AlarmNum
            ACCESS  read-only
            STATUS  mandatory
            DESCRIPTION
                "Alarm Num"
            ::= { bCurrentActiveAlarmEntry 7 }

        bActiveAlmVC43STS31Type  OBJECT-TYPE
            SYNTAX  Au4Au3Type
            ACCESS  read-only
            STATUS  mandatory
            DESCRIPTION
                "AU4 or AU3 type"
            ::= { bCurrentActiveAlarmEntry 8 }

        bActiveAlmTU1xVTxType  OBJECT-TYPE
            SYNTAX  Tu1xVtxType
            ACCESS  read-only
            STATUS  mandatory
            DESCRIPTION
                "Tu1x type"
            ::= { bCurrentActiveAlarmEntry 9 }

        bActiveAlmAUG1STS3  OBJECT-TYPE
            SYNTAX  Aug1Sts3Num
            ACCESS  read-only
            STATUS  mandatory
            DESCRIPTION
                "The number of AU4"
            ::= { bCurrentActiveAlarmEntry 10 }

        bActiveAlmTUG3  OBJECT-TYPE
            SYNTAX  INTEGER
            ACCESS  read-only
            STATUS  mandatory
            DESCRIPTION
                "The number of Tug3"
            ::= { bCurrentActiveAlarmEntry 11 }

        bActiveAlmTUG2VTG  OBJECT-TYPE
            SYNTAX  INTEGER
            ACCESS  read-only
            STATUS  mandatory
            DESCRIPTION
                "The number of Tug2"
            ::= { bCurrentActiveAlarmEntry 12 }

        bActiveAlmTU1xVTx  OBJECT-TYPE
            SYNTAX  INTEGER
            ACCESS  read-only
            STATUS  mandatory
            DESCRIPTION
                "The number of Tu1x"
            ::= { bCurrentActiveAlarmEntry 13 }

        bActiveAlmStatus  OBJECT-TYPE
            SYNTAX  AlmStatus
            ACCESS  read-only
            STATUS  mandatory
            DESCRIPTION
                "The Status of Alarm"
            ::= { bCurrentActiveAlarmEntry 14 }

        bActiveAlmSeverity  OBJECT-TYPE
            SYNTAX  Severity
            ACCESS  read-only
            STATUS  mandatory
            DESCRIPTION
                "Alarm Severity"
            ::= { bCurrentActiveAlarmEntry 15 }

--
--  B155/622 SF/SD Table
--
        b155-622SfSdThreshTab  OBJECT-TYPE
            SYNTAX  SEQUENCE OF  B155-622SfSdThreshEty
            ACCESS  not-accessible
            STATUS  mandatory
            DESCRIPTION
                "B155/622 SF/SD alarm threshold table "
            ::= { b155-622-card 10 }

        b155-622SfSdThreshEty  OBJECT-TYPE
            SYNTAX  B155-622SfSdThreshEty
            ACCESS  not-accessible
            STATUS  mandatory
            DESCRIPTION
                "B155/622 SF/SD alarm threshold entry"
            INDEX { bSfSdUnit }
            ::= { b155-622SfSdThreshTab 1 }

        B155-622SfSdThreshEty ::= SEQUENCE {
            bSfSdUnit                   UnitID,
            bSfSdMS-LineSdThresh        INTEGER,
            bSfSdMS-LineSfThresh        INTEGER,
            bSfSdHO-STSPathSdThresh     INTEGER,
            bSfSdHO-STSPathSfThresh     INTEGER,
            bSfSdLO-VTPathSdThresh      INTEGER,
            bSfSdLO-VTPathSfThresh      INTEGER
        }

        bSfSdUnit  OBJECT-TYPE
            SYNTAX  UnitID
            ACCESS  read-only
            STATUS  mandatory
            DESCRIPTION
            "unit 1 to 4."
            ::= { b155-622SfSdThreshEty 1 }

        bSfSdMS-LineSdThresh   OBJECT-TYPE
            SYNTAX  INTEGER {
                    e-3(1),
                    e-4(2),
                    e-5(3),
                    e-6(4),
                    e-7(5),
                    e-8(6),
                    e-9(7),
                    e-10(8),
                    e-11(9)
                }
            ACCESS  read-write
            STATUS  mandatory
            DESCRIPTION
                "MS/line sd threshold"
            ::= { b155-622SfSdThreshEty 2 }

        bSfSdMS-LineSfThresh   OBJECT-TYPE
            SYNTAX  INTEGER {
                    e-3(1),
                    e-4(2),
                    e-5(3),
                    e-6(4),
                    e-7(5),
                    e-8(6),
                    e-9(7),
                    e-10(8),
                    e-11(9)
                }
            ACCESS  read-write
            STATUS  mandatory
            DESCRIPTION
                "MS/line sf threshold"
            ::= { b155-622SfSdThreshEty 3 }

        bSfSdHO-STSPathSdThresh        OBJECT-TYPE
            SYNTAX  INTEGER {
                    e-3(1),
                    e-4(2),
                    e-5(3),
                    e-6(4),
                    e-7(5),
                    e-8(6),
                    e-9(7),
                    e-10(8),
                    e-11(9)
                }
            ACCESS  read-write
            STATUS  mandatory
            DESCRIPTION
                "HO/STS path sd threshold"
            ::= { b155-622SfSdThreshEty 4 }

        bSfSdHO-STSPathSfThresh        OBJECT-TYPE
            SYNTAX  INTEGER {
                    e-3(1),
                    e-4(2),
                    e-5(3),
                    e-6(4),
                    e-7(5),
                    e-8(6),
                    e-9(7),
                    e-10(8),
                    e-11(9)
                }
            ACCESS  read-write
            STATUS  mandatory
            DESCRIPTION
                "HO/STS path sf threshold"
            ::= { b155-622SfSdThreshEty 5 }

        bSfSdLO-VTPathSdThresh         OBJECT-TYPE
            SYNTAX  INTEGER {
                    e-3(1),
                    e-4(2),
                    e-5(3),
                    e-6(4),
                    e-7(5),
                    e-8(6),
                    e-9(7),
                    e-10(8),
                    e-11(9)
                }
            ACCESS  read-write
            STATUS  mandatory
            DESCRIPTION
                "LO/VT path sd threshold"
            ::= { b155-622SfSdThreshEty 6 }

        bSfSdLO-VTPathSfThresh         OBJECT-TYPE
            SYNTAX  INTEGER {
                    e-3(1),
                    e-4(2),
                    e-5(3),
                    e-6(4),
                    e-7(5),
                    e-8(6),
                    e-9(7),
                    e-10(8),
                    e-11(9)
                }
            ACCESS  read-write
            STATUS  mandatory
            DESCRIPTION
                "LO/VT path sf threshold"
            ::= { b155-622SfSdThreshEty 7 }

--
--  B155/622 Insert AIS Alarm Table
--
        b155-622InsertAisAlmTab  OBJECT-TYPE
            SYNTAX  SEQUENCE OF  B155-622InsertAisAlmEty
            ACCESS  not-accessible
            STATUS  mandatory
            DESCRIPTION
                "B155/622 insert AIS alarm table "
            ::= { b155-622-card 11 }

        b155-622InsertAisAlmEty  OBJECT-TYPE
            SYNTAX  B155-622InsertAisAlmEty
            ACCESS  not-accessible
            STATUS  mandatory
            DESCRIPTION
                "B155/622 insert AIS alarm entry"
            INDEX { bInsAisUnit }
            ::= { b155-622InsertAisAlmTab 1 }

        B155-622InsertAisAlmEty ::= SEQUENCE {
            bInsAisUnit                 UnitID,
            bInsAisRsTim-TimLToAis      INTEGER,
            bInsAisMsAis-AisLToAis      INTEGER,
            bInsAisAuLop-LopPToAis      INTEGER,
            bInsAisAuAis-AisPToAis      INTEGER,
            bInsAisHpUneq-UneqPToAis    INTEGER,
            bInsAisHpTim-TimPToAis      INTEGER,
            bInsAisHpLom-LomPToAis      INTEGER,
            bInsAisHpPlm-PlmPToAis      INTEGER,
            bInsAisTuLop-LopVToAis      INTEGER,
            bInsAisTuAis-AisVToAis      INTEGER,
            bInsAisLpUneq-UneqVToAis    INTEGER
        }

        bInsAisUnit  OBJECT-TYPE
            SYNTAX  UnitID
            ACCESS  read-only
            STATUS  mandatory
            DESCRIPTION
            "unit 1 to 4."
            ::= { b155-622InsertAisAlmEty 1 }

        bInsAisRsTim-TimLToAis  OBJECT-TYPE
            SYNTAX  INTEGER {
                    disable(1),
                    enable(2)
                }
            ACCESS  read-write
            STATUS  mandatory
            DESCRIPTION
                "RS-TIM/TIM-L To Ais"
            ::= { b155-622InsertAisAlmEty 2 }

        bInsAisMsAis-AisLToAis  OBJECT-TYPE
            SYNTAX  INTEGER {
                    disable(1),
                    enable(2)
                }
            ACCESS  read-write
            STATUS  mandatory
            DESCRIPTION
                "MS-AIS/AIS-L To Ais"
            ::= { b155-622InsertAisAlmEty 3 }

        bInsAisAuLop-LopPToAis  OBJECT-TYPE
            SYNTAX  INTEGER {
                    disable(1),
                    enable(2)
                }
            ACCESS  read-write
            STATUS  mandatory
            DESCRIPTION
                "AU-LOP/LOP-P To Ais"
            ::= { b155-622InsertAisAlmEty 4 }

        bInsAisAuAis-AisPToAis  OBJECT-TYPE
            SYNTAX  INTEGER {
                    disable(1),
                    enable(2)
                }
            ACCESS  read-write
            STATUS  mandatory
            DESCRIPTION
                "AU-AIS/AIS-P To Ais"
            ::= { b155-622InsertAisAlmEty 5 }

        bInsAisHpUneq-UneqPToAis  OBJECT-TYPE
            SYNTAX  INTEGER {
                    disable(1),
                    enable(2)
                }
            ACCESS  read-write
            STATUS  mandatory
            DESCRIPTION
                "HP-UNEQ/UNEQ-P To Ais"
            ::= { b155-622InsertAisAlmEty 6 }

        bInsAisHpTim-TimPToAis  OBJECT-TYPE
            SYNTAX  INTEGER {
                    disable(1),
                    enable(2)
                }
            ACCESS  read-write
            STATUS  mandatory
            DESCRIPTION
                "HP-TIM/TIM-P To Ais"
            ::= { b155-622InsertAisAlmEty 7 }

        bInsAisHpLom-LomPToAis  OBJECT-TYPE
            SYNTAX  INTEGER {
                    disable(1),
                    enable(2)
                }
            ACCESS  read-write
            STATUS  mandatory
            DESCRIPTION
                "HP-LOM/LOM-P To Ais"
            ::= { b155-622InsertAisAlmEty 8 }

        bInsAisHpPlm-PlmPToAis  OBJECT-TYPE
            SYNTAX  INTEGER {
                    disable(1),
                    enable(2)
                }
            ACCESS  read-write
            STATUS  mandatory
            DESCRIPTION
                "HP-PLM/PLM-P To Ais"
            ::= { b155-622InsertAisAlmEty 9 }

        bInsAisTuLop-LopVToAis  OBJECT-TYPE
            SYNTAX  INTEGER {
                    disable(1),
                    enable(2)
                }
            ACCESS  read-write
            STATUS  mandatory
            DESCRIPTION
                "TU-LOP/LOP-V To Ais"
            ::= { b155-622InsertAisAlmEty 10 }

        bInsAisTuAis-AisVToAis  OBJECT-TYPE
            SYNTAX  INTEGER {
                    disable(1),
                    enable(2)
                }
            ACCESS  read-write
            STATUS  mandatory
            DESCRIPTION
                "TU-AIS/AIS-V To Ais"
            ::= { b155-622InsertAisAlmEty 11 }

        bInsAisLpUneq-UneqVToAis  OBJECT-TYPE
            SYNTAX  INTEGER {
                    disable(1),
                    enable(2)
                }
            ACCESS  read-write
            STATUS  mandatory
            DESCRIPTION
                "LP-UNEQ/UNEQ-V To Ais"
            ::= { b155-622InsertAisAlmEty 12 }

--
--  B155/622 SFP information Table
--
        b155-622SfpInfoTab  OBJECT-TYPE
            SYNTAX  SEQUENCE OF  B155-622SfpInfoEty
            ACCESS  not-accessible
            STATUS  mandatory
            DESCRIPTION
                "B155/622 SFP Information table"
            ::= { b155-622-card 12 }

        b155-622SfpInfoEty  OBJECT-TYPE
            SYNTAX  B155-622SfpInfoEty
            ACCESS  not-accessible
            STATUS  mandatory
            DESCRIPTION
                "An entry in the B155/622 SFP information table."
            INDEX { bSfpInfoUnit , bSfpInfoPort }
            ::= { b155-622SfpInfoTab 1 }

        B155-622SfpInfoEty ::= SEQUENCE  {
            bSfpInfoUnit                UnitID,
            bSfpInfoPort                PortID,
            bSfpInfoEquip               INTEGER,
            bSfpInfoConnector           INTEGER,
            bSfpInfoTransceiver         DisplayString,
            bSfpInfoLinkLength          DisplayString,
            bSfpInfoTechnology          DisplayString,
            bSfpInfoEncoding            DisplayString,
            bSfpInfoLen-9-125-um        DisplayString,
            bSfpInfoLen-50-125-um       DisplayString,
            bSfpInfoLen-62p5-125-um     DisplayString,
            bSfpInfoLen-copper          DisplayString,
            bSfpInfoTemperature         DisplayString,
            bSfpInfoVcc                 DisplayString,
            bSfpInfoTxBias              DisplayString,
            bSfpInfoTxPower             DisplayString,
            bSfpInfoRxPower             DisplayString,
            bSfpInfoDateCode            DisplayString,
            bSfpInfoVendorName          DisplayString,
            bSfpInfoVendorOUI           DisplayString,
            bSfpInfoVendorPN            DisplayString,
            bSfpInfoVendorRev           DisplayString,
            bSfpInfoWaveLength          DisplayString
        }

        bSfpInfoUnit  OBJECT-TYPE
            SYNTAX  UnitID
            ACCESS  read-only
            STATUS  mandatory
            DESCRIPTION
            "unit 1 to 4."
            ::= { b155-622SfpInfoEty  1 }

        bSfpInfoPort  OBJECT-TYPE
            SYNTAX  PortID
            ACCESS  read-only
            STATUS  mandatory
            DESCRIPTION
                "PORT #1~#2"
            ::= { b155-622SfpInfoEty  2 }

        bSfpInfoEquip  OBJECT-TYPE
            SYNTAX  INTEGER {
                    unequipped(1),
                    equipped(2)
                }
            ACCESS  read-only
            STATUS  mandatory
            DESCRIPTION
                "Port equip or not"
            ::= { b155-622SfpInfoEty 3 }

        bSfpInfoConnector  OBJECT-TYPE
            SYNTAX  INTEGER {
                    not-available(1),
                    sc(2),
                    fibre-channel-style-1-copper(3),
                    fibre-hannel-style-2-copper(4),
                    bnc-tnc(5),
                    fibre-channel-coaxial-header(6),
                    fiberJack(7),
                    lc(8),
                    mt-rj(9),
                    mu(10),
                    sg(11),
                    optcal-pigtail(12),
                    hssdc-ii(13),
                    copper-pigtail(14)
                }
            ACCESS  read-only
            STATUS  mandatory
            DESCRIPTION
                "Port connector"
            ::= { b155-622SfpInfoEty 4 }

        bSfpInfoTransceiver  OBJECT-TYPE
            SYNTAX  DisplayString (SIZE (0..255) )
            ACCESS  read-only
            STATUS  mandatory
            DESCRIPTION
                "Port transceiver"
            ::= { b155-622SfpInfoEty 5 }

        bSfpInfoLinkLength  OBJECT-TYPE
            SYNTAX  DisplayString (SIZE (0..255) )
            ACCESS  read-only
            STATUS  mandatory
            DESCRIPTION
                "Port Link Length"
            ::= { b155-622SfpInfoEty 6 }

        bSfpInfoTechnology  OBJECT-TYPE
            SYNTAX  DisplayString (SIZE (0..255) )
            ACCESS  read-only
            STATUS  mandatory
            DESCRIPTION
                "Port Technology"
            ::= { b155-622SfpInfoEty 7 }

        bSfpInfoEncoding  OBJECT-TYPE
            SYNTAX  DisplayString (SIZE (0..255) )
            ACCESS  read-only
            STATUS  mandatory
            DESCRIPTION
                "Port Encoding"
            ::= { b155-622SfpInfoEty 8 }

        bSfpInfoLen-9-125-um  OBJECT-TYPE
            SYNTAX  DisplayString (SIZE (0..255) )
            ACCESS  read-only
            STATUS  mandatory
            DESCRIPTION
                "Port length for 9/125 um fiber"
            ::= { b155-622SfpInfoEty 9 }

        bSfpInfoLen-50-125-um  OBJECT-TYPE
            SYNTAX  DisplayString (SIZE (0..255) )
            ACCESS  read-only
            STATUS  mandatory
            DESCRIPTION
                "Port length for 50/125 um fiber"
            ::= { b155-622SfpInfoEty 10 }

        bSfpInfoLen-62p5-125-um  OBJECT-TYPE
            SYNTAX  DisplayString (SIZE (0..255) )
            ACCESS  read-only
            STATUS  mandatory
            DESCRIPTION
                "Port length for 62.5/125 um fiber"
            ::= { b155-622SfpInfoEty 11 }

        bSfpInfoLen-copper  OBJECT-TYPE
            SYNTAX  DisplayString (SIZE (0..255) )
            ACCESS  read-only
            STATUS  mandatory
            DESCRIPTION
                "Port length for copper"
            ::= { b155-622SfpInfoEty 12 }

        bSfpInfoTemperature  OBJECT-TYPE
            SYNTAX  DisplayString (SIZE (0..255) )
            ACCESS  read-only
            STATUS  mandatory
            DESCRIPTION
                "Port Temperature"
            ::= { b155-622SfpInfoEty 13 }

        bSfpInfoVcc  OBJECT-TYPE
            SYNTAX  DisplayString (SIZE (0..255) )
            ACCESS  read-only
            STATUS  mandatory
            DESCRIPTION
                "Port Vcc"
            ::= { b155-622SfpInfoEty 14 }

        bSfpInfoTxBias  OBJECT-TYPE
            SYNTAX  DisplayString (SIZE (0..255) )
            ACCESS  read-only
            STATUS  mandatory
            DESCRIPTION
                "Port Tx Bias current"
            ::= { b155-622SfpInfoEty 15 }

        bSfpInfoTxPower  OBJECT-TYPE
            SYNTAX  DisplayString (SIZE (0..255) )
            ACCESS  read-only
            STATUS  mandatory
            DESCRIPTION
                "Port Tx power"
            ::= { b155-622SfpInfoEty 16 }

        bSfpInfoRxPower  OBJECT-TYPE
            SYNTAX  DisplayString (SIZE (0..255) )
            ACCESS  read-only
            STATUS  mandatory
            DESCRIPTION
                "Port Rx power"
            ::= { b155-622SfpInfoEty 17 }
        bSfpInfoDateCode  OBJECT-TYPE
            SYNTAX  DisplayString (SIZE (0..255) )
            ACCESS  read-only
            STATUS  mandatory
            DESCRIPTION
                "Port date code "
            ::= { b155-622SfpInfoEty 18 }

        bSfpInfoVendorName  OBJECT-TYPE
            SYNTAX  DisplayString (SIZE (0..255) )
            ACCESS  read-only
            STATUS  mandatory
            DESCRIPTION
                "Port vendor name "
            ::= { b155-622SfpInfoEty 19 }

        bSfpInfoVendorOUI  OBJECT-TYPE
            SYNTAX  DisplayString (SIZE (0..255) )
            ACCESS  read-only
            STATUS  mandatory
            DESCRIPTION
                "Port vendor OUI "
            ::= { b155-622SfpInfoEty 20 }

        bSfpInfoVendorPN  OBJECT-TYPE
            SYNTAX  DisplayString (SIZE (0..255) )
            ACCESS  read-only
            STATUS  mandatory
            DESCRIPTION
                "Port vendor pn "
            ::= { b155-622SfpInfoEty 21 }

        bSfpInfoVendorRev  OBJECT-TYPE
            SYNTAX  DisplayString (SIZE (0..255) )
            ACCESS  read-only
            STATUS  mandatory
            DESCRIPTION
                "Port vendor rev "
            ::= { b155-622SfpInfoEty 22 }

        bSfpInfoWaveLength  OBJECT-TYPE
            SYNTAX  DisplayString (SIZE (0..255) )
            ACCESS  read-only
            STATUS  mandatory
            DESCRIPTION
                "Port wave length "
            ::= { b155-622SfpInfoEty 23 }

--
--  B155/622 Performance Threshold Table
--
    b155-622PerfThreshTab  OBJECT IDENTIFIER ::= { b155-622-card 13 }

--
--  B155/622 Performance TCA Mask Table
--
        b155-622TcaMaskTab  OBJECT-TYPE
            SYNTAX  SEQUENCE OF  B155-622TcaMaskEty
            ACCESS  not-accessible
            STATUS  mandatory
            DESCRIPTION
                "B155/622 performance TCA mask table "
            ::= { b155-622PerfThreshTab 1 }

        b155-622TcaMaskEty  OBJECT-TYPE
            SYNTAX  B155-622TcaMaskEty
            ACCESS  not-accessible
            STATUS  mandatory
            DESCRIPTION
                "B155/622 performance TCA mask entry"
            INDEX { bTcaMaskUnit }
            ::= { b155-622TcaMaskTab 1 }

        B155-622TcaMaskEty ::= SEQUENCE {
            bTcaMaskUnit                UnitID,
            bTcaMaskRs-Section          INTEGER,
            bTcaMaskMs-Line             INTEGER,
            bTcaMaskFarEndMs-Line       INTEGER,
            bTcaMaskHp-Sts              INTEGER,
            bTcaMaskFarEndHp-Sts        INTEGER,
            bTcaMaskLp-Vt-V5            INTEGER,
            bTcaMaskFarEndLp-Vt-V5      INTEGER,
            bTcaMaskLp-Vt-B3            INTEGER,
            bTcaMaskFarEndLp-Vt-B3      INTEGER
        }

        bTcaMaskUnit  OBJECT-TYPE
            SYNTAX  UnitID
            ACCESS  read-only
            STATUS  mandatory
            DESCRIPTION
            "unit 1 to 4."
            ::= { b155-622TcaMaskEty 1 }

        bTcaMaskRs-Section  OBJECT-TYPE
            SYNTAX  INTEGER {
                    disable(1),
                    enable(2)
                }
            ACCESS  read-write
            STATUS  mandatory
            DESCRIPTION
                "RS/Section TCA Mask"
            ::= { b155-622TcaMaskEty 2 }

        bTcaMaskMs-Line  OBJECT-TYPE
            SYNTAX  INTEGER {
                    disable(1),
                    enable(2)
                }
            ACCESS  read-write
            STATUS  mandatory
            DESCRIPTION
                "MS/Line TCA Mask"
            ::= { b155-622TcaMaskEty 3 }

        bTcaMaskFarEndMs-Line  OBJECT-TYPE
            SYNTAX  INTEGER {
                    disable(1),
                    enable(2)
                }
            ACCESS  read-write
            STATUS  mandatory
            DESCRIPTION
                "FarEnd MS/Line TCA Mask"
            ::= { b155-622TcaMaskEty 4 }

        bTcaMaskHp-Sts  OBJECT-TYPE
            SYNTAX  INTEGER {
                    disable(1),
                    enable(2)
                }
            ACCESS  read-write
            STATUS  mandatory
            DESCRIPTION
                "HP/STS TCA Mask"
            ::= { b155-622TcaMaskEty 5 }

        bTcaMaskFarEndHp-Sts  OBJECT-TYPE
            SYNTAX  INTEGER {
                    disable(1),
                    enable(2)
                }
            ACCESS  read-write
            STATUS  mandatory
            DESCRIPTION
                "FarEnd HP/STS TCA Mask"
            ::= { b155-622TcaMaskEty 6 }

        bTcaMaskLp-Vt-V5  OBJECT-TYPE
            SYNTAX  INTEGER {
                    disable(1),
                    enable(2)
                }
            ACCESS  read-write
            STATUS  mandatory
            DESCRIPTION
                "LP/VT V5 TCA Mask"
            ::= { b155-622TcaMaskEty 7 }

        bTcaMaskFarEndLp-Vt-V5  OBJECT-TYPE
            SYNTAX  INTEGER {
                    disable(1),
                    enable(2)
                }
            ACCESS  read-write
            STATUS  mandatory
            DESCRIPTION
                "FarEnd LP/VT V5 TCA Mask"
            ::= { b155-622TcaMaskEty 8 }

        bTcaMaskLp-Vt-B3  OBJECT-TYPE
            SYNTAX  INTEGER {
                    disable(1),
                    enable(2)
                }
            ACCESS  read-write
            STATUS  mandatory
            DESCRIPTION
                "LP/VT B3 TCA Mask"
            ::= { b155-622TcaMaskEty 9 }

        bTcaMaskFarEndLp-Vt-B3  OBJECT-TYPE
            SYNTAX  INTEGER {
                    disable(1),
                    enable(2)
                }
            ACCESS  read-write
            STATUS  mandatory
            DESCRIPTION
                "FarEnd LP/VT B3 TCA Mask"
            ::= { b155-622TcaMaskEty 10 }

--
--  B155/622 Performance TCA Severity Table
--
        b155-622TcaSvrityTab  OBJECT-TYPE
            SYNTAX  SEQUENCE OF  B155-622TcaSvrityEty
            ACCESS  not-accessible
            STATUS  mandatory
            DESCRIPTION
                "B155/622 performance TCA severity table "
            ::= { b155-622PerfThreshTab 2 }

        b155-622TcaSvrityEty  OBJECT-TYPE
            SYNTAX  B155-622TcaSvrityEty
            ACCESS  not-accessible
            STATUS  mandatory
            DESCRIPTION
                "B155/622 performance TCA severity entry"
            INDEX { bTcaSvrityUnit }
            ::= { b155-622TcaSvrityTab 1 }

        B155-622TcaSvrityEty ::= SEQUENCE {
            bTcaSvrityUnit              UnitID,
            bTcaSvrityRs-Section        Severity,
            bTcaSvrityMs-Line           Severity,
            bTcaSvrityFarEndMs-Line     Severity,
            bTcaSvrityHp-Sts            Severity,
            bTcaSvrityFarEndHp-Sts      Severity,
            bTcaSvrityLp-Vt-V5          Severity,
            bTcaSvrityFarEndLp-Vt-V5    Severity,
            bTcaSvrityLp-Vt-B3          Severity,
            bTcaSvrityFarEndLp-Vt-B3    Severity
        }

        bTcaSvrityUnit  OBJECT-TYPE
            SYNTAX  UnitID
            ACCESS  read-only
            STATUS  mandatory
            DESCRIPTION
            "unit 1 to 4."
            ::= { b155-622TcaSvrityEty 1 }

        bTcaSvrityRs-Section  OBJECT-TYPE
            SYNTAX  Severity
            ACCESS  read-write
            STATUS  mandatory
            DESCRIPTION
                "RS/Section TCA Severity"
            ::= { b155-622TcaSvrityEty 2 }

        bTcaSvrityMs-Line  OBJECT-TYPE
            SYNTAX  Severity
            ACCESS  read-write
            STATUS  mandatory
            DESCRIPTION
                "MS/Line TCA Severity"
            ::= { b155-622TcaSvrityEty 3 }

        bTcaSvrityFarEndMs-Line  OBJECT-TYPE
            SYNTAX  Severity
            ACCESS  read-write
            STATUS  mandatory
            DESCRIPTION
                "FarEnd MS/Line TCA Severity"
            ::= { b155-622TcaSvrityEty 4 }

        bTcaSvrityHp-Sts  OBJECT-TYPE
            SYNTAX  Severity
            ACCESS  read-write
            STATUS  mandatory
            DESCRIPTION
                "HP/STS TCA Severity"
            ::= { b155-622TcaSvrityEty 5 }

        bTcaSvrityFarEndHp-Sts  OBJECT-TYPE
            SYNTAX  Severity
            ACCESS  read-write
            STATUS  mandatory
            DESCRIPTION
                "FarEnd HP/STS TCA Severity"
            ::= { b155-622TcaSvrityEty 6 }

        bTcaSvrityLp-Vt-V5  OBJECT-TYPE
            SYNTAX  Severity
            ACCESS  read-write
            STATUS  mandatory
            DESCRIPTION
                "LP/VT V5 TCA Severity"
            ::= { b155-622TcaSvrityEty 7 }

        bTcaSvrityFarEndLp-Vt-V5  OBJECT-TYPE
            SYNTAX  Severity
            ACCESS  read-write
            STATUS  mandatory
            DESCRIPTION
                "FarEnd LP/VT V5 TCA Severity"
            ::= { b155-622TcaSvrityEty 8 }

        bTcaSvrityLp-Vt-B3  OBJECT-TYPE
            SYNTAX  Severity
            ACCESS  read-write
            STATUS  mandatory
            DESCRIPTION
                "LP/VT B3 TCA Severity"
            ::= { b155-622TcaSvrityEty 9 }

        bTcaSvrityFarEndLp-Vt-B3  OBJECT-TYPE
            SYNTAX  Severity
            ACCESS  read-write
            STATUS  mandatory
            DESCRIPTION
                "FarEnd LP/VT B3 TCA Severity"
            ::= { b155-622TcaSvrityEty 10 }

--
--  B155/622 Performance TCA Threshold Table
--
        b155-622TcaThreshTab  OBJECT-TYPE
            SYNTAX  SEQUENCE OF  B155-622TcaThreshEty
            ACCESS  not-accessible
            STATUS  mandatory
            DESCRIPTION
                "B155/622 performance TCA threshold table "
            ::= { b155-622PerfThreshTab 3 }

        b155-622TcaThreshEty  OBJECT-TYPE
            SYNTAX  B155-622TcaThreshEty
            ACCESS  not-accessible
            STATUS  mandatory
            DESCRIPTION
                "B155/622 performance TCA threshold entry"
            INDEX { bTcaThreshUnit }
            ::= { b155-622TcaThreshTab 1 }

        B155-622TcaThreshEty ::= SEQUENCE {
            bTcaThreshUnit              UnitID,
            bTcaThreshRs-Section        INTEGER,
            bTcaThreshMs-Line           INTEGER,
            bTcaThreshFarEndMs-Line     INTEGER,
            bTcaThreshHp-Sts            INTEGER,
            bTcaThreshFarEndHp-Sts      INTEGER,
            bTcaThreshLp-Vt-V5          INTEGER,
            bTcaThreshFarEndLp-Vt-V5    INTEGER,
            bTcaThreshLp-Vt-B3          INTEGER,
            bTcaThreshFarEndLp-Vt-B3    INTEGER
        }

        bTcaThreshUnit  OBJECT-TYPE
            SYNTAX  UnitID
            ACCESS  read-only
            STATUS  mandatory
            DESCRIPTION
            "unit 1 to 4."
            ::= { b155-622TcaThreshEty 1 }

        bTcaThreshRs-Section  OBJECT-TYPE
            SYNTAX  INTEGER (1..99999)
            ACCESS  read-write
            STATUS  mandatory
            DESCRIPTION
                "RS/Section TCA Thresh"
            ::= { b155-622TcaThreshEty 2 }

        bTcaThreshMs-Line  OBJECT-TYPE
            SYNTAX  INTEGER (1..99999)
            ACCESS  read-write
            STATUS  mandatory
            DESCRIPTION
                "MS/Line TCA Thresh"
            ::= { b155-622TcaThreshEty 3 }

        bTcaThreshFarEndMs-Line  OBJECT-TYPE
            SYNTAX  INTEGER (1..99999)
            ACCESS  read-write
            STATUS  mandatory
            DESCRIPTION
                "FarEnd MS/Line TCA Thresh"
            ::= { b155-622TcaThreshEty 4 }

        bTcaThreshHp-Sts  OBJECT-TYPE
            SYNTAX  INTEGER (1..99999)
            ACCESS  read-write
            STATUS  mandatory
            DESCRIPTION
                "HP/STS TCA Thresh"
            ::= { b155-622TcaThreshEty 5 }

        bTcaThreshFarEndHp-Sts  OBJECT-TYPE
            SYNTAX  INTEGER (1..99999)
            ACCESS  read-write
            STATUS  mandatory
            DESCRIPTION
                "FarEnd HP/STS TCA Thresh"
            ::= { b155-622TcaThreshEty 6 }

        bTcaThreshLp-Vt-V5  OBJECT-TYPE
            SYNTAX  INTEGER (1..99999)
            ACCESS  read-write
            STATUS  mandatory
            DESCRIPTION
                "LP/VT V5 TCA Thresh"
            ::= { b155-622TcaThreshEty 7 }

        bTcaThreshFarEndLp-Vt-V5  OBJECT-TYPE
            SYNTAX  INTEGER (1..99999)
            ACCESS  read-write
            STATUS  mandatory
            DESCRIPTION
                "FarEnd LP/VT V5 TCA Thresh"
            ::= { b155-622TcaThreshEty 8 }

        bTcaThreshLp-Vt-B3  OBJECT-TYPE
            SYNTAX  INTEGER (1..99999)
            ACCESS  read-write
            STATUS  mandatory
            DESCRIPTION
                "LP/VT B3 TCA Thresh"
            ::= { b155-622TcaThreshEty 9 }

        bTcaThreshFarEndLp-Vt-B3  OBJECT-TYPE
            SYNTAX  INTEGER (1..99999)
            ACCESS  read-write
            STATUS  mandatory
            DESCRIPTION
                "FarEnd LP/VT B3 TCA Thresh"
            ::= { b155-622TcaThreshEty 10 }

--
--  B155/622 Performance Control Table
--
        b155-622PerfControlTab  OBJECT-TYPE
            SYNTAX  SEQUENCE OF  B155-622PerfControlEty
            ACCESS  not-accessible
            STATUS  mandatory
            DESCRIPTION
                "B155/622 performance control table "
            ::= { b155-622-card 14 }

        b155-622PerfControlEty  OBJECT-TYPE
            SYNTAX  B155-622PerfControlEty
            ACCESS  not-accessible
            STATUS  mandatory
            DESCRIPTION
                "B155/622 performance control entry"
            INDEX { bPerfCtrlUnit }
            ::= { b155-622PerfControlTab 1 }

        B155-622PerfControlEty ::= SEQUENCE {
            bPerfCtrlUnit               UnitID,
            bPerfCtrlPerfClear          INTEGER
        }

        bPerfCtrlUnit  OBJECT-TYPE
            SYNTAX  UnitID
            ACCESS  read-only
            STATUS  mandatory
            DESCRIPTION
            "unit 1 to 4."
            ::= { b155-622PerfControlEty 1 }

        bPerfCtrlPerfClear  OBJECT-TYPE
            SYNTAX  INTEGER {
                    no(1),
                    clear(2)
                }
            ACCESS  read-write
            STATUS  mandatory
            DESCRIPTION
                "Clear performance"
            ::= { b155-622PerfControlEty 2 }

--
--  B155/622 Performance Display Table
--
    b155-622PerfDisplayTab  OBJECT IDENTIFIER ::= { b155-622-card 15 }

--
--  B155/622 B1 Current Table
--
        bRS-SectionCurrTab  OBJECT-TYPE
            SYNTAX  SEQUENCE OF  BRS-SectionCurrEty
            ACCESS  not-accessible
            STATUS  mandatory
            DESCRIPTION
                "The B155/622 B1 Current table."
            ::= { b155-622PerfDisplayTab 1 }

        bRS-SectionCurrEty  OBJECT-TYPE
            SYNTAX  BRS-SectionCurrEty
            ACCESS  not-accessible
            STATUS  mandatory
            DESCRIPTION
                "An entry in the B155/622 B1 Current table."
            INDEX { bRsSecCurrUnit , bRsSecCurrPort }
            ::= { bRS-SectionCurrTab 1 }

        BRS-SectionCurrEty ::= SEQUENCE {
            bRsSecCurrUnit              UnitID,
            bRsSecCurrPort              PortID,
            bRsSecCurrEBs               Counter,
            bRsSecCurrBBEs              Counter,
            bRsSecCurrESs               Counter,
            bRsSecCurrBESs              Counter,
            bRsSecCurrSESs              Counter,
            bRsSecCurrUASs              Counter,
            bRsSecCurr24HValid15M       Counter,
            bRsSecCurr7DayValidDay      Counter,
            bRsSecCurr15MTimeElaps      Counter,
            bRsSecCurrDayValid15M       Counter
        }

        bRsSecCurrUnit  OBJECT-TYPE
            SYNTAX  UnitID
            ACCESS  read-only
            STATUS  mandatory
            DESCRIPTION
            "unit 1 to 4."
            ::= { bRS-SectionCurrEty 1 }

        bRsSecCurrPort  OBJECT-TYPE
            SYNTAX  PortID
            ACCESS  read-only
            STATUS  mandatory
            DESCRIPTION
                "PORT #1~#2"
            ::= { bRS-SectionCurrEty 2 }

        bRsSecCurrEBs  OBJECT-TYPE
            SYNTAX  Counter
            ACCESS  read-only
            STATUS  mandatory
            DESCRIPTION
                "B1(BIP-8) Error Block"
            ::= { bRS-SectionCurrEty 3 }

        bRsSecCurrBBEs  OBJECT-TYPE
            SYNTAX  Counter
            ACCESS  read-only
            STATUS  mandatory
            DESCRIPTION
                "B1(BIP-8) Background Block Error"
            ::= { bRS-SectionCurrEty 4 }

        bRsSecCurrESs  OBJECT-TYPE
            SYNTAX  Counter
            ACCESS  read-only
            STATUS  mandatory
            DESCRIPTION
                "B1(BIP-8) Error Second"
            ::= { bRS-SectionCurrEty 5 }

        bRsSecCurrBESs  OBJECT-TYPE
            SYNTAX  Counter
            ACCESS  read-only
            STATUS  mandatory
            DESCRIPTION
                "B1(BIP-8) Background Error Second"
            ::= { bRS-SectionCurrEty 6 }

        bRsSecCurrSESs  OBJECT-TYPE
            SYNTAX  Counter
            ACCESS  read-only
            STATUS  mandatory
            DESCRIPTION
                "B1(BIP-8) Severly Error Second"
            ::= { bRS-SectionCurrEty 7 }

        bRsSecCurrUASs  OBJECT-TYPE
            SYNTAX  Counter
            ACCESS  read-only
            STATUS  mandatory
            DESCRIPTION
                "B1(BIP-8) Unavailable Second"
            ::= { bRS-SectionCurrEty 8 }

        bRsSecCurr24HValid15M  OBJECT-TYPE
            SYNTAX  Counter
            ACCESS  read-only
            STATUS  mandatory
            DESCRIPTION
                "B1(BIP-8) Valid 15-Min Interval"
            ::= { bRS-SectionCurrEty 9 }

        bRsSecCurr7DayValidDay  OBJECT-TYPE
            SYNTAX  Counter
            ACCESS  read-only
            STATUS  mandatory
            DESCRIPTION
                "B1(BIP-8) Valid 1-Day Interval"
            ::= { bRS-SectionCurrEty 10 }

        bRsSecCurr15MTimeElaps  OBJECT-TYPE
            SYNTAX  Counter
            ACCESS  read-only
            STATUS  mandatory
            DESCRIPTION
                "B1(BIP-8) Current 15-MIN Time Elapsed"
            ::= { bRS-SectionCurrEty 11 }

        bRsSecCurrDayValid15M  OBJECT-TYPE
            SYNTAX  Counter
            ACCESS  read-only
            STATUS  mandatory
            DESCRIPTION
                "B1(BIP-8) Current Day Time Elapsed"
            ::= { bRS-SectionCurrEty 12 }

--
--  B155/622 B1 Interval Table
--
        bRS-SectionIntervTab  OBJECT-TYPE
            SYNTAX  SEQUENCE OF  BRS-SectionIntervEty
            ACCESS  not-accessible
            STATUS  mandatory
            DESCRIPTION
                "The B155/622 B1 Interval table."
            ::= { b155-622PerfDisplayTab 2 }

        bRS-SectionIntervEty  OBJECT-TYPE
            SYNTAX  BRS-SectionIntervEty
            ACCESS  not-accessible
            STATUS  mandatory
            DESCRIPTION
                "An entry in the B155/622 B1 Interval table."
            INDEX { bRsSecIntervUnit , bRsSecIntervPort ,
                    bRsSecIntervNumber }
            ::= { bRS-SectionIntervTab 1 }

        BRS-SectionIntervEty ::= SEQUENCE {
            bRsSecIntervUnit            UnitID,
            bRsSecIntervPort            PortID,
            bRsSecIntervNumber          INTEGER (1..96),
            bRsSecIntervEBs             Counter,
            bRsSecIntervBBEs            Counter,
            bRsSecIntervESs             Counter,
            bRsSecIntervBESs            Counter,
            bRsSecIntervSESs            Counter,
            bRsSecIntervUASs            Counter
        }

        bRsSecIntervUnit  OBJECT-TYPE
            SYNTAX  UnitID
            ACCESS  read-only
            STATUS  mandatory
            DESCRIPTION
            "unit 1 to 4."
            ::= { bRS-SectionIntervEty 1 }

        bRsSecIntervPort  OBJECT-TYPE
            SYNTAX  PortID
            ACCESS  read-only
            STATUS  mandatory
            DESCRIPTION
                "PORT #1~#2"
            ::= { bRS-SectionIntervEty 2 }

        bRsSecIntervNumber  OBJECT-TYPE
            SYNTAX  INTEGER (1..96)
            ACCESS  read-only
            STATUS  mandatory
            DESCRIPTION
                "A number between 1 and 96"
            ::= { bRS-SectionIntervEty 3 }

        bRsSecIntervEBs  OBJECT-TYPE
            SYNTAX  Counter
            ACCESS  read-only
            STATUS  mandatory
            DESCRIPTION
                "B1(BIP-8) Error Block"
            ::= { bRS-SectionIntervEty 4 }

        bRsSecIntervBBEs  OBJECT-TYPE
            SYNTAX  Counter
            ACCESS  read-only
            STATUS  mandatory
            DESCRIPTION
                "B1(BIP-8) Background Block Error"
            ::= { bRS-SectionIntervEty 5 }

        bRsSecIntervESs  OBJECT-TYPE
            SYNTAX  Counter
            ACCESS  read-only
            STATUS  mandatory
            DESCRIPTION
                "B1(BIP-8) Error Second"
            ::= { bRS-SectionIntervEty 6 }

        bRsSecIntervBESs  OBJECT-TYPE
            SYNTAX  Counter
            ACCESS  read-only
            STATUS  mandatory
            DESCRIPTION
                "B1(BIP-8) Background Error Second"
            ::= { bRS-SectionIntervEty 7 }

        bRsSecIntervSESs  OBJECT-TYPE
            SYNTAX  Counter
            ACCESS  read-only
            STATUS  mandatory
            DESCRIPTION
                "B1(BIP-8) Severly Error Second"
            ::= { bRS-SectionIntervEty 8 }

        bRsSecIntervUASs  OBJECT-TYPE
            SYNTAX  Counter
            ACCESS  read-only
            STATUS  mandatory
            DESCRIPTION
                "B1(BIP-8) Unavailable Second"
            ::= { bRS-SectionIntervEty 9 }

--
--  B155/622 B1 7 Days Table
--
        bRS-Section7DaysTab  OBJECT-TYPE
            SYNTAX  SEQUENCE OF  BRS-Section7DaysEty
            ACCESS  not-accessible
            STATUS  mandatory
            DESCRIPTION
                "The B155/622 B1 7 days table."
            ::= { b155-622PerfDisplayTab 3 }

        bRS-Section7DaysEty  OBJECT-TYPE
            SYNTAX  BRS-Section7DaysEty
            ACCESS  not-accessible
            STATUS  mandatory
            DESCRIPTION
                "An entry in the B155/622 B1 7 days table."
            INDEX { bRsSec7DaysUnit , bRsSec7DaysPort ,
                    bRsSec7DaysNumber }
            ::= { bRS-Section7DaysTab 1 }

        BRS-Section7DaysEty ::= SEQUENCE {
            bRsSec7DaysUnit             UnitID,
            bRsSec7DaysPort             PortID,
            bRsSec7DaysNumber           INTEGER (1..7),
            bRsSec7DaysDate             DisplayString (SIZE (0..255)),
            bRsSec7DaysEBs              Counter,
            bRsSec7DaysBBEs             Counter,
            bRsSec7DaysESs              Counter,
            bRsSec7DaysBESs             Counter,
            bRsSec7DaysSESs             Counter,
            bRsSec7DaysUASs             Counter
        }

        bRsSec7DaysUnit  OBJECT-TYPE
            SYNTAX  UnitID
            ACCESS  read-only
            STATUS  mandatory
            DESCRIPTION
            "unit 1 to 4."
            ::= { bRS-Section7DaysEty 1 }

        bRsSec7DaysPort  OBJECT-TYPE
            SYNTAX  PortID
            ACCESS  read-only
            STATUS  mandatory
            DESCRIPTION
                "PORT #1~#2"
            ::= { bRS-Section7DaysEty 2 }

        bRsSec7DaysNumber  OBJECT-TYPE
            SYNTAX  INTEGER (1..7)
            ACCESS  read-only
            STATUS  mandatory
            DESCRIPTION
                "A number between 1 and 7"
            ::= { bRS-Section7DaysEty 3 }

        bRsSec7DaysDate  OBJECT-TYPE
            SYNTAX  DisplayString (SIZE (0..255))
            ACCESS  read-only
            STATUS  mandatory
            DESCRIPTION
                "Date"
            ::= { bRS-Section7DaysEty 4 }

        bRsSec7DaysEBs  OBJECT-TYPE
            SYNTAX  Counter
            ACCESS  read-only
            STATUS  mandatory
            DESCRIPTION
                "B1(BIP-8) Error Block"
            ::= { bRS-Section7DaysEty 5 }

        bRsSec7DaysBBEs  OBJECT-TYPE
            SYNTAX  Counter
            ACCESS  read-only
            STATUS  mandatory
            DESCRIPTION
                "B1(BIP-8) Background Block Error"
            ::= { bRS-Section7DaysEty 6 }

        bRsSec7DaysESs  OBJECT-TYPE
            SYNTAX  Counter
            ACCESS  read-only
            STATUS  mandatory
            DESCRIPTION
                "B1(BIP-8) Error Second"
            ::= { bRS-Section7DaysEty 7 }

        bRsSec7DaysBESs  OBJECT-TYPE
            SYNTAX  Counter
            ACCESS  read-only
            STATUS  mandatory
            DESCRIPTION
                "B1(BIP-8) Background Error Second"
            ::= { bRS-Section7DaysEty 8 }

        bRsSec7DaysSESs  OBJECT-TYPE
            SYNTAX  Counter
            ACCESS  read-only
            STATUS  mandatory
            DESCRIPTION
                "B1(BIP-8) Severly Error Second"
            ::= { bRS-Section7DaysEty 9 }

        bRsSec7DaysUASs  OBJECT-TYPE
            SYNTAX  Counter
            ACCESS  read-only
            STATUS  mandatory
            DESCRIPTION
                "B1(BIP-8) Unavailable Second"
            ::= { bRS-Section7DaysEty 10 }

--
--  B155/622 B1 Total Table
--
        bRS-SectionTotalTab  OBJECT-TYPE
            SYNTAX  SEQUENCE OF  BRS-SectionTotalEty
            ACCESS  not-accessible
            STATUS  mandatory
            DESCRIPTION
                "The B155/622 B1 Total table."
            ::= { b155-622PerfDisplayTab 4 }

        bRS-SectionTotalEty  OBJECT-TYPE
            SYNTAX  BRS-SectionTotalEty
            ACCESS  not-accessible
            STATUS  mandatory
            DESCRIPTION
                "An entry in the B155/622 B1 Total table."
            INDEX { bRsSecTotalUnit , bRsSecTotalPort }
            ::= { bRS-SectionTotalTab 1 }

        BRS-SectionTotalEty ::= SEQUENCE {
            bRsSecTotalUnit             UnitID,
            bRsSecTotalPort             PortID,
            bRsSecTotalEBs              Counter,
            bRsSecTotalBBEs             Counter,
            bRsSecTotalESs              Counter,
            bRsSecTotalBESs             Counter,
            bRsSecTotalSESs             Counter,
            bRsSecTotalUASs             Counter
        }

        bRsSecTotalUnit  OBJECT-TYPE
            SYNTAX  UnitID
            ACCESS  read-only
            STATUS  mandatory
            DESCRIPTION
            "unit 1 to 4."
            ::= { bRS-SectionTotalEty 1 }

        bRsSecTotalPort  OBJECT-TYPE
            SYNTAX  PortID
            ACCESS  read-only
            STATUS  mandatory
            DESCRIPTION
                "PORT #1~#2"
            ::= { bRS-SectionTotalEty 2 }

        bRsSecTotalEBs  OBJECT-TYPE
            SYNTAX  Counter
            ACCESS  read-only
            STATUS  mandatory
            DESCRIPTION
                "B1(BIP-8) Error Block"
            ::= { bRS-SectionTotalEty 3 }

        bRsSecTotalBBEs  OBJECT-TYPE
            SYNTAX  Counter
            ACCESS  read-only
            STATUS  mandatory
            DESCRIPTION
                "B1(BIP-8) Background Block Error"
            ::= { bRS-SectionTotalEty 4 }

        bRsSecTotalESs  OBJECT-TYPE
            SYNTAX  Counter
            ACCESS  read-only
            STATUS  mandatory
            DESCRIPTION
                "B1(BIP-8) Error Second"
            ::= { bRS-SectionTotalEty 5 }

        bRsSecTotalBESs  OBJECT-TYPE
            SYNTAX  Counter
            ACCESS  read-only
            STATUS  mandatory
            DESCRIPTION
                "B1(BIP-8) Background Error Second"
            ::= { bRS-SectionTotalEty 6 }

        bRsSecTotalSESs  OBJECT-TYPE
            SYNTAX  Counter
            ACCESS  read-only
            STATUS  mandatory
            DESCRIPTION
                "B1(BIP-8) Severly Error Second"
            ::= { bRS-SectionTotalEty 7 }

        bRsSecTotalUASs  OBJECT-TYPE
            SYNTAX  Counter
            ACCESS  read-only
            STATUS  mandatory
            DESCRIPTION
                "B1(BIP-8) Unavailable Second"
            ::= { bRS-SectionTotalEty 8 }

--
--  B155/622 B2 Current Table
--
        bMS-LineCurrTab  OBJECT-TYPE
            SYNTAX  SEQUENCE OF  BMS-LineCurrEty
            ACCESS  not-accessible
            STATUS  mandatory
            DESCRIPTION
                "The B155/622 B2 Current table."
            ::= { b155-622PerfDisplayTab 5 }

        bMS-LineCurrEty  OBJECT-TYPE
            SYNTAX  BMS-LineCurrEty
            ACCESS  not-accessible
            STATUS  mandatory
            DESCRIPTION
                "An entry in the B155/622 B2 Current table."
            INDEX { bMsLnCurrUnit , bMsLnCurrPort }
            ::= { bMS-LineCurrTab 1 }

        BMS-LineCurrEty ::= SEQUENCE {
            bMsLnCurrUnit               UnitID,
            bMsLnCurrPort               PortID,
            bMsLnCurrEBs                Counter,
            bMsLnCurrBBEs               Counter,
            bMsLnCurrESs                Counter,
            bMsLnCurrBESs               Counter,
            bMsLnCurrSESs               Counter,
            bMsLnCurrUASs               Counter,
            bMsLnCurr24HValid15M        Counter,
            bMsLnCurr7DayValidDay       Counter,
            bMsLnCurr15MTimeElaps       Counter,
            bMsLnCurrDayValid15M        Counter
        }

        bMsLnCurrUnit  OBJECT-TYPE
            SYNTAX  UnitID
            ACCESS  read-only
            STATUS  mandatory
            DESCRIPTION
            "unit 1 to 4."
            ::= { bMS-LineCurrEty 1 }

        bMsLnCurrPort  OBJECT-TYPE
            SYNTAX  PortID
            ACCESS  read-only
            STATUS  mandatory
            DESCRIPTION
                "PORT #1~#2"
            ::= { bMS-LineCurrEty 2 }

        bMsLnCurrEBs  OBJECT-TYPE
            SYNTAX  Counter
            ACCESS  read-only
            STATUS  mandatory
            DESCRIPTION
                "B2(BIP-8) Error Block"
            ::= { bMS-LineCurrEty 3 }

        bMsLnCurrBBEs  OBJECT-TYPE
            SYNTAX  Counter
            ACCESS  read-only
            STATUS  mandatory
            DESCRIPTION
                "B2(BIP-8) Background Block Error"
            ::= { bMS-LineCurrEty 4 }

        bMsLnCurrESs  OBJECT-TYPE
            SYNTAX  Counter
            ACCESS  read-only
            STATUS  mandatory
            DESCRIPTION
                "B2(BIP-8) Error Second"
            ::= { bMS-LineCurrEty 5 }

        bMsLnCurrBESs  OBJECT-TYPE
            SYNTAX  Counter
            ACCESS  read-only
            STATUS  mandatory
            DESCRIPTION
                "B2(BIP-8) Background Error Second"
            ::= { bMS-LineCurrEty 6 }

        bMsLnCurrSESs  OBJECT-TYPE
            SYNTAX  Counter
            ACCESS  read-only
            STATUS  mandatory
            DESCRIPTION
                "B2(BIP-8) Severly Error Second"
            ::= { bMS-LineCurrEty 7 }

        bMsLnCurrUASs  OBJECT-TYPE
            SYNTAX  Counter
            ACCESS  read-only
            STATUS  mandatory
            DESCRIPTION
                "B2(BIP-8) Unavailable Second"
            ::= { bMS-LineCurrEty 8 }

        bMsLnCurr24HValid15M  OBJECT-TYPE
            SYNTAX  Counter
            ACCESS  read-only
            STATUS  mandatory
            DESCRIPTION
                "B1(BIP-8) Valid 15-Min Interval"
            ::= { bMS-LineCurrEty 9 }

        bMsLnCurr7DayValidDay  OBJECT-TYPE
            SYNTAX  Counter
            ACCESS  read-only
            STATUS  mandatory
            DESCRIPTION
                "B1(BIP-8) Valid 1-Day Interval"
            ::= { bMS-LineCurrEty 10 }

        bMsLnCurr15MTimeElaps  OBJECT-TYPE
            SYNTAX  Counter
            ACCESS  read-only
            STATUS  mandatory
            DESCRIPTION
                "B1(BIP-8) Current 15-MIN Time Elapsed"
            ::= { bMS-LineCurrEty 11 }

        bMsLnCurrDayValid15M  OBJECT-TYPE
            SYNTAX  Counter
            ACCESS  read-only
            STATUS  mandatory
            DESCRIPTION
                "B1(BIP-8) Current Day Time Elapsed"
            ::= { bMS-LineCurrEty 12 }

--
--  B155/622 B2 Interval Table
--
        bMS-LineIntervTab  OBJECT-TYPE
            SYNTAX  SEQUENCE OF  BMS-LineIntervEty
            ACCESS  not-accessible
            STATUS  mandatory
            DESCRIPTION
                "The B155/622 B2 Interval table."
            ::= { b155-622PerfDisplayTab 6 }

        bMS-LineIntervEty  OBJECT-TYPE
            SYNTAX  BMS-LineIntervEty
            ACCESS  not-accessible
            STATUS  mandatory
            DESCRIPTION
                "An entry in the B155/622 B2 Interval table."
            INDEX { bMsLnIntervUnit , bMsLnIntervPort ,
                    bMsLnIntervNumber }
            ::= { bMS-LineIntervTab 1 }

        BMS-LineIntervEty ::= SEQUENCE {
            bMsLnIntervUnit             UnitID,
            bMsLnIntervPort             PortID,
            bMsLnIntervNumber           INTEGER (1..96),
            bMsLnIntervEBs              Counter,
            bMsLnIntervBBEs             Counter,
            bMsLnIntervESs              Counter,
            bMsLnIntervBESs             Counter,
            bMsLnIntervSESs             Counter,
            bMsLnIntervUASs             Counter
        }

        bMsLnIntervUnit  OBJECT-TYPE
            SYNTAX  UnitID
            ACCESS  read-only
            STATUS  mandatory
            DESCRIPTION
            "unit 1 to 4."
            ::= { bMS-LineIntervEty 1 }

        bMsLnIntervPort  OBJECT-TYPE
            SYNTAX  PortID
            ACCESS  read-only
            STATUS  mandatory
            DESCRIPTION
                "PORT #1~#2"
            ::= { bMS-LineIntervEty 2 }

        bMsLnIntervNumber  OBJECT-TYPE
            SYNTAX  INTEGER (1..96)
            ACCESS  read-only
            STATUS  mandatory
            DESCRIPTION
                "A number between 1 and 96"
            ::= { bMS-LineIntervEty 3 }

        bMsLnIntervEBs  OBJECT-TYPE
            SYNTAX  Counter
            ACCESS  read-only
            STATUS  mandatory
            DESCRIPTION
                "B2(BIP-8) Error Block"
            ::= { bMS-LineIntervEty 4 }

        bMsLnIntervBBEs  OBJECT-TYPE
            SYNTAX  Counter
            ACCESS  read-only
            STATUS  mandatory
            DESCRIPTION
                "B2(BIP-8) Background Block Error"
            ::= { bMS-LineIntervEty 5 }

        bMsLnIntervESs  OBJECT-TYPE
            SYNTAX  Counter
            ACCESS  read-only
            STATUS  mandatory
            DESCRIPTION
                "B2(BIP-8) Error Second"
            ::= { bMS-LineIntervEty 6 }

        bMsLnIntervBESs  OBJECT-TYPE
            SYNTAX  Counter
            ACCESS  read-only
            STATUS  mandatory
            DESCRIPTION
                "B2(BIP-8) Background Error Second"
            ::= { bMS-LineIntervEty 7 }

        bMsLnIntervSESs  OBJECT-TYPE
            SYNTAX  Counter
            ACCESS  read-only
            STATUS  mandatory
            DESCRIPTION
                "B2(BIP-8) Severly Error Second"
            ::= { bMS-LineIntervEty 8 }

        bMsLnIntervUASs  OBJECT-TYPE
            SYNTAX  Counter
            ACCESS  read-only
            STATUS  mandatory
            DESCRIPTION
                "B2(BIP-8) Unavailable Second"
            ::= { bMS-LineIntervEty 9 }

--
--  B155/622 B2 7 Days Table
--
        bMS-Line7DaysTab  OBJECT-TYPE
            SYNTAX  SEQUENCE OF  BMS-Line7DaysEty
            ACCESS  not-accessible
            STATUS  mandatory
            DESCRIPTION
                "The B155/622 B2 7 days table."
            ::= { b155-622PerfDisplayTab 7 }

        bMS-Line7DaysEty  OBJECT-TYPE
            SYNTAX  BMS-Line7DaysEty
            ACCESS  not-accessible
            STATUS  mandatory
            DESCRIPTION
                "An entry in the B155/622 B2 7 days table."
            INDEX { bMsLn7DaysUnit , bMsLn7DaysPort ,
                    bMsLn7DaysNumber }
            ::= { bMS-Line7DaysTab 1 }

        BMS-Line7DaysEty ::= SEQUENCE {
            bMsLn7DaysUnit              UnitID,
            bMsLn7DaysPort              PortID,
            bMsLn7DaysNumber            INTEGER (1..7),
            bMsLn7DaysDate              DisplayString (SIZE (0..255)),
            bMsLn7DaysEBs               Counter,
            bMsLn7DaysBBEs              Counter,
            bMsLn7DaysESs               Counter,
            bMsLn7DaysBESs              Counter,
            bMsLn7DaysSESs              Counter,
            bMsLn7DaysUASs              Counter
        }

        bMsLn7DaysUnit  OBJECT-TYPE
            SYNTAX  UnitID
            ACCESS  read-only
            STATUS  mandatory
            DESCRIPTION
            "unit 1 to 4."
            ::= { bMS-Line7DaysEty 1 }

        bMsLn7DaysPort  OBJECT-TYPE
            SYNTAX  PortID
            ACCESS  read-only
            STATUS  mandatory
            DESCRIPTION
                "PORT #1~#2"
            ::= { bMS-Line7DaysEty 2 }

        bMsLn7DaysNumber  OBJECT-TYPE
            SYNTAX  INTEGER (1..7)
            ACCESS  read-only
            STATUS  mandatory
            DESCRIPTION
                "A number between 1 and 7"
            ::= { bMS-Line7DaysEty 3 }

        bMsLn7DaysDate  OBJECT-TYPE
            SYNTAX  DisplayString (SIZE (0..255))
            ACCESS  read-only
            STATUS  mandatory
            DESCRIPTION
                "Date"
            ::= { bMS-Line7DaysEty 4 }

        bMsLn7DaysEBs  OBJECT-TYPE
            SYNTAX  Counter
            ACCESS  read-only
            STATUS  mandatory
            DESCRIPTION
                "B2(BIP-8) Error Block"
            ::= { bMS-Line7DaysEty 5 }

        bMsLn7DaysBBEs  OBJECT-TYPE
            SYNTAX  Counter
            ACCESS  read-only
            STATUS  mandatory
            DESCRIPTION
                "B2(BIP-8) Background Block Error"
            ::= { bMS-Line7DaysEty 6 }

        bMsLn7DaysESs  OBJECT-TYPE
            SYNTAX  Counter
            ACCESS  read-only
            STATUS  mandatory
            DESCRIPTION
                "B2(BIP-8) Error Second"
            ::= { bMS-Line7DaysEty 7 }

        bMsLn7DaysBESs  OBJECT-TYPE
            SYNTAX  Counter
            ACCESS  read-only
            STATUS  mandatory
            DESCRIPTION
                "B2(BIP-8) Background Error Second"
            ::= { bMS-Line7DaysEty 8 }

        bMsLn7DaysSESs  OBJECT-TYPE
            SYNTAX  Counter
            ACCESS  read-only
            STATUS  mandatory
            DESCRIPTION
                "B2(BIP-8) Severly Error Second"
            ::= { bMS-Line7DaysEty 9 }

        bMsLn7DaysUASs  OBJECT-TYPE
            SYNTAX  Counter
            ACCESS  read-only
            STATUS  mandatory
            DESCRIPTION
                "B2(BIP-8) Unavailable Second"
            ::= { bMS-Line7DaysEty 10 }

--
--  B155/622 B2 Total Table
--
        bMS-LineTotalTab  OBJECT-TYPE
            SYNTAX  SEQUENCE OF  BMS-LineTotalEty
            ACCESS  not-accessible
            STATUS  mandatory
            DESCRIPTION
                "The B155/622 B2 Total table."
            ::= { b155-622PerfDisplayTab 8 }

        bMS-LineTotalEty  OBJECT-TYPE
            SYNTAX  BMS-LineTotalEty
            ACCESS  not-accessible
            STATUS  mandatory
            DESCRIPTION
                "An entry in the B155/622 B2 Total table."
            INDEX { bMsLnTotalUnit , bMsLnTotalPort }
            ::= { bMS-LineTotalTab 1 }

        BMS-LineTotalEty ::= SEQUENCE {
            bMsLnTotalUnit              UnitID,
            bMsLnTotalPort              PortID,
            bMsLnTotalEBs               Counter,
            bMsLnTotalBBEs              Counter,
            bMsLnTotalESs               Counter,
            bMsLnTotalBESs              Counter,
            bMsLnTotalSESs              Counter,
            bMsLnTotalUASs              Counter
        }

        bMsLnTotalUnit  OBJECT-TYPE
            SYNTAX  UnitID
            ACCESS  read-only
            STATUS  mandatory
            DESCRIPTION
            "unit 1 to 4."
            ::= { bMS-LineTotalEty 1 }

        bMsLnTotalPort  OBJECT-TYPE
            SYNTAX  PortID
            ACCESS  read-only
            STATUS  mandatory
            DESCRIPTION
                "PORT #1~#2"
            ::= { bMS-LineTotalEty 2 }

        bMsLnTotalEBs  OBJECT-TYPE
            SYNTAX  Counter
            ACCESS  read-only
            STATUS  mandatory
            DESCRIPTION
                "B2(BIP-8) Error Block"
            ::= { bMS-LineTotalEty 3 }

        bMsLnTotalBBEs  OBJECT-TYPE
            SYNTAX  Counter
            ACCESS  read-only
            STATUS  mandatory
            DESCRIPTION
                "B2(BIP-8) Background Block Error"
            ::= { bMS-LineTotalEty 4 }

        bMsLnTotalESs  OBJECT-TYPE
            SYNTAX  Counter
            ACCESS  read-only
            STATUS  mandatory
            DESCRIPTION
                "B2(BIP-8) Error Second"
            ::= { bMS-LineTotalEty 5 }

        bMsLnTotalBESs  OBJECT-TYPE
            SYNTAX  Counter
            ACCESS  read-only
            STATUS  mandatory
            DESCRIPTION
                "B2(BIP-8) Background Error Second"
            ::= { bMS-LineTotalEty 6 }

        bMsLnTotalSESs  OBJECT-TYPE
            SYNTAX  Counter
            ACCESS  read-only
            STATUS  mandatory
            DESCRIPTION
                "B2(BIP-8) Severly Error Second"
            ::= { bMS-LineTotalEty 7 }

        bMsLnTotalUASs  OBJECT-TYPE
            SYNTAX  Counter
            ACCESS  read-only
            STATUS  mandatory
            DESCRIPTION
                "B2(BIP-8) Unavailable Second"
            ::= { bMS-LineTotalEty 8 }

--
--  B155/622 MS-REI/REI-L Current Table
--
        bFarEndMS-LineCurrTab  OBJECT-TYPE
            SYNTAX  SEQUENCE OF  BFarEndMS-LineCurrEty
            ACCESS  not-accessible
            STATUS  mandatory
            DESCRIPTION
                "The B155/622 MS-REI/REI-L Current table."
            ::= { b155-622PerfDisplayTab 9 }

        bFarEndMS-LineCurrEty  OBJECT-TYPE
            SYNTAX  BFarEndMS-LineCurrEty
            ACCESS  not-accessible
            STATUS  mandatory
            DESCRIPTION
                "An entry in the B155/622 MS-REI/REI-L Current table."
            INDEX { bFrMsLnCurrUnit , bFrMsLnCurrPort }
            ::= { bFarEndMS-LineCurrTab 1 }

        BFarEndMS-LineCurrEty ::= SEQUENCE {
            bFrMsLnCurrUnit             UnitID,
            bFrMsLnCurrPort             PortID,
            bFrMsLnCurrEBs              Counter,
            bFrMsLnCurrBBEs             Counter,
            bFrMsLnCurrESs              Counter,
            bFrMsLnCurrBESs             Counter,
            bFrMsLnCurrSESs             Counter,
            bFrMsLnCurrUASs             Counter,
            bFrMsLnCurr24HValid15M      Counter,
            bFrMsLnCurr7DayValidDay     Counter,
            bFrMsLnCurr15MTimeElaps     Counter,
            bFrMsLnCurrDayValid15M      Counter
        }

        bFrMsLnCurrUnit  OBJECT-TYPE
            SYNTAX  UnitID
            ACCESS  read-only
            STATUS  mandatory
            DESCRIPTION
            "unit 1 to 4."
            ::= { bFarEndMS-LineCurrEty 1 }

        bFrMsLnCurrPort  OBJECT-TYPE
            SYNTAX  PortID
            ACCESS  read-only
            STATUS  mandatory
            DESCRIPTION
                "PORT #1~#2"
            ::= { bFarEndMS-LineCurrEty 2 }

        bFrMsLnCurrEBs  OBJECT-TYPE
            SYNTAX  Counter
            ACCESS  read-only
            STATUS  mandatory
            DESCRIPTION
                "MS-REI/REI-L Error Block"
            ::= { bFarEndMS-LineCurrEty 3 }

        bFrMsLnCurrBBEs  OBJECT-TYPE
            SYNTAX  Counter
            ACCESS  read-only
            STATUS  mandatory
            DESCRIPTION
                "MS-REI/REI-L Background Block Error"
            ::= { bFarEndMS-LineCurrEty 4 }

        bFrMsLnCurrESs  OBJECT-TYPE
            SYNTAX  Counter
            ACCESS  read-only
            STATUS  mandatory
            DESCRIPTION
                "MS-REI/REI-L Error Second"
            ::= { bFarEndMS-LineCurrEty 5 }

        bFrMsLnCurrBESs  OBJECT-TYPE
            SYNTAX  Counter
            ACCESS  read-only
            STATUS  mandatory
            DESCRIPTION
                "MS-REI/REI-L Background Error Second"
            ::= { bFarEndMS-LineCurrEty 6 }

        bFrMsLnCurrSESs  OBJECT-TYPE
            SYNTAX  Counter
            ACCESS  read-only
            STATUS  mandatory
            DESCRIPTION
                "MS-REI/REI-L Severly Error Second"
            ::= { bFarEndMS-LineCurrEty 7 }

        bFrMsLnCurrUASs  OBJECT-TYPE
            SYNTAX  Counter
            ACCESS  read-only
            STATUS  mandatory
            DESCRIPTION
                "MS-REI/REI-L Unavailable Second"
            ::= { bFarEndMS-LineCurrEty 8 }

        bFrMsLnCurr24HValid15M  OBJECT-TYPE
            SYNTAX  Counter
            ACCESS  read-only
            STATUS  mandatory
            DESCRIPTION
                "B1(BIP-8) Valid 15-Min Interval"
            ::= { bFarEndMS-LineCurrEty 9 }

        bFrMsLnCurr7DayValidDay  OBJECT-TYPE
            SYNTAX  Counter
            ACCESS  read-only
            STATUS  mandatory
            DESCRIPTION
                "B1(BIP-8) Valid 1-Day Interval"
            ::= { bFarEndMS-LineCurrEty 10 }

        bFrMsLnCurr15MTimeElaps  OBJECT-TYPE
            SYNTAX  Counter
            ACCESS  read-only
            STATUS  mandatory
            DESCRIPTION
                "B1(BIP-8) Current 15-MIN Time Elapsed"
            ::= { bFarEndMS-LineCurrEty 11 }

        bFrMsLnCurrDayValid15M  OBJECT-TYPE
            SYNTAX  Counter
            ACCESS  read-only
            STATUS  mandatory
            DESCRIPTION
                "B1(BIP-8) Current Day Time Elapsed"
            ::= { bFarEndMS-LineCurrEty 12 }

--
--  B155/622 MS-REI/REI-L Interval Table
--
        bFarEndMS-LineIntervTab  OBJECT-TYPE
            SYNTAX  SEQUENCE OF  BFarEndMS-LineIntervEty
            ACCESS  not-accessible
            STATUS  mandatory
            DESCRIPTION
                "The B155/622 MS-REI/REI-L Interval table."
            ::= { b155-622PerfDisplayTab 10 }

        bFarEndMS-LineIntervEty  OBJECT-TYPE
            SYNTAX  BFarEndMS-LineIntervEty
            ACCESS  not-accessible
            STATUS  mandatory
            DESCRIPTION
                "An entry in the B155/622 MS-REI/REI-L Interval table."
            INDEX { bFrMsLnIntervUnit , bFrMsLnIntervPort ,
                    bFrMsLnIntervNumber }
            ::= { bFarEndMS-LineIntervTab 1 }

        BFarEndMS-LineIntervEty ::= SEQUENCE {
            bFrMsLnIntervUnit           UnitID,
            bFrMsLnIntervPort           PortID,
            bFrMsLnIntervNumber         INTEGER (1..96),
            bFrMsLnIntervEBs            Counter,
            bFrMsLnIntervBBEs           Counter,
            bFrMsLnIntervESs            Counter,
            bFrMsLnIntervBESs           Counter,
            bFrMsLnIntervSESs           Counter,
            bFrMsLnIntervUASs           Counter
        }

        bFrMsLnIntervUnit  OBJECT-TYPE
            SYNTAX  UnitID
            ACCESS  read-only
            STATUS  mandatory
            DESCRIPTION
            "unit 1 to 4."
            ::= { bFarEndMS-LineIntervEty 1 }

        bFrMsLnIntervPort  OBJECT-TYPE
            SYNTAX  PortID
            ACCESS  read-only
            STATUS  mandatory
            DESCRIPTION
                "PORT #1~#2"
            ::= { bFarEndMS-LineIntervEty 2 }

        bFrMsLnIntervNumber  OBJECT-TYPE
            SYNTAX  INTEGER (1..96)
            ACCESS  read-only
            STATUS  mandatory
            DESCRIPTION
                "A number between 1 and 96"
            ::= { bFarEndMS-LineIntervEty 3 }

        bFrMsLnIntervEBs  OBJECT-TYPE
            SYNTAX  Counter
            ACCESS  read-only
            STATUS  mandatory
            DESCRIPTION
                "MS-REI/REI-L Error Block"
            ::= { bFarEndMS-LineIntervEty 4 }

        bFrMsLnIntervBBEs  OBJECT-TYPE
            SYNTAX  Counter
            ACCESS  read-only
            STATUS  mandatory
            DESCRIPTION
                "MS-REI/REI-L Background Block Error"
            ::= { bFarEndMS-LineIntervEty 5 }

        bFrMsLnIntervESs  OBJECT-TYPE
            SYNTAX  Counter
            ACCESS  read-only
            STATUS  mandatory
            DESCRIPTION
                "MS-REI/REI-L Error Second"
            ::= { bFarEndMS-LineIntervEty 6 }

        bFrMsLnIntervBESs  OBJECT-TYPE
            SYNTAX  Counter
            ACCESS  read-only
            STATUS  mandatory
            DESCRIPTION
                "MS-REI/REI-L Background Error Second"
            ::= { bFarEndMS-LineIntervEty 7 }

        bFrMsLnIntervSESs  OBJECT-TYPE
            SYNTAX  Counter
            ACCESS  read-only
            STATUS  mandatory
            DESCRIPTION
                "MS-REI/REI-L Severly Error Second"
            ::= { bFarEndMS-LineIntervEty 8 }

        bFrMsLnIntervUASs  OBJECT-TYPE
            SYNTAX  Counter
            ACCESS  read-only
            STATUS  mandatory
            DESCRIPTION
                "MS-REI/REI-L Unavailable Second"
            ::= { bFarEndMS-LineIntervEty 9 }

--
--  B155/622 MS-REI/REI-L 7 Days Table
--
        bFarEndMS-Line7DaysTab  OBJECT-TYPE
            SYNTAX  SEQUENCE OF  BFarEndMS-Line7DaysEty
            ACCESS  not-accessible
            STATUS  mandatory
            DESCRIPTION
                "The B155/622 MS-REI/REI-L 7 days table."
            ::= { b155-622PerfDisplayTab 11 }

        bFarEndMS-Line7DaysEty  OBJECT-TYPE
            SYNTAX  BFarEndMS-Line7DaysEty
            ACCESS  not-accessible
            STATUS  mandatory
            DESCRIPTION
                "An entry in the B155/622 MS-REI/REI-L 7 days table."
            INDEX { bFrMsLn7DaysUnit , bFrMsLn7DaysPort ,
                    bFrMsLn7DaysNumber }
            ::= { bFarEndMS-Line7DaysTab 1 }

        BFarEndMS-Line7DaysEty ::= SEQUENCE {
            bFrMsLn7DaysUnit            UnitID,
            bFrMsLn7DaysPort            PortID,
            bFrMsLn7DaysNumber          INTEGER (1..7),
            bFrMsLn7DaysDate            DisplayString (SIZE (0..255)),
            bFrMsLn7DaysEBs             Counter,
            bFrMsLn7DaysBBEs            Counter,
            bFrMsLn7DaysESs             Counter,
            bFrMsLn7DaysBESs            Counter,
            bFrMsLn7DaysSESs            Counter,
            bFrMsLn7DaysUASs            Counter
        }

        bFrMsLn7DaysUnit  OBJECT-TYPE
            SYNTAX  UnitID
            ACCESS  read-only
            STATUS  mandatory
            DESCRIPTION
            "unit 1 to 4."
            ::= { bFarEndMS-Line7DaysEty 1 }

        bFrMsLn7DaysPort  OBJECT-TYPE
            SYNTAX  PortID
            ACCESS  read-only
            STATUS  mandatory
            DESCRIPTION
                "PORT #1~#2"
            ::= { bFarEndMS-Line7DaysEty 2 }

        bFrMsLn7DaysNumber  OBJECT-TYPE
            SYNTAX  INTEGER (1..7)
            ACCESS  read-only
            STATUS  mandatory
            DESCRIPTION
                "A number between 1 and 7"
            ::= { bFarEndMS-Line7DaysEty 3 }

        bFrMsLn7DaysDate  OBJECT-TYPE
            SYNTAX  DisplayString (SIZE (0..255))
            ACCESS  read-only
            STATUS  mandatory
            DESCRIPTION
                "Date"
            ::= { bFarEndMS-Line7DaysEty 4 }

        bFrMsLn7DaysEBs  OBJECT-TYPE
            SYNTAX  Counter
            ACCESS  read-only
            STATUS  mandatory
            DESCRIPTION
                "MS-REI/REI-L Error Block"
            ::= { bFarEndMS-Line7DaysEty 5 }

        bFrMsLn7DaysBBEs  OBJECT-TYPE
            SYNTAX  Counter
            ACCESS  read-only
            STATUS  mandatory
            DESCRIPTION
                "MS-REI/REI-L Background Block Error"
            ::= { bFarEndMS-Line7DaysEty 6 }

        bFrMsLn7DaysESs  OBJECT-TYPE
            SYNTAX  Counter
            ACCESS  read-only
            STATUS  mandatory
            DESCRIPTION
                "MS-REI/REI-L Error Second"
            ::= { bFarEndMS-Line7DaysEty 7 }

        bFrMsLn7DaysBESs  OBJECT-TYPE
            SYNTAX  Counter
            ACCESS  read-only
            STATUS  mandatory
            DESCRIPTION
                "MS-REI/REI-L Background Error Second"
            ::= { bFarEndMS-Line7DaysEty 8 }

        bFrMsLn7DaysSESs  OBJECT-TYPE
            SYNTAX  Counter
            ACCESS  read-only
            STATUS  mandatory
            DESCRIPTION
                "MS-REI/REI-L Severly Error Second"
            ::= { bFarEndMS-Line7DaysEty 9 }

        bFrMsLn7DaysUASs  OBJECT-TYPE
            SYNTAX  Counter
            ACCESS  read-only
            STATUS  mandatory
            DESCRIPTION
                "MS-REI/REI-L Unavailable Second"
            ::= { bFarEndMS-Line7DaysEty 10 }

--
--  B155/622 MS-REI/REI-L Total Table
--
        bFarEndMS-LineTotalTab  OBJECT-TYPE
            SYNTAX  SEQUENCE OF  BFarEndMS-LineTotalEty
            ACCESS  not-accessible
            STATUS  mandatory
            DESCRIPTION
                "The B155/622 MS-REI/REI-L Total table."
            ::= { b155-622PerfDisplayTab 12 }

        bFarEndMS-LineTotalEty  OBJECT-TYPE
            SYNTAX  BFarEndMS-LineTotalEty
            ACCESS  not-accessible
            STATUS  mandatory
            DESCRIPTION
                "An entry in the B155/622 MS-REI/REI-L Total table."
            INDEX { bFrMsLnTotalUnit , bFrMsLnTotalPort }
            ::= { bFarEndMS-LineTotalTab 1 }

        BFarEndMS-LineTotalEty ::= SEQUENCE {
            bFrMsLnTotalUnit            UnitID,
            bFrMsLnTotalPort            PortID,
            bFrMsLnTotalEBs             Counter,
            bFrMsLnTotalBBEs            Counter,
            bFrMsLnTotalESs             Counter,
            bFrMsLnTotalBESs            Counter,
            bFrMsLnTotalSESs            Counter,
            bFrMsLnTotalUASs            Counter
        }

        bFrMsLnTotalUnit  OBJECT-TYPE
            SYNTAX  UnitID
            ACCESS  read-only
            STATUS  mandatory
            DESCRIPTION
            "unit 1 to 4."
            ::= { bFarEndMS-LineTotalEty 1 }

        bFrMsLnTotalPort  OBJECT-TYPE
            SYNTAX  PortID
            ACCESS  read-only
            STATUS  mandatory
            DESCRIPTION
                "PORT #1~#2"
            ::= { bFarEndMS-LineTotalEty 2 }

        bFrMsLnTotalEBs  OBJECT-TYPE
            SYNTAX  Counter
            ACCESS  read-only
            STATUS  mandatory
            DESCRIPTION
                "MS-REI/REI-L Error Block"
            ::= { bFarEndMS-LineTotalEty 3 }

        bFrMsLnTotalBBEs  OBJECT-TYPE
            SYNTAX  Counter
            ACCESS  read-only
            STATUS  mandatory
            DESCRIPTION
                "MS-REI/REI-L Background Block Error"
            ::= { bFarEndMS-LineTotalEty 4 }

        bFrMsLnTotalESs  OBJECT-TYPE
            SYNTAX  Counter
            ACCESS  read-only
            STATUS  mandatory
            DESCRIPTION
                "MS-REI/REI-L Error Second"
            ::= { bFarEndMS-LineTotalEty 5 }

        bFrMsLnTotalBESs  OBJECT-TYPE
            SYNTAX  Counter
            ACCESS  read-only
            STATUS  mandatory
            DESCRIPTION
                "MS-REI/REI-L Background Error Second"
            ::= { bFarEndMS-LineTotalEty 6 }

        bFrMsLnTotalSESs  OBJECT-TYPE
            SYNTAX  Counter
            ACCESS  read-only
            STATUS  mandatory
            DESCRIPTION
                "MS-REI/REI-L Severly Error Second"
            ::= { bFarEndMS-LineTotalEty 7 }

        bFrMsLnTotalUASs  OBJECT-TYPE
            SYNTAX  Counter
            ACCESS  read-only
            STATUS  mandatory
            DESCRIPTION
                "MS-REI/REI-L Unavailable Second"
            ::= { bFarEndMS-LineTotalEty 8 }

--
--  B155/622 B3 Current Table
--
        bHP-STSCurrTab  OBJECT-TYPE
            SYNTAX  SEQUENCE OF  BHP-STSCurrEty
            ACCESS  not-accessible
            STATUS  mandatory
            DESCRIPTION
                "The B155/622 B3 Current table."
            ::= { b155-622PerfDisplayTab 13 }

        bHP-STSCurrEty  OBJECT-TYPE
            SYNTAX  BHP-STSCurrEty
            ACCESS  not-accessible
            STATUS  mandatory
            DESCRIPTION
                "An entry in the B155/622 B3 Current table."
            INDEX { bHpStsCurrUnit , bHpStsCurrPort ,
                    bHpStsCurrAug1Sts3 , bHpStsCurrVc3Sts1 }
            ::= { bHP-STSCurrTab 1 }

        BHP-STSCurrEty ::= SEQUENCE {
            bHpStsCurrUnit              UnitID,
            bHpStsCurrPort              PortID,
            bHpStsCurrAug1Sts3          Aug1Sts3Num,
            bHpStsCurrVc3Sts1           Vc3Sts1Num,
            bHpStsCurrEBs               Counter,
            bHpStsCurrBBEs              Counter,
            bHpStsCurrESs               Counter,
            bHpStsCurrBESs              Counter,
            bHpStsCurrSESs              Counter,
            bHpStsCurrUASs              Counter,
            bHpStsCurr24HValid15M       Counter,
            bHpStsCurr7DayValidDay      Counter,
            bHpStsCurr15MTimeElaps      Counter,
            bHpStsCurrDayValid15M       Counter
        }

        bHpStsCurrUnit  OBJECT-TYPE
            SYNTAX  UnitID
            ACCESS  read-only
            STATUS  mandatory
            DESCRIPTION
            "unit 1 to 4."
            ::= { bHP-STSCurrEty 1 }

        bHpStsCurrPort  OBJECT-TYPE
            SYNTAX  PortID
            ACCESS  read-only
            STATUS  mandatory
            DESCRIPTION
                "PORT #1~#2"
            ::= { bHP-STSCurrEty 2 }

        bHpStsCurrAug1Sts3  OBJECT-TYPE
            SYNTAX  Aug1Sts3Num
            ACCESS  read-only
            STATUS  mandatory
            DESCRIPTION
                "AUG1/STS3 index"
            ::= { bHP-STSCurrEty 3 }

        bHpStsCurrVc3Sts1  OBJECT-TYPE
            SYNTAX  Vc3Sts1Num
            ACCESS  read-only
            STATUS  mandatory
            DESCRIPTION
                "VC3/STS1 index"
            ::= { bHP-STSCurrEty 4 }

        bHpStsCurrEBs  OBJECT-TYPE
            SYNTAX  Counter
            ACCESS  read-only
            STATUS  mandatory
            DESCRIPTION
                "B3(BIP-8) Error Block"
            ::= { bHP-STSCurrEty 5 }

        bHpStsCurrBBEs  OBJECT-TYPE
            SYNTAX  Counter
            ACCESS  read-only
            STATUS  mandatory
            DESCRIPTION
                "B3(BIP-8) Background Block Error"
            ::= { bHP-STSCurrEty 6 }

        bHpStsCurrESs  OBJECT-TYPE
            SYNTAX  Counter
            ACCESS  read-only
            STATUS  mandatory
            DESCRIPTION
                "B3(BIP-8) Error Second"
            ::= { bHP-STSCurrEty 7 }

        bHpStsCurrBESs  OBJECT-TYPE
            SYNTAX  Counter
            ACCESS  read-only
            STATUS  mandatory
            DESCRIPTION
                "B3(BIP-8) Background Error Second"
            ::= { bHP-STSCurrEty 8 }

        bHpStsCurrSESs  OBJECT-TYPE
            SYNTAX  Counter
            ACCESS  read-only
            STATUS  mandatory
            DESCRIPTION
                "B3(BIP-8) Severly Error Second"
            ::= { bHP-STSCurrEty 9 }

        bHpStsCurrUASs  OBJECT-TYPE
            SYNTAX  Counter
            ACCESS  read-only
            STATUS  mandatory
            DESCRIPTION
                "B3(BIP-8) Unavailable Second"
            ::= { bHP-STSCurrEty 10 }

        bHpStsCurr24HValid15M  OBJECT-TYPE
            SYNTAX  Counter
            ACCESS  read-only
            STATUS  mandatory
            DESCRIPTION
                "B3(BIP-8) Valid 15-Min Interval"
            ::= { bHP-STSCurrEty 11 }

        bHpStsCurr7DayValidDay  OBJECT-TYPE
            SYNTAX  Counter
            ACCESS  read-only
            STATUS  mandatory
            DESCRIPTION
                "B3(BIP-8) Valid 1-Day Interval"
            ::= { bHP-STSCurrEty 12 }

        bHpStsCurr15MTimeElaps  OBJECT-TYPE
            SYNTAX  Counter
            ACCESS  read-only
            STATUS  mandatory
            DESCRIPTION
                "B3(BIP-8) Current 15-MIN Time Elapsed"
            ::= { bHP-STSCurrEty 13 }

        bHpStsCurrDayValid15M  OBJECT-TYPE
            SYNTAX  Counter
            ACCESS  read-only
            STATUS  mandatory
            DESCRIPTION
                "B3(BIP-8) Current Day Time Elapsed"
            ::= { bHP-STSCurrEty 14 }

--
--  B155/622 B3 Interval Table
--
        bHP-STSIntervTab  OBJECT-TYPE
            SYNTAX  SEQUENCE OF  BHP-STSIntervEty
            ACCESS  not-accessible
            STATUS  mandatory
            DESCRIPTION
                "The B155/622 B3 Interval table."
            ::= { b155-622PerfDisplayTab 14 }

        bHP-STSIntervEty  OBJECT-TYPE
            SYNTAX  BHP-STSIntervEty
            ACCESS  not-accessible
            STATUS  mandatory
            DESCRIPTION
                "An entry in the B155/622 B3 Interval table."
            INDEX { bHpStsIntervUnit , bHpStsIntervPort ,
                    bHpStsIntervAug1Sts3 , bHpStsIntervVc3Sts1 ,
                    bHpStsIntervNumber }
            ::= { bHP-STSIntervTab 1 }

        BHP-STSIntervEty ::= SEQUENCE {
            bHpStsIntervUnit            UnitID,
            bHpStsIntervPort            PortID,
            bHpStsIntervAug1Sts3        Aug1Sts3Num,
            bHpStsIntervVc3Sts1         Vc3Sts1Num,
            bHpStsIntervNumber          INTEGER (1..96),
            bHpStsIntervEBs             Counter,
            bHpStsIntervBBEs            Counter,
            bHpStsIntervESs             Counter,
            bHpStsIntervBESs            Counter,
            bHpStsIntervSESs            Counter,
            bHpStsIntervUASs            Counter
        }

        bHpStsIntervUnit  OBJECT-TYPE
            SYNTAX  UnitID
            ACCESS  read-only
            STATUS  mandatory
            DESCRIPTION
            "unit 1 to 4."
            ::= { bHP-STSIntervEty 1 }

        bHpStsIntervPort  OBJECT-TYPE
            SYNTAX  PortID
            ACCESS  read-only
            STATUS  mandatory
            DESCRIPTION
                "PORT #1~#2"
            ::= { bHP-STSIntervEty 2 }

        bHpStsIntervAug1Sts3  OBJECT-TYPE
            SYNTAX  Aug1Sts3Num
            ACCESS  read-only
            STATUS  mandatory
            DESCRIPTION
                "AUG1/STS3 index"
            ::= { bHP-STSIntervEty 3 }

        bHpStsIntervVc3Sts1  OBJECT-TYPE
            SYNTAX  Vc3Sts1Num
            ACCESS  read-only
            STATUS  mandatory
            DESCRIPTION
                "VC3/STS1 index"
            ::= { bHP-STSIntervEty 4 }

        bHpStsIntervNumber  OBJECT-TYPE
            SYNTAX  INTEGER (1..96)
            ACCESS  read-only
            STATUS  mandatory
            DESCRIPTION
                "A number between 1 and 96"
            ::= { bHP-STSIntervEty 5 }

        bHpStsIntervEBs  OBJECT-TYPE
            SYNTAX  Counter
            ACCESS  read-only
            STATUS  mandatory
            DESCRIPTION
                "B3(BIP-8) Error Block"
            ::= { bHP-STSIntervEty 6 }

        bHpStsIntervBBEs  OBJECT-TYPE
            SYNTAX  Counter
            ACCESS  read-only
            STATUS  mandatory
            DESCRIPTION
                "B3(BIP-8) Background Block Error"
            ::= { bHP-STSIntervEty 7 }

        bHpStsIntervESs  OBJECT-TYPE
            SYNTAX  Counter
            ACCESS  read-only
            STATUS  mandatory
            DESCRIPTION
                "B3(BIP-8) Error Second"
            ::= { bHP-STSIntervEty 8 }

        bHpStsIntervBESs  OBJECT-TYPE
            SYNTAX  Counter
            ACCESS  read-only
            STATUS  mandatory
            DESCRIPTION
                "B3(BIP-8) Background Error Second"
            ::= { bHP-STSIntervEty 9 }

        bHpStsIntervSESs  OBJECT-TYPE
            SYNTAX  Counter
            ACCESS  read-only
            STATUS  mandatory
            DESCRIPTION
                "B3(BIP-8) Severly Error Second"
            ::= { bHP-STSIntervEty 10 }

        bHpStsIntervUASs  OBJECT-TYPE
            SYNTAX  Counter
            ACCESS  read-only
            STATUS  mandatory
            DESCRIPTION
                "B3(BIP-8) Unavailable Second"
            ::= { bHP-STSIntervEty 11 }

--
--  B155/622 B3 7 Days Table
--
        bHP-STS7DaysTab  OBJECT-TYPE
            SYNTAX  SEQUENCE OF  BHP-STS7DaysEty
            ACCESS  not-accessible
            STATUS  mandatory
            DESCRIPTION
                "The B155/622 B3 7 days table."
            ::= { b155-622PerfDisplayTab 15 }

        bHP-STS7DaysEty  OBJECT-TYPE
            SYNTAX  BHP-STS7DaysEty
            ACCESS  not-accessible
            STATUS  mandatory
            DESCRIPTION
                "An entry in the B155/622 B3 7 days table."
            INDEX { bHpSts7DaysUnit , bHpSts7DaysPort ,
                    bHpSts7DaysAug1Sts3 , bHpSts7DaysVc3Sts1 ,
                    bHpSts7DaysNumber }
            ::= { bHP-STS7DaysTab 1 }

        BHP-STS7DaysEty ::= SEQUENCE {
            bHpSts7DaysUnit             UnitID,
            bHpSts7DaysPort             PortID,
            bHpSts7DaysAug1Sts3         Aug1Sts3Num,
            bHpSts7DaysVc3Sts1          Vc3Sts1Num,
            bHpSts7DaysNumber           INTEGER (1..7),
            bHpSts7DaysDate             DisplayString (SIZE (0..255)),
            bHpSts7DaysEBs              Counter,
            bHpSts7DaysBBEs             Counter,
            bHpSts7DaysESs              Counter,
            bHpSts7DaysBESs             Counter,
            bHpSts7DaysSESs             Counter,
            bHpSts7DaysUASs             Counter
        }

        bHpSts7DaysUnit  OBJECT-TYPE
            SYNTAX  UnitID
            ACCESS  read-only
            STATUS  mandatory
            DESCRIPTION
            "unit 1 to 4."
            ::= { bHP-STS7DaysEty 1 }

        bHpSts7DaysPort  OBJECT-TYPE
            SYNTAX  PortID
            ACCESS  read-only
            STATUS  mandatory
            DESCRIPTION
                "PORT #1~#2"
            ::= { bHP-STS7DaysEty 2 }

        bHpSts7DaysAug1Sts3  OBJECT-TYPE
            SYNTAX  Aug1Sts3Num
            ACCESS  read-only
            STATUS  mandatory
            DESCRIPTION
                "AUG1/STS3 index"
            ::= { bHP-STS7DaysEty 3 }

        bHpSts7DaysVc3Sts1  OBJECT-TYPE
            SYNTAX  Vc3Sts1Num
            ACCESS  read-only
            STATUS  mandatory
            DESCRIPTION
                "VC3/STS1 index"
            ::= { bHP-STS7DaysEty 4 }

        bHpSts7DaysNumber  OBJECT-TYPE
            SYNTAX  INTEGER (1..7)
            ACCESS  read-only
            STATUS  mandatory
            DESCRIPTION
                "A number between 1 and 7"
            ::= { bHP-STS7DaysEty 5 }

        bHpSts7DaysDate  OBJECT-TYPE
            SYNTAX  DisplayString (SIZE (0..255))
            ACCESS  read-only
            STATUS  mandatory
            DESCRIPTION
                "Date"
            ::= { bHP-STS7DaysEty 6 }

        bHpSts7DaysEBs  OBJECT-TYPE
            SYNTAX  Counter
            ACCESS  read-only
            STATUS  mandatory
            DESCRIPTION
                "B3(BIP-8) Error Block"
            ::= { bHP-STS7DaysEty 7 }

        bHpSts7DaysBBEs  OBJECT-TYPE
            SYNTAX  Counter
            ACCESS  read-only
            STATUS  mandatory
            DESCRIPTION
                "B3(BIP-8) Background Block Error"
            ::= { bHP-STS7DaysEty 8 }

        bHpSts7DaysESs  OBJECT-TYPE
            SYNTAX  Counter
            ACCESS  read-only
            STATUS  mandatory
            DESCRIPTION
                "B3(BIP-8) Error Second"
            ::= { bHP-STS7DaysEty 9 }

        bHpSts7DaysBESs  OBJECT-TYPE
            SYNTAX  Counter
            ACCESS  read-only
            STATUS  mandatory
            DESCRIPTION
                "B3(BIP-8) Background Error Second"
            ::= { bHP-STS7DaysEty 10 }

        bHpSts7DaysSESs  OBJECT-TYPE
            SYNTAX  Counter
            ACCESS  read-only
            STATUS  mandatory
            DESCRIPTION
                "B3(BIP-8) Severly Error Second"
            ::= { bHP-STS7DaysEty 11 }

        bHpSts7DaysUASs  OBJECT-TYPE
            SYNTAX  Counter
            ACCESS  read-only
            STATUS  mandatory
            DESCRIPTION
                "B3(BIP-8) Unavailable Second"
            ::= { bHP-STS7DaysEty 12 }

--
--  B155/622 B3 Total Table
--
        bHP-STSTotalTab  OBJECT-TYPE
            SYNTAX  SEQUENCE OF  BHP-STSTotalEty
            ACCESS  not-accessible
            STATUS  mandatory
            DESCRIPTION
                "The B155/622 B3 Total table."
            ::= { b155-622PerfDisplayTab 16 }

        bHP-STSTotalEty  OBJECT-TYPE
            SYNTAX  BHP-STSTotalEty
            ACCESS  not-accessible
            STATUS  mandatory
            DESCRIPTION
                "An entry in the B155/622 B3 Total table."
            INDEX { bHpStsTotalUnit , bHpStsTotalPort ,
                    bHpStsTotalAug1Sts3 , bHpStsTotalVc3Sts1 }
            ::= { bHP-STSTotalTab 1 }

        BHP-STSTotalEty ::= SEQUENCE {
            bHpStsTotalUnit             UnitID,
            bHpStsTotalPort             PortID,
            bHpStsTotalAug1Sts3         Aug1Sts3Num,
            bHpStsTotalVc3Sts1          Vc3Sts1Num,
            bHpStsTotalEBs              Counter,
            bHpStsTotalBBEs             Counter,
            bHpStsTotalESs              Counter,
            bHpStsTotalBESs             Counter,
            bHpStsTotalSESs             Counter,
            bHpStsTotalUASs             Counter
        }

        bHpStsTotalUnit  OBJECT-TYPE
            SYNTAX  UnitID
            ACCESS  read-only
            STATUS  mandatory
            DESCRIPTION
            "unit 1 to 4."
            ::= { bHP-STSTotalEty 1 }

        bHpStsTotalPort  OBJECT-TYPE
            SYNTAX  PortID
            ACCESS  read-only
            STATUS  mandatory
            DESCRIPTION
                "PORT #1~#2"
            ::= { bHP-STSTotalEty 2 }

        bHpStsTotalAug1Sts3  OBJECT-TYPE
            SYNTAX  Aug1Sts3Num
            ACCESS  read-only
            STATUS  mandatory
            DESCRIPTION
                "AUG1/STS3 index"
            ::= { bHP-STSTotalEty 3 }

        bHpStsTotalVc3Sts1  OBJECT-TYPE
            SYNTAX  Vc3Sts1Num
            ACCESS  read-only
            STATUS  mandatory
            DESCRIPTION
                "VC3/STS1 index"
            ::= { bHP-STSTotalEty 4 }

        bHpStsTotalEBs  OBJECT-TYPE
            SYNTAX  Counter
            ACCESS  read-only
            STATUS  mandatory
            DESCRIPTION
                "B3(BIP-8) Error Block"
            ::= { bHP-STSTotalEty 5 }

        bHpStsTotalBBEs  OBJECT-TYPE
            SYNTAX  Counter
            ACCESS  read-only
            STATUS  mandatory
            DESCRIPTION
                "B3(BIP-8) Background Block Error"
            ::= { bHP-STSTotalEty 6 }

        bHpStsTotalESs  OBJECT-TYPE
            SYNTAX  Counter
            ACCESS  read-only
            STATUS  mandatory
            DESCRIPTION
                "B3(BIP-8) Error Second"
            ::= { bHP-STSTotalEty 7 }

        bHpStsTotalBESs  OBJECT-TYPE
            SYNTAX  Counter
            ACCESS  read-only
            STATUS  mandatory
            DESCRIPTION
                "B3(BIP-8) Background Error Second"
            ::= { bHP-STSTotalEty 8 }

        bHpStsTotalSESs  OBJECT-TYPE
            SYNTAX  Counter
            ACCESS  read-only
            STATUS  mandatory
            DESCRIPTION
                "B3(BIP-8) Severly Error Second"
            ::= { bHP-STSTotalEty 9 }

        bHpStsTotalUASs  OBJECT-TYPE
            SYNTAX  Counter
            ACCESS  read-only
            STATUS  mandatory
            DESCRIPTION
                "B3(BIP-8) Unavailable Second"
            ::= { bHP-STSTotalEty 10 }

--
--  B155/622 HP-REI Current Table
--
        bFarEndHP-STSCurrTab  OBJECT-TYPE
            SYNTAX  SEQUENCE OF  BFarEndHP-STSCurrEty
            ACCESS  not-accessible
            STATUS  mandatory
            DESCRIPTION
                "The B155/622 HP-REI/REI-P Current table."
            ::= { b155-622PerfDisplayTab 17 }

        bFarEndHP-STSCurrEty  OBJECT-TYPE
            SYNTAX  BFarEndHP-STSCurrEty
            ACCESS  not-accessible
            STATUS  mandatory
            DESCRIPTION
                "An entry in the B155/622 HP-REI/REI-P Current table."
            INDEX { bFrHpStsCurrUnit , bFrHpStsCurrPort ,
                    bFrHpStsCurrAug1Sts3 , bFrHpStsCurrVc3Sts1 }
            ::= { bFarEndHP-STSCurrTab 1 }

        BFarEndHP-STSCurrEty ::= SEQUENCE {
            bFrHpStsCurrUnit            UnitID,
            bFrHpStsCurrPort            PortID,
            bFrHpStsCurrAug1Sts3        Aug1Sts3Num,
            bFrHpStsCurrVc3Sts1         Vc3Sts1Num,
            bFrHpStsCurrEBs             Counter,
            bFrHpStsCurrBBEs            Counter,
            bFrHpStsCurrESs             Counter,
            bFrHpStsCurrBESs            Counter,
            bFrHpStsCurrSESs            Counter,
            bFrHpStsCurrUASs            Counter,
            bFrHpStsCurr24HValid15M     Counter,
            bFrHpStsCurr7DayValidDay    Counter,
            bFrHpStsCurr15MTimeElaps    Counter,
            bFrHpStsCurrDayValid15M     Counter
        }

        bFrHpStsCurrUnit  OBJECT-TYPE
            SYNTAX  UnitID
            ACCESS  read-only
            STATUS  mandatory
            DESCRIPTION
            "unit 1 to 4."
            ::= { bFarEndHP-STSCurrEty 1 }

        bFrHpStsCurrPort  OBJECT-TYPE
            SYNTAX  PortID
            ACCESS  read-only
            STATUS  mandatory
            DESCRIPTION
                "PORT #1~#2"
            ::= { bFarEndHP-STSCurrEty 2 }

        bFrHpStsCurrAug1Sts3  OBJECT-TYPE
            SYNTAX  Aug1Sts3Num
            ACCESS  read-only
            STATUS  mandatory
            DESCRIPTION
                "AUG1/STS3 index"
            ::= { bFarEndHP-STSCurrEty 3 }

        bFrHpStsCurrVc3Sts1  OBJECT-TYPE
            SYNTAX  Vc3Sts1Num
            ACCESS  read-only
            STATUS  mandatory
            DESCRIPTION
                "VC3/STS1 index"
            ::= { bFarEndHP-STSCurrEty 4 }

        bFrHpStsCurrEBs  OBJECT-TYPE
            SYNTAX  Counter
            ACCESS  read-only
            STATUS  mandatory
            DESCRIPTION
                "HP-REI/REI-P(BIP-8) Error Block"
            ::= { bFarEndHP-STSCurrEty 5 }

        bFrHpStsCurrBBEs  OBJECT-TYPE
            SYNTAX  Counter
            ACCESS  read-only
            STATUS  mandatory
            DESCRIPTION
                "HP-REI/REI-P(BIP-8) Background Block Error"
            ::= { bFarEndHP-STSCurrEty 6 }

        bFrHpStsCurrESs  OBJECT-TYPE
            SYNTAX  Counter
            ACCESS  read-only
            STATUS  mandatory
            DESCRIPTION
                "HP-REI/REI-P(BIP-8) Error Second"
            ::= { bFarEndHP-STSCurrEty 7 }

        bFrHpStsCurrBESs  OBJECT-TYPE
            SYNTAX  Counter
            ACCESS  read-only
            STATUS  mandatory
            DESCRIPTION
                "HP-REI/REI-P(BIP-8) Background Error Second"
            ::= { bFarEndHP-STSCurrEty 8 }

        bFrHpStsCurrSESs  OBJECT-TYPE
            SYNTAX  Counter
            ACCESS  read-only
            STATUS  mandatory
            DESCRIPTION
                "HP-REI/REI-P(BIP-8) Severly Error Second"
            ::= { bFarEndHP-STSCurrEty 9 }

        bFrHpStsCurrUASs  OBJECT-TYPE
            SYNTAX  Counter
            ACCESS  read-only
            STATUS  mandatory
            DESCRIPTION
                "HP-REI/REI-P(BIP-8) Unavailable Second"
            ::= { bFarEndHP-STSCurrEty 10 }

        bFrHpStsCurr24HValid15M  OBJECT-TYPE
            SYNTAX  Counter
            ACCESS  read-only
            STATUS  mandatory
            DESCRIPTION
                "HP-REI/REI-P(BIP-8) Valid 15-Min Interval"
            ::= { bFarEndHP-STSCurrEty 11 }

        bFrHpStsCurr7DayValidDay  OBJECT-TYPE
            SYNTAX  Counter
            ACCESS  read-only
            STATUS  mandatory
            DESCRIPTION
                "HP-REI/REI-P(BIP-8) Valid 1-Day Interval"
            ::= { bFarEndHP-STSCurrEty 12 }

        bFrHpStsCurr15MTimeElaps  OBJECT-TYPE
            SYNTAX  Counter
            ACCESS  read-only
            STATUS  mandatory
            DESCRIPTION
                "HP-REI/REI-P(BIP-8) Current 15-MIN Time Elapsed"
            ::= { bFarEndHP-STSCurrEty 13 }

        bFrHpStsCurrDayValid15M  OBJECT-TYPE
            SYNTAX  Counter
            ACCESS  read-only
            STATUS  mandatory
            DESCRIPTION
                "HP-REI/REI-P(BIP-8) Current Day Time Elapsed"
            ::= { bFarEndHP-STSCurrEty 14 }

--
--  B155/622 HP-REI/REI-P Interval Table
--
        bFarEndHP-STSIntervTab  OBJECT-TYPE
            SYNTAX  SEQUENCE OF  BFarEndHP-STSIntervEty
            ACCESS  not-accessible
            STATUS  mandatory
            DESCRIPTION
                "The B155/622 HP-REI/REI-P Interval table."
            ::= { b155-622PerfDisplayTab 18 }

        bFarEndHP-STSIntervEty  OBJECT-TYPE
            SYNTAX  BFarEndHP-STSIntervEty
            ACCESS  not-accessible
            STATUS  mandatory
            DESCRIPTION
                "An entry in the B155/622 HP-REI/REI-P Interval table."
            INDEX { bFrHpStsIntervUnit , bFrHpStsIntervPort ,
                    bFrHpStsIntervAug1Sts3 , bFrHpStsIntervVc3Sts1 ,
                    bFrHpStsIntervNumber }
            ::= { bFarEndHP-STSIntervTab 1 }

        BFarEndHP-STSIntervEty ::= SEQUENCE {
            bFrHpStsIntervUnit          UnitID,
            bFrHpStsIntervPort          PortID,
            bFrHpStsIntervAug1Sts3      Aug1Sts3Num,
            bFrHpStsIntervVc3Sts1       Vc3Sts1Num,
            bFrHpStsIntervNumber        INTEGER (1..96),
            bFrHpStsIntervEBs           Counter,
            bFrHpStsIntervBBEs          Counter,
            bFrHpStsIntervESs           Counter,
            bFrHpStsIntervBESs          Counter,
            bFrHpStsIntervSESs          Counter,
            bFrHpStsIntervUASs          Counter
        }

        bFrHpStsIntervUnit  OBJECT-TYPE
            SYNTAX  UnitID
            ACCESS  read-only
            STATUS  mandatory
            DESCRIPTION
            "unit 1 to 4."
            ::= { bFarEndHP-STSIntervEty 1 }

        bFrHpStsIntervPort  OBJECT-TYPE
            SYNTAX  PortID
            ACCESS  read-only
            STATUS  mandatory
            DESCRIPTION
                "PORT #1~#2"
            ::= { bFarEndHP-STSIntervEty 2 }

        bFrHpStsIntervAug1Sts3  OBJECT-TYPE
            SYNTAX  Aug1Sts3Num
            ACCESS  read-only
            STATUS  mandatory
            DESCRIPTION
                "AUG1/STS3 index"
            ::= { bFarEndHP-STSIntervEty 3 }

        bFrHpStsIntervVc3Sts1  OBJECT-TYPE
            SYNTAX  Vc3Sts1Num
            ACCESS  read-only
            STATUS  mandatory
            DESCRIPTION
                "VC3/STS1 index"
            ::= { bFarEndHP-STSIntervEty 4 }

        bFrHpStsIntervNumber  OBJECT-TYPE
            SYNTAX  INTEGER (1..96)
            ACCESS  read-only
            STATUS  mandatory
            DESCRIPTION
                "A number between 1 and 96"
            ::= { bFarEndHP-STSIntervEty 5 }

        bFrHpStsIntervEBs  OBJECT-TYPE
            SYNTAX  Counter
            ACCESS  read-only
            STATUS  mandatory
            DESCRIPTION
                "HP-REI/REI-P(BIP-8) Error Block"
            ::= { bFarEndHP-STSIntervEty 6 }

        bFrHpStsIntervBBEs  OBJECT-TYPE
            SYNTAX  Counter
            ACCESS  read-only
            STATUS  mandatory
            DESCRIPTION
                "HP-REI/REI-P(BIP-8) Background Block Error"
            ::= { bFarEndHP-STSIntervEty 7 }

        bFrHpStsIntervESs  OBJECT-TYPE
            SYNTAX  Counter
            ACCESS  read-only
            STATUS  mandatory
            DESCRIPTION
                "HP-REI/REI-P(BIP-8) Error Second"
            ::= { bFarEndHP-STSIntervEty 8 }

        bFrHpStsIntervBESs  OBJECT-TYPE
            SYNTAX  Counter
            ACCESS  read-only
            STATUS  mandatory
            DESCRIPTION
                "HP-REI/REI-P(BIP-8) Background Error Second"
            ::= { bFarEndHP-STSIntervEty 9 }

        bFrHpStsIntervSESs  OBJECT-TYPE
            SYNTAX  Counter
            ACCESS  read-only
            STATUS  mandatory
            DESCRIPTION
                "HP-REI/REI-P(BIP-8) Severly Error Second"
            ::= { bFarEndHP-STSIntervEty 10 }

        bFrHpStsIntervUASs  OBJECT-TYPE
            SYNTAX  Counter
            ACCESS  read-only
            STATUS  mandatory
            DESCRIPTION
                "HP-REI/REI-P(BIP-8) Unavailable Second"
            ::= { bFarEndHP-STSIntervEty 11 }

--
--  B155/622 HP-REI/REI-P 7 Days Table
--
        bFarEndHP-STS7DaysTab  OBJECT-TYPE
            SYNTAX  SEQUENCE OF  BFarEndHP-STS7DaysEty
            ACCESS  not-accessible
            STATUS  mandatory
            DESCRIPTION
                "The B155/622 HP-REI/REI-P 7 days table."
            ::= { b155-622PerfDisplayTab 19 }

        bFarEndHP-STS7DaysEty  OBJECT-TYPE
            SYNTAX  BFarEndHP-STS7DaysEty
            ACCESS  not-accessible
            STATUS  mandatory
            DESCRIPTION
                "An entry in the B155/622 HP-REI/REI-P 7 days table."
            INDEX { bFrHpSts7DaysUnit , bFrHpSts7DaysPort ,
                    bFrHpSts7DaysAug1Sts3 , bFrHpSts7DaysVc3Sts1 ,
                    bFrHpSts7DaysNumber }
            ::= { bFarEndHP-STS7DaysTab 1 }

        BFarEndHP-STS7DaysEty ::= SEQUENCE {
            bFrHpSts7DaysUnit           UnitID,
            bFrHpSts7DaysPort           PortID,
            bFrHpSts7DaysAug1Sts3       Aug1Sts3Num,
            bFrHpSts7DaysVc3Sts1        Vc3Sts1Num,
            bFrHpSts7DaysNumber         INTEGER (1..7),
            bFrHpSts7DaysDate           DisplayString (SIZE (0..255)),
            bFrHpSts7DaysEBs            Counter,
            bFrHpSts7DaysBBEs           Counter,
            bFrHpSts7DaysESs            Counter,
            bFrHpSts7DaysBESs           Counter,
            bFrHpSts7DaysSESs           Counter,
            bFrHpSts7DaysUASs           Counter
        }

        bFrHpSts7DaysUnit  OBJECT-TYPE
            SYNTAX  UnitID
            ACCESS  read-only
            STATUS  mandatory
            DESCRIPTION
            "unit 1 to 4."
            ::= { bFarEndHP-STS7DaysEty 1 }

        bFrHpSts7DaysPort  OBJECT-TYPE
            SYNTAX  PortID
            ACCESS  read-only
            STATUS  mandatory
            DESCRIPTION
                "PORT #1~#2"
            ::= { bFarEndHP-STS7DaysEty 2 }

        bFrHpSts7DaysAug1Sts3  OBJECT-TYPE
            SYNTAX  Aug1Sts3Num
            ACCESS  read-only
            STATUS  mandatory
            DESCRIPTION
                "AUG1/STS3 index"
            ::= { bFarEndHP-STS7DaysEty 3 }

        bFrHpSts7DaysVc3Sts1  OBJECT-TYPE
            SYNTAX  Vc3Sts1Num
            ACCESS  read-only
            STATUS  mandatory
            DESCRIPTION
                "VC3/STS1 index"
            ::= { bFarEndHP-STS7DaysEty 4 }

        bFrHpSts7DaysNumber  OBJECT-TYPE
            SYNTAX  INTEGER (1..7)
            ACCESS  read-only
            STATUS  mandatory
            DESCRIPTION
                "A number between 1 and 7"
            ::= { bFarEndHP-STS7DaysEty 5 }

        bFrHpSts7DaysDate  OBJECT-TYPE
            SYNTAX  DisplayString (SIZE (0..255))
            ACCESS  read-only
            STATUS  mandatory
            DESCRIPTION
                "Date"
            ::= { bFarEndHP-STS7DaysEty 6 }

        bFrHpSts7DaysEBs  OBJECT-TYPE
            SYNTAX  Counter
            ACCESS  read-only
            STATUS  mandatory
            DESCRIPTION
                "HP-REI/REI-P(BIP-8) Error Block"
            ::= { bFarEndHP-STS7DaysEty 7 }

        bFrHpSts7DaysBBEs  OBJECT-TYPE
            SYNTAX  Counter
            ACCESS  read-only
            STATUS  mandatory
            DESCRIPTION
                "HP-REI/REI-P(BIP-8) Background Block Error"
            ::= { bFarEndHP-STS7DaysEty 8 }

        bFrHpSts7DaysESs  OBJECT-TYPE
            SYNTAX  Counter
            ACCESS  read-only
            STATUS  mandatory
            DESCRIPTION
                "HP-REI/REI-P(BIP-8) Error Second"
            ::= { bFarEndHP-STS7DaysEty 9 }

        bFrHpSts7DaysBESs  OBJECT-TYPE
            SYNTAX  Counter
            ACCESS  read-only
            STATUS  mandatory
            DESCRIPTION
                "HP-REI/REI-P(BIP-8) Background Error Second"
            ::= { bFarEndHP-STS7DaysEty 10 }

        bFrHpSts7DaysSESs  OBJECT-TYPE
            SYNTAX  Counter
            ACCESS  read-only
            STATUS  mandatory
            DESCRIPTION
                "HP-REI/REI-P(BIP-8) Severly Error Second"
            ::= { bFarEndHP-STS7DaysEty 11 }

        bFrHpSts7DaysUASs  OBJECT-TYPE
            SYNTAX  Counter
            ACCESS  read-only
            STATUS  mandatory
            DESCRIPTION
                "HP-REI/REI-P(BIP-8) Unavailable Second"
            ::= { bFarEndHP-STS7DaysEty 12 }

--
--  B155/622 HP-REI/REI-P Total Table
--
        bFarEndHP-STSTotalTab  OBJECT-TYPE
            SYNTAX  SEQUENCE OF  BFarEndHP-STSTotalEty
            ACCESS  not-accessible
            STATUS  mandatory
            DESCRIPTION
                "The B155/622 HP-REI/REI-P Total table."
            ::= { b155-622PerfDisplayTab 20 }

        bFarEndHP-STSTotalEty  OBJECT-TYPE
            SYNTAX  BFarEndHP-STSTotalEty
            ACCESS  not-accessible
            STATUS  mandatory
            DESCRIPTION
                "An entry in the B155/622 HP-REI/REI-P Total table."
            INDEX { bFrHpStsTotalUnit , bFrHpStsTotalPort ,
                    bFrHpStsTotalAug1Sts3 , bFrHpStsTotalVc3Sts1 }
            ::= { bFarEndHP-STSTotalTab 1 }

        BFarEndHP-STSTotalEty ::= SEQUENCE {
            bFrHpStsTotalUnit           UnitID,
            bFrHpStsTotalPort           PortID,
            bFrHpStsTotalAug1Sts3       Aug1Sts3Num,
            bFrHpStsTotalVc3Sts1        Vc3Sts1Num,
            bFrHpStsTotalEBs            Counter,
            bFrHpStsTotalBBEs           Counter,
            bFrHpStsTotalESs            Counter,
            bFrHpStsTotalBESs           Counter,
            bFrHpStsTotalSESs           Counter,
            bFrHpStsTotalUASs           Counter
        }

        bFrHpStsTotalUnit  OBJECT-TYPE
            SYNTAX  UnitID
            ACCESS  read-only
            STATUS  mandatory
            DESCRIPTION
            "unit 1 to 4."
            ::= { bFarEndHP-STSTotalEty 1 }

        bFrHpStsTotalPort  OBJECT-TYPE
            SYNTAX  PortID
            ACCESS  read-only
            STATUS  mandatory
            DESCRIPTION
                "PORT #1~#2"
            ::= { bFarEndHP-STSTotalEty 2 }

        bFrHpStsTotalAug1Sts3  OBJECT-TYPE
            SYNTAX  Aug1Sts3Num
            ACCESS  read-only
            STATUS  mandatory
            DESCRIPTION
                "AUG1/STS3 index"
            ::= { bFarEndHP-STSTotalEty 3 }

        bFrHpStsTotalVc3Sts1  OBJECT-TYPE
            SYNTAX  Vc3Sts1Num
            ACCESS  read-only
            STATUS  mandatory
            DESCRIPTION
                "VC3/STS1 index"
            ::= { bFarEndHP-STSTotalEty 4 }

        bFrHpStsTotalEBs  OBJECT-TYPE
            SYNTAX  Counter
            ACCESS  read-only
            STATUS  mandatory
            DESCRIPTION
                "HP-REI/REI-P(BIP-8) Error Block"
            ::= { bFarEndHP-STSTotalEty 5 }

        bFrHpStsTotalBBEs  OBJECT-TYPE
            SYNTAX  Counter
            ACCESS  read-only
            STATUS  mandatory
            DESCRIPTION
                "HP-REI/REI-P(BIP-8) Background Block Error"
            ::= { bFarEndHP-STSTotalEty 6 }

        bFrHpStsTotalESs  OBJECT-TYPE
            SYNTAX  Counter
            ACCESS  read-only
            STATUS  mandatory
            DESCRIPTION
                "HP-REI/REI-P(BIP-8) Error Second"
            ::= { bFarEndHP-STSTotalEty 7 }

        bFrHpStsTotalBESs  OBJECT-TYPE
            SYNTAX  Counter
            ACCESS  read-only
            STATUS  mandatory
            DESCRIPTION
                "HP-REI/REI-P(BIP-8) Background Error Second"
            ::= { bFarEndHP-STSTotalEty 8 }

        bFrHpStsTotalSESs  OBJECT-TYPE
            SYNTAX  Counter
            ACCESS  read-only
            STATUS  mandatory
            DESCRIPTION
                "HP-REI/REI-P(BIP-8) Severly Error Second"
            ::= { bFarEndHP-STSTotalEty 9 }

        bFrHpStsTotalUASs  OBJECT-TYPE
            SYNTAX  Counter
            ACCESS  read-only
            STATUS  mandatory
            DESCRIPTION
                "HP-REI/REI-P(BIP-8) Unavailable Second"
            ::= { bFarEndHP-STSTotalEty 10 }

--
--  B155/622 LP-BIP Current Table
--
        bLP-VTCurrTab  OBJECT-TYPE
            SYNTAX  SEQUENCE OF  BLP-VTCurrEty
            ACCESS  not-accessible
            STATUS  mandatory
            DESCRIPTION
                "The B155/622 LP-BIP Current table."
            ::= { b155-622PerfDisplayTab 21 }

        bLP-VTCurrEty  OBJECT-TYPE
            SYNTAX  BLP-VTCurrEty
            ACCESS  not-accessible
            STATUS  mandatory
            DESCRIPTION
                "An entry in the B155/622 LP-BIP Current table."
            INDEX { bLpVtCurrUnit , bLpVtCurrPort ,
                    bLpVtCurrAug1Sts3 , bLpVtCurrVc3Sts1 ,
                    bLpVtCurrTU1xVtx }
            ::= { bLP-VTCurrTab 1 }

        BLP-VTCurrEty ::= SEQUENCE {
            bLpVtCurrUnit               UnitID,
            bLpVtCurrPort               PortID,
            bLpVtCurrAug1Sts3           Aug1Sts3Num,
            bLpVtCurrVc3Sts1            Vc3Sts1Num,
            bLpVtCurrTU1xVtx            TU1xVtxNum,
            bLpVtCurrEBs                Counter,
            bLpVtCurrBBEs               Counter,
            bLpVtCurrESs                Counter,
            bLpVtCurrBESs               Counter,
            bLpVtCurrSESs               Counter,
            bLpVtCurrUASs               Counter,
            bLpVtCurr24HValid15M        Counter,
            bLpVtCurr7DayValidDay       Counter,
            bLpVtCurr15MTimeElaps       Counter,
            bLpVtCurrDayValid15M        Counter
        }

        bLpVtCurrUnit  OBJECT-TYPE
            SYNTAX  UnitID
            ACCESS  read-only
            STATUS  mandatory
            DESCRIPTION
            "unit 1 to 4."
            ::= { bLP-VTCurrEty 1 }

        bLpVtCurrPort  OBJECT-TYPE
            SYNTAX  PortID
            ACCESS  read-only
            STATUS  mandatory
            DESCRIPTION
                "PORT #1~#2"
            ::= { bLP-VTCurrEty 2 }

        bLpVtCurrAug1Sts3  OBJECT-TYPE
            SYNTAX  Aug1Sts3Num
            ACCESS  read-only
            STATUS  mandatory
            DESCRIPTION
                "AUG1/STS3 index"
            ::= { bLP-VTCurrEty 3 }

        bLpVtCurrVc3Sts1  OBJECT-TYPE
            SYNTAX  Vc3Sts1Num
            ACCESS  read-only
            STATUS  mandatory
            DESCRIPTION
                "VC3/STS1 index"
            ::= { bLP-VTCurrEty 4 }

        bLpVtCurrTU1xVtx  OBJECT-TYPE
            SYNTAX  TU1xVtxNum
            ACCESS  read-only
            STATUS  mandatory
            DESCRIPTION
                "VC1x/VTx index"
            ::= { bLP-VTCurrEty 5 }

        bLpVtCurrEBs  OBJECT-TYPE
            SYNTAX  Counter
            ACCESS  read-only
            STATUS  mandatory
            DESCRIPTION
                "LP-BIP Error Block"
            ::= { bLP-VTCurrEty 6 }

        bLpVtCurrBBEs  OBJECT-TYPE
            SYNTAX  Counter
            ACCESS  read-only
            STATUS  mandatory
            DESCRIPTION
                "LP-BIP Background Block Error"
            ::= { bLP-VTCurrEty 7 }

        bLpVtCurrESs  OBJECT-TYPE
            SYNTAX  Counter
            ACCESS  read-only
            STATUS  mandatory
            DESCRIPTION
                "LP-BIP Error Second"
            ::= { bLP-VTCurrEty 8 }

        bLpVtCurrBESs  OBJECT-TYPE
            SYNTAX  Counter
            ACCESS  read-only
            STATUS  mandatory
            DESCRIPTION
                "LP-BIP Background Error Second"
            ::= { bLP-VTCurrEty 9 }

        bLpVtCurrSESs  OBJECT-TYPE
            SYNTAX  Counter
            ACCESS  read-only
            STATUS  mandatory
            DESCRIPTION
                "LP-BIP Severly Error Second"
            ::= { bLP-VTCurrEty 10 }

        bLpVtCurrUASs  OBJECT-TYPE
            SYNTAX  Counter
            ACCESS  read-only
            STATUS  mandatory
            DESCRIPTION
                "LP-BIP Unavailable Second"
            ::= { bLP-VTCurrEty 11 }

        bLpVtCurr24HValid15M  OBJECT-TYPE
            SYNTAX  Counter
            ACCESS  read-only
            STATUS  mandatory
            DESCRIPTION
                "LP-BIP Valid 15-Min Interval"
            ::= { bLP-VTCurrEty 12 }

        bLpVtCurr7DayValidDay  OBJECT-TYPE
            SYNTAX  Counter
            ACCESS  read-only
            STATUS  mandatory
            DESCRIPTION
                "LP-BIP Valid 1-Day Interval"
            ::= { bLP-VTCurrEty 13 }

        bLpVtCurr15MTimeElaps  OBJECT-TYPE
            SYNTAX  Counter
            ACCESS  read-only
            STATUS  mandatory
            DESCRIPTION
                "LP-BIP Current 15-MIN Time Elapsed"
            ::= { bLP-VTCurrEty 14 }

        bLpVtCurrDayValid15M  OBJECT-TYPE
            SYNTAX  Counter
            ACCESS  read-only
            STATUS  mandatory
            DESCRIPTION
                "LP-BIP Current Day Time Elapsed"
            ::= { bLP-VTCurrEty 15 }

--
--  B155/622 LP-BIP Interval Table
--
        bLP-VTIntervTab  OBJECT-TYPE
            SYNTAX  SEQUENCE OF  BLP-VTIntervEty
            ACCESS  not-accessible
            STATUS  mandatory
            DESCRIPTION
                "The B155/622 LP-BIP Interval table."
            ::= { b155-622PerfDisplayTab 22 }

        bLP-VTIntervEty  OBJECT-TYPE
            SYNTAX  BLP-VTIntervEty
            ACCESS  not-accessible
            STATUS  mandatory
            DESCRIPTION
                "An entry in the B155/622 LP-BIP Interval table."
            INDEX { bLpVtIntervUnit , bLpVtIntervPort ,
                    bLpVtIntervAug1Sts3 , bLpVtIntervVc3Sts1 ,
                    bLpVtIntervTU1xVtx , bLpVtIntervNumber }
            ::= { bLP-VTIntervTab 1 }

        BLP-VTIntervEty ::= SEQUENCE {
            bLpVtIntervUnit             UnitID,
            bLpVtIntervPort             PortID,
            bLpVtIntervAug1Sts3         Aug1Sts3Num,
            bLpVtIntervVc3Sts1          Vc3Sts1Num,
            bLpVtIntervTU1xVtx          TU1xVtxNum,
            bLpVtIntervNumber           INTEGER (1..96),
            bLpVtIntervEBs              Counter,
            bLpVtIntervBBEs             Counter,
            bLpVtIntervESs              Counter,
            bLpVtIntervBESs             Counter,
            bLpVtIntervSESs             Counter,
            bLpVtIntervUASs             Counter
        }

        bLpVtIntervUnit  OBJECT-TYPE
            SYNTAX  UnitID
            ACCESS  read-only
            STATUS  mandatory
            DESCRIPTION
            "unit 1 to 4."
            ::= { bLP-VTIntervEty 1 }

        bLpVtIntervPort  OBJECT-TYPE
            SYNTAX  PortID
            ACCESS  read-only
            STATUS  mandatory
            DESCRIPTION
                "PORT #1~#2"
            ::= { bLP-VTIntervEty 2 }

        bLpVtIntervAug1Sts3  OBJECT-TYPE
            SYNTAX  Aug1Sts3Num
            ACCESS  read-only
            STATUS  mandatory
            DESCRIPTION
                "AUG1/STS3 index"
            ::= { bLP-VTIntervEty 3 }

        bLpVtIntervVc3Sts1  OBJECT-TYPE
            SYNTAX  Vc3Sts1Num
            ACCESS  read-only
            STATUS  mandatory
            DESCRIPTION
                "VC3/STS1 index"
            ::= { bLP-VTIntervEty 4 }

        bLpVtIntervTU1xVtx  OBJECT-TYPE
            SYNTAX  TU1xVtxNum
            ACCESS  read-only
            STATUS  mandatory
            DESCRIPTION
                "VC1x/VTx index"
            ::= { bLP-VTIntervEty 5 }

        bLpVtIntervNumber  OBJECT-TYPE
            SYNTAX  INTEGER (1..96)
            ACCESS  read-only
            STATUS  mandatory
            DESCRIPTION
                "A number between 1 and 96"
            ::= { bLP-VTIntervEty 6 }

        bLpVtIntervEBs  OBJECT-TYPE
            SYNTAX  Counter
            ACCESS  read-only
            STATUS  mandatory
            DESCRIPTION
                "LP-BIP Error Block"
            ::= { bLP-VTIntervEty 7 }

        bLpVtIntervBBEs  OBJECT-TYPE
            SYNTAX  Counter
            ACCESS  read-only
            STATUS  mandatory
            DESCRIPTION
                "LP-BIP Background Block Error"
            ::= { bLP-VTIntervEty 8 }

        bLpVtIntervESs  OBJECT-TYPE
            SYNTAX  Counter
            ACCESS  read-only
            STATUS  mandatory
            DESCRIPTION
                "LP-BIP Error Second"
            ::= { bLP-VTIntervEty 9 }

        bLpVtIntervBESs  OBJECT-TYPE
            SYNTAX  Counter
            ACCESS  read-only
            STATUS  mandatory
            DESCRIPTION
                "LP-BIP Background Error Second"
            ::= { bLP-VTIntervEty 10 }

        bLpVtIntervSESs  OBJECT-TYPE
            SYNTAX  Counter
            ACCESS  read-only
            STATUS  mandatory
            DESCRIPTION
                "LP-BIP Severly Error Second"
            ::= { bLP-VTIntervEty 11 }

        bLpVtIntervUASs  OBJECT-TYPE
            SYNTAX  Counter
            ACCESS  read-only
            STATUS  mandatory
            DESCRIPTION
                "LP-BIP Unavailable Second"
            ::= { bLP-VTIntervEty 12 }

--
--  B155/622 LP-BIP 7 Days Table
--
        bLP-VT7DaysTab  OBJECT-TYPE
            SYNTAX  SEQUENCE OF  BLP-VT7DaysEty
            ACCESS  not-accessible
            STATUS  mandatory
            DESCRIPTION
                "The B155/622 LP-BIP 7 days table."
            ::= { b155-622PerfDisplayTab 23 }

        bLP-VT7DaysEty  OBJECT-TYPE
            SYNTAX  BLP-VT7DaysEty
            ACCESS  not-accessible
            STATUS  mandatory
            DESCRIPTION
                "An entry in the B155/622 LP-BIP 7 days table."
            INDEX { bLpVt7DaysUnit , bLpVt7DaysPort ,
                    bLpVt7DaysAug1Sts3 , bLpVt7DaysVc3Sts1 ,
                    bLpVt7DaysTU1xVtx , bLpVt7DaysNumber }
            ::= { bLP-VT7DaysTab 1 }

        BLP-VT7DaysEty ::= SEQUENCE {
            bLpVt7DaysUnit              UnitID,
            bLpVt7DaysPort              PortID,
            bLpVt7DaysAug1Sts3          Aug1Sts3Num,
            bLpVt7DaysVc3Sts1           Vc3Sts1Num,
            bLpVt7DaysTU1xVtx           TU1xVtxNum,
            bLpVt7DaysNumber            INTEGER (1..7),
            bLpVt7DaysDate              DisplayString (SIZE (0..255)),
            bLpVt7DaysEBs               Counter,
            bLpVt7DaysBBEs              Counter,
            bLpVt7DaysESs               Counter,
            bLpVt7DaysBESs              Counter,
            bLpVt7DaysSESs              Counter,
            bLpVt7DaysUASs              Counter
        }

        bLpVt7DaysUnit  OBJECT-TYPE
            SYNTAX  UnitID
            ACCESS  read-only
            STATUS  mandatory
            DESCRIPTION
            "unit 1 to 4."
            ::= { bLP-VT7DaysEty 1 }

        bLpVt7DaysPort  OBJECT-TYPE
            SYNTAX  PortID
            ACCESS  read-only
            STATUS  mandatory
            DESCRIPTION
                "PORT #1~#2"
            ::= { bLP-VT7DaysEty 2 }

        bLpVt7DaysAug1Sts3  OBJECT-TYPE
            SYNTAX  Aug1Sts3Num
            ACCESS  read-only
            STATUS  mandatory
            DESCRIPTION
                "AUG1/STS3 index"
            ::= { bLP-VT7DaysEty 3 }

        bLpVt7DaysVc3Sts1  OBJECT-TYPE
            SYNTAX  Vc3Sts1Num
            ACCESS  read-only
            STATUS  mandatory
            DESCRIPTION
                "VC3/STS1 index"
            ::= { bLP-VT7DaysEty 4 }

        bLpVt7DaysTU1xVtx  OBJECT-TYPE
            SYNTAX  TU1xVtxNum
            ACCESS  read-only
            STATUS  mandatory
            DESCRIPTION
                "VC1x/VTx index"
            ::= { bLP-VT7DaysEty 5 }

        bLpVt7DaysNumber  OBJECT-TYPE
            SYNTAX  INTEGER (1..7)
            ACCESS  read-only
            STATUS  mandatory
            DESCRIPTION
                "A number between 1 and 7"
            ::= { bLP-VT7DaysEty 6 }

        bLpVt7DaysDate  OBJECT-TYPE
            SYNTAX  DisplayString (SIZE (0..255))
            ACCESS  read-only
            STATUS  mandatory
            DESCRIPTION
                "Date"
            ::= { bLP-VT7DaysEty 7 }

        bLpVt7DaysEBs  OBJECT-TYPE
            SYNTAX  Counter
            ACCESS  read-only
            STATUS  mandatory
            DESCRIPTION
                "LP-BIP Error Block"
            ::= { bLP-VT7DaysEty 8 }

        bLpVt7DaysBBEs  OBJECT-TYPE
            SYNTAX  Counter
            ACCESS  read-only
            STATUS  mandatory
            DESCRIPTION
                "LP-BIP Background Block Error"
            ::= { bLP-VT7DaysEty 9 }

        bLpVt7DaysESs  OBJECT-TYPE
            SYNTAX  Counter
            ACCESS  read-only
            STATUS  mandatory
            DESCRIPTION
                "LP-BIP Error Second"
            ::= { bLP-VT7DaysEty 10 }

        bLpVt7DaysBESs  OBJECT-TYPE
            SYNTAX  Counter
            ACCESS  read-only
            STATUS  mandatory
            DESCRIPTION
                "LP-BIP Background Error Second"
            ::= { bLP-VT7DaysEty 11 }

        bLpVt7DaysSESs  OBJECT-TYPE
            SYNTAX  Counter
            ACCESS  read-only
            STATUS  mandatory
            DESCRIPTION
                "LP-BIP Severly Error Second"
            ::= { bLP-VT7DaysEty 12 }

        bLpVt7DaysUASs  OBJECT-TYPE
            SYNTAX  Counter
            ACCESS  read-only
            STATUS  mandatory
            DESCRIPTION
                "LP-BIP Unavailable Second"
            ::= { bLP-VT7DaysEty 13 }

--
--  B155/622 LP-BIP Total Table
--
        bLP-VTTotalTab  OBJECT-TYPE
            SYNTAX  SEQUENCE OF  BLP-VTTotalEty
            ACCESS  not-accessible
            STATUS  mandatory
            DESCRIPTION
                "The B155/622 LP-BIP Total table."
            ::= { b155-622PerfDisplayTab 24 }

        bLP-VTTotalEty  OBJECT-TYPE
            SYNTAX  BLP-VTTotalEty
            ACCESS  not-accessible
            STATUS  mandatory
            DESCRIPTION
                "An entry in the B155/622 LP-BIP Total table."
            INDEX { bLpVtTotalUnit , bLpVtTotalPort ,
                    bLpVtTotalAug1Sts3 , bLpVtTotalVc3Sts1 ,
                    bLpVtTotalTU1xVtx }
            ::= { bLP-VTTotalTab 1 }

        BLP-VTTotalEty ::= SEQUENCE {
            bLpVtTotalUnit              UnitID,
            bLpVtTotalPort              PortID,
            bLpVtTotalAug1Sts3          Aug1Sts3Num,
            bLpVtTotalVc3Sts1           Vc3Sts1Num,
            bLpVtTotalTU1xVtx           TU1xVtxNum,
            bLpVtTotalEBs               Counter,
            bLpVtTotalBBEs              Counter,
            bLpVtTotalESs               Counter,
            bLpVtTotalBESs              Counter,
            bLpVtTotalSESs              Counter,
            bLpVtTotalUASs              Counter
        }

        bLpVtTotalUnit  OBJECT-TYPE
            SYNTAX  UnitID
            ACCESS  read-only
            STATUS  mandatory
            DESCRIPTION
            "unit 1 to 4."
            ::= { bLP-VTTotalEty 1 }

        bLpVtTotalPort  OBJECT-TYPE
            SYNTAX  PortID
            ACCESS  read-only
            STATUS  mandatory
            DESCRIPTION
                "PORT #1~#2"
            ::= { bLP-VTTotalEty 2 }

        bLpVtTotalAug1Sts3  OBJECT-TYPE
            SYNTAX  Aug1Sts3Num
            ACCESS  read-only
            STATUS  mandatory
            DESCRIPTION
                "AUG1/STS3 index"
            ::= { bLP-VTTotalEty 3 }

        bLpVtTotalVc3Sts1  OBJECT-TYPE
            SYNTAX  Vc3Sts1Num
            ACCESS  read-only
            STATUS  mandatory
            DESCRIPTION
                "VC3/STS1 index"
            ::= { bLP-VTTotalEty 4 }

        bLpVtTotalTU1xVtx  OBJECT-TYPE
            SYNTAX  TU1xVtxNum
            ACCESS  read-only
            STATUS  mandatory
            DESCRIPTION
                "VC1x/VTx index"
            ::= { bLP-VTTotalEty 5 }

        bLpVtTotalEBs  OBJECT-TYPE
            SYNTAX  Counter
            ACCESS  read-only
            STATUS  mandatory
            DESCRIPTION
                "LP-BIP Error Block"
            ::= { bLP-VTTotalEty 6 }

        bLpVtTotalBBEs  OBJECT-TYPE
            SYNTAX  Counter
            ACCESS  read-only
            STATUS  mandatory
            DESCRIPTION
                "LP-BIP Background Block Error"
            ::= { bLP-VTTotalEty 7 }

        bLpVtTotalESs  OBJECT-TYPE
            SYNTAX  Counter
            ACCESS  read-only
            STATUS  mandatory
            DESCRIPTION
                "LP-BIP Error Second"
            ::= { bLP-VTTotalEty 8 }

        bLpVtTotalBESs  OBJECT-TYPE
            SYNTAX  Counter
            ACCESS  read-only
            STATUS  mandatory
            DESCRIPTION
                "LP-BIP Background Error Second"
            ::= { bLP-VTTotalEty 9 }

        bLpVtTotalSESs  OBJECT-TYPE
            SYNTAX  Counter
            ACCESS  read-only
            STATUS  mandatory
            DESCRIPTION
                "LP-BIP Severly Error Second"
            ::= { bLP-VTTotalEty 10 }

        bLpVtTotalUASs  OBJECT-TYPE
            SYNTAX  Counter
            ACCESS  read-only
            STATUS  mandatory
            DESCRIPTION
                "LP-BIP Unavailable Second"
            ::= { bLP-VTTotalEty 11 }

--
--  B155/622 LP-REI Current Table
--
        bFarEndLP-VTCurrTab  OBJECT-TYPE
            SYNTAX  SEQUENCE OF  BFarEndLP-VTCurrEty
            ACCESS  not-accessible
            STATUS  mandatory
            DESCRIPTION
                "The B155/622 LP-REI/REI-V Current table."
            ::= { b155-622PerfDisplayTab 25 }

        bFarEndLP-VTCurrEty  OBJECT-TYPE
            SYNTAX  BFarEndLP-VTCurrEty
            ACCESS  not-accessible
            STATUS  mandatory
            DESCRIPTION
                "An entry in the B155/622 LP-REI/REI-V Current table."
            INDEX { bFrLpVtCurrUnit , bFrLpVtCurrPort ,
                    bFrLpVtCurrAug1Sts3 , bFrLpVtCurrVc3Sts1 ,
                    bFrLpVtCurrTU1xVtx }
            ::= { bFarEndLP-VTCurrTab 1 }

        BFarEndLP-VTCurrEty ::= SEQUENCE {
            bFrLpVtCurrUnit             UnitID,
            bFrLpVtCurrPort             PortID,
            bFrLpVtCurrAug1Sts3         Aug1Sts3Num,
            bFrLpVtCurrVc3Sts1          Vc3Sts1Num,
            bFrLpVtCurrTU1xVtx          TU1xVtxNum,
            bFrLpVtCurrEBs              Counter,
            bFrLpVtCurrBBEs             Counter,
            bFrLpVtCurrESs              Counter,
            bFrLpVtCurrBESs             Counter,
            bFrLpVtCurrSESs             Counter,
            bFrLpVtCurrUASs             Counter,
            bFrLpVtCurr24HValid15M      Counter,
            bFrLpVtCurr7DayValidDay     Counter,
            bFrLpVtCurr15MTimeElaps     Counter,
            bFrLpVtCurrDayValid15M      Counter
        }

        bFrLpVtCurrUnit  OBJECT-TYPE
            SYNTAX  UnitID
            ACCESS  read-only
            STATUS  mandatory
            DESCRIPTION
            "unit 1 to 4."
            ::= { bFarEndLP-VTCurrEty 1 }

        bFrLpVtCurrPort  OBJECT-TYPE
            SYNTAX  PortID
            ACCESS  read-only
            STATUS  mandatory
            DESCRIPTION
                "PORT #1~#2"
            ::= { bFarEndLP-VTCurrEty 2 }

        bFrLpVtCurrAug1Sts3  OBJECT-TYPE
            SYNTAX  Aug1Sts3Num
            ACCESS  read-only
            STATUS  mandatory
            DESCRIPTION
                "AUG1/STS3 index"
            ::= { bFarEndLP-VTCurrEty 3 }

        bFrLpVtCurrVc3Sts1  OBJECT-TYPE
            SYNTAX  Vc3Sts1Num
            ACCESS  read-only
            STATUS  mandatory
            DESCRIPTION
                "VC3/STS1 index"
            ::= { bFarEndLP-VTCurrEty 4 }

        bFrLpVtCurrTU1xVtx  OBJECT-TYPE
            SYNTAX  TU1xVtxNum
            ACCESS  read-only
            STATUS  mandatory
            DESCRIPTION
                "VC1x/VTx index"
            ::= { bFarEndLP-VTCurrEty 5 }

        bFrLpVtCurrEBs  OBJECT-TYPE
            SYNTAX  Counter
            ACCESS  read-only
            STATUS  mandatory
            DESCRIPTION
                "LP-REI/REI-V Error Block"
            ::= { bFarEndLP-VTCurrEty 6 }

        bFrLpVtCurrBBEs  OBJECT-TYPE
            SYNTAX  Counter
            ACCESS  read-only
            STATUS  mandatory
            DESCRIPTION
                "LP-REI/REI-V Background Block Error"
            ::= { bFarEndLP-VTCurrEty 7 }

        bFrLpVtCurrESs  OBJECT-TYPE
            SYNTAX  Counter
            ACCESS  read-only
            STATUS  mandatory
            DESCRIPTION
                "LP-REI/REI-V Error Second"
            ::= { bFarEndLP-VTCurrEty 8 }

        bFrLpVtCurrBESs  OBJECT-TYPE
            SYNTAX  Counter
            ACCESS  read-only
            STATUS  mandatory
            DESCRIPTION
                "LP-REI/REI-V Background Error Second"
            ::= { bFarEndLP-VTCurrEty 9 }

        bFrLpVtCurrSESs  OBJECT-TYPE
            SYNTAX  Counter
            ACCESS  read-only
            STATUS  mandatory
            DESCRIPTION
                "LP-REI/REI-V Severly Error Second"
            ::= { bFarEndLP-VTCurrEty 10 }

        bFrLpVtCurrUASs  OBJECT-TYPE
            SYNTAX  Counter
            ACCESS  read-only
            STATUS  mandatory
            DESCRIPTION
                "LP-REI/REI-V Unavailable Second"
            ::= { bFarEndLP-VTCurrEty 11 }

        bFrLpVtCurr24HValid15M  OBJECT-TYPE
            SYNTAX  Counter
            ACCESS  read-only
            STATUS  mandatory
            DESCRIPTION
                "LP-REI/REI-V Valid 15-Min Interval"
            ::= { bFarEndLP-VTCurrEty 12 }

        bFrLpVtCurr7DayValidDay  OBJECT-TYPE
            SYNTAX  Counter
            ACCESS  read-only
            STATUS  mandatory
            DESCRIPTION
                "LP-REI/REI-V Valid 1-Day Interval"
            ::= { bFarEndLP-VTCurrEty 13 }

        bFrLpVtCurr15MTimeElaps  OBJECT-TYPE
            SYNTAX  Counter
            ACCESS  read-only
            STATUS  mandatory
            DESCRIPTION
                "LP-REI/REI-V Current 15-MIN Time Elapsed"
            ::= { bFarEndLP-VTCurrEty 14 }

        bFrLpVtCurrDayValid15M  OBJECT-TYPE
            SYNTAX  Counter
            ACCESS  read-only
            STATUS  mandatory
            DESCRIPTION
                "LP-REI/REI-V Current Day Time Elapsed"
            ::= { bFarEndLP-VTCurrEty 15 }

--
--  B155/622 LP-REI/REI-V Interval Table
--
        bFarEndLP-VTIntervTab  OBJECT-TYPE
            SYNTAX  SEQUENCE OF  BFarEndLP-VTIntervEty
            ACCESS  not-accessible
            STATUS  mandatory
            DESCRIPTION
                "The B155/622 LP-REI/REI-V Interval table."
            ::= { b155-622PerfDisplayTab 26 }

        bFarEndLP-VTIntervEty  OBJECT-TYPE
            SYNTAX  BFarEndLP-VTIntervEty
            ACCESS  not-accessible
            STATUS  mandatory
            DESCRIPTION
                "An entry in the B155/622 LP-REI/REI-V Interval table."
            INDEX { bFrLpVtIntervUnit , bFrLpVtIntervPort ,
                    bFrLpVtIntervAug1Sts3 , bFrLpVtIntervVc3Sts1 ,
                    bFrLpVtIntervTU1xVtx , bFrLpVtIntervNumber }
            ::= { bFarEndLP-VTIntervTab 1 }

        BFarEndLP-VTIntervEty ::= SEQUENCE {
            bFrLpVtIntervUnit           UnitID,
            bFrLpVtIntervPort           PortID,
            bFrLpVtIntervAug1Sts3       Aug1Sts3Num,
            bFrLpVtIntervVc3Sts1        Vc3Sts1Num,
            bFrLpVtIntervTU1xVtx        TU1xVtxNum,
            bFrLpVtIntervNumber         INTEGER (1..96),
            bFrLpVtIntervEBs            Counter,
            bFrLpVtIntervBBEs           Counter,
            bFrLpVtIntervESs            Counter,
            bFrLpVtIntervBESs           Counter,
            bFrLpVtIntervSESs           Counter,
            bFrLpVtIntervUASs           Counter
        }

        bFrLpVtIntervUnit  OBJECT-TYPE
            SYNTAX  UnitID
            ACCESS  read-only
            STATUS  mandatory
            DESCRIPTION
            "unit 1 to 4."
            ::= { bFarEndLP-VTIntervEty 1 }

        bFrLpVtIntervPort  OBJECT-TYPE
            SYNTAX  PortID
            ACCESS  read-only
            STATUS  mandatory
            DESCRIPTION
                "PORT #1~#2"
            ::= { bFarEndLP-VTIntervEty 2 }

        bFrLpVtIntervAug1Sts3  OBJECT-TYPE
            SYNTAX  Aug1Sts3Num
            ACCESS  read-only
            STATUS  mandatory
            DESCRIPTION
                "AUG1/STS3 index"
            ::= { bFarEndLP-VTIntervEty 3 }

        bFrLpVtIntervVc3Sts1  OBJECT-TYPE
            SYNTAX  Vc3Sts1Num
            ACCESS  read-only
            STATUS  mandatory
            DESCRIPTION
                "VC3/STS1 index"
            ::= { bFarEndLP-VTIntervEty 4 }

        bFrLpVtIntervTU1xVtx  OBJECT-TYPE
            SYNTAX  TU1xVtxNum
            ACCESS  read-only
            STATUS  mandatory
            DESCRIPTION
                "VC1x/VTx index"
            ::= { bFarEndLP-VTIntervEty 5 }

        bFrLpVtIntervNumber  OBJECT-TYPE
            SYNTAX  INTEGER (1..96)
            ACCESS  read-only
            STATUS  mandatory
            DESCRIPTION
                "A number between 1 and 96"
            ::= { bFarEndLP-VTIntervEty 6 }

        bFrLpVtIntervEBs  OBJECT-TYPE
            SYNTAX  Counter
            ACCESS  read-only
            STATUS  mandatory
            DESCRIPTION
                "LP-REI/REI-V Error Block"
            ::= { bFarEndLP-VTIntervEty 7 }

        bFrLpVtIntervBBEs  OBJECT-TYPE
            SYNTAX  Counter
            ACCESS  read-only
            STATUS  mandatory
            DESCRIPTION
                "LP-REI/REI-V Background Block Error"
            ::= { bFarEndLP-VTIntervEty 8 }

        bFrLpVtIntervESs  OBJECT-TYPE
            SYNTAX  Counter
            ACCESS  read-only
            STATUS  mandatory
            DESCRIPTION
                "LP-REI/REI-V Error Second"
            ::= { bFarEndLP-VTIntervEty 9 }

        bFrLpVtIntervBESs  OBJECT-TYPE
            SYNTAX  Counter
            ACCESS  read-only
            STATUS  mandatory
            DESCRIPTION
                "LP-REI/REI-V Background Error Second"
            ::= { bFarEndLP-VTIntervEty 10 }

        bFrLpVtIntervSESs  OBJECT-TYPE
            SYNTAX  Counter
            ACCESS  read-only
            STATUS  mandatory
            DESCRIPTION
                "LP-REI/REI-V Severly Error Second"
            ::= { bFarEndLP-VTIntervEty 11 }

        bFrLpVtIntervUASs  OBJECT-TYPE
            SYNTAX  Counter
            ACCESS  read-only
            STATUS  mandatory
            DESCRIPTION
                "LP-REI/REI-V Unavailable Second"
            ::= { bFarEndLP-VTIntervEty 12 }

--
--  B155/622 LP-REI/REI-V 7 Days Table
--
        bFarEndLP-VT7DaysTab  OBJECT-TYPE
            SYNTAX  SEQUENCE OF  BFarEndLP-VT7DaysEty
            ACCESS  not-accessible
            STATUS  mandatory
            DESCRIPTION
                "The B155/622 LP-REI/REI-V 7 days table."
            ::= { b155-622PerfDisplayTab 27 }

        bFarEndLP-VT7DaysEty  OBJECT-TYPE
            SYNTAX  BFarEndLP-VT7DaysEty
            ACCESS  not-accessible
            STATUS  mandatory
            DESCRIPTION
                "An entry in the B155/622 LP-REI/REI-V 7 days table."
            INDEX { bFrLpVt7DaysUnit , bFrLpVt7DaysPort ,
                    bFrLpVt7DaysAug1Sts3 , bFrLpVt7DaysVc3Sts1 ,
                    bFrLpVt7DaysTU1xVtx , bFrLpVt7DaysNumber }
            ::= { bFarEndLP-VT7DaysTab 1 }

        BFarEndLP-VT7DaysEty ::= SEQUENCE {
            bFrLpVt7DaysUnit            UnitID,
            bFrLpVt7DaysPort            PortID,
            bFrLpVt7DaysAug1Sts3        Aug1Sts3Num,
            bFrLpVt7DaysVc3Sts1         Vc3Sts1Num,
            bFrLpVt7DaysTU1xVtx         TU1xVtxNum,
            bFrLpVt7DaysNumber          INTEGER (1..7),
            bFrLpVt7DaysDate            DisplayString (SIZE (0..255)),
            bFrLpVt7DaysEBs             Counter,
            bFrLpVt7DaysBBEs            Counter,
            bFrLpVt7DaysESs             Counter,
            bFrLpVt7DaysBESs            Counter,
            bFrLpVt7DaysSESs            Counter,
            bFrLpVt7DaysUASs            Counter
        }

        bFrLpVt7DaysUnit  OBJECT-TYPE
            SYNTAX  UnitID
            ACCESS  read-only
            STATUS  mandatory
            DESCRIPTION
            "unit 1 to 4."
            ::= { bFarEndLP-VT7DaysEty 1 }

        bFrLpVt7DaysPort  OBJECT-TYPE
            SYNTAX  PortID
            ACCESS  read-only
            STATUS  mandatory
            DESCRIPTION
                "PORT #1~#2"
            ::= { bFarEndLP-VT7DaysEty 2 }

        bFrLpVt7DaysAug1Sts3  OBJECT-TYPE
            SYNTAX  Aug1Sts3Num
            ACCESS  read-only
            STATUS  mandatory
            DESCRIPTION
                "AUG1/STS3 index"
            ::= { bFarEndLP-VT7DaysEty 3 }

        bFrLpVt7DaysVc3Sts1  OBJECT-TYPE
            SYNTAX  Vc3Sts1Num
            ACCESS  read-only
            STATUS  mandatory
            DESCRIPTION
                "VC3/STS1 index"
            ::= { bFarEndLP-VT7DaysEty 4 }

        bFrLpVt7DaysTU1xVtx  OBJECT-TYPE
            SYNTAX  TU1xVtxNum
            ACCESS  read-only
            STATUS  mandatory
            DESCRIPTION
                "VC1x/Vtx index"
            ::= { bFarEndLP-VT7DaysEty 5 }

        bFrLpVt7DaysNumber  OBJECT-TYPE
            SYNTAX  INTEGER (1..7)
            ACCESS  read-only
            STATUS  mandatory
            DESCRIPTION
                "A number between 1 and 7"
            ::= { bFarEndLP-VT7DaysEty 6 }

        bFrLpVt7DaysDate  OBJECT-TYPE
            SYNTAX  DisplayString (SIZE (0..255))
            ACCESS  read-only
            STATUS  mandatory
            DESCRIPTION
                "Date"
            ::= { bFarEndLP-VT7DaysEty 7 }

        bFrLpVt7DaysEBs  OBJECT-TYPE
            SYNTAX  Counter
            ACCESS  read-only
            STATUS  mandatory
            DESCRIPTION
                "LP-REI/REI-V Error Block"
            ::= { bFarEndLP-VT7DaysEty 8 }

        bFrLpVt7DaysBBEs  OBJECT-TYPE
            SYNTAX  Counter
            ACCESS  read-only
            STATUS  mandatory
            DESCRIPTION
                "LP-REI/REI-V Background Block Error"
            ::= { bFarEndLP-VT7DaysEty 9 }

        bFrLpVt7DaysESs  OBJECT-TYPE
            SYNTAX  Counter
            ACCESS  read-only
            STATUS  mandatory
            DESCRIPTION
                "LP-REI/REI-V Error Second"
            ::= { bFarEndLP-VT7DaysEty 10 }

        bFrLpVt7DaysBESs  OBJECT-TYPE
            SYNTAX  Counter
            ACCESS  read-only
            STATUS  mandatory
            DESCRIPTION
                "LP-REI/REI-V Background Error Second"
            ::= { bFarEndLP-VT7DaysEty 11 }

        bFrLpVt7DaysSESs  OBJECT-TYPE
            SYNTAX  Counter
            ACCESS  read-only
            STATUS  mandatory
            DESCRIPTION
                "LP-REI/REI-V Severly Error Second"
            ::= { bFarEndLP-VT7DaysEty 12 }

        bFrLpVt7DaysUASs  OBJECT-TYPE
            SYNTAX  Counter
            ACCESS  read-only
            STATUS  mandatory
            DESCRIPTION
                "LP-REI/REI-V Unavailable Second"
            ::= { bFarEndLP-VT7DaysEty 13 }

--
--  B155/622 LP-REI/REI-V Total Table
--
        bFarEndLP-VTTotalTab  OBJECT-TYPE
            SYNTAX  SEQUENCE OF  BFarEndLP-VTTotalEty
            ACCESS  not-accessible
            STATUS  mandatory
            DESCRIPTION
                "The B155/622 LP-REI/REI-V Total table."
            ::= { b155-622PerfDisplayTab 28 }

        bFarEndLP-VTTotalEty  OBJECT-TYPE
            SYNTAX  BFarEndLP-VTTotalEty
            ACCESS  not-accessible
            STATUS  mandatory
            DESCRIPTION
                "An entry in the B155/622 LP-REI/REI-V Total table."
            INDEX { bFrLpVtTotalUnit , bFrLpVtTotalPort ,
                    bFrLpVtTotalAug1Sts3 , bFrLpVtTotalVc3Sts1 ,
                    bFrLpVtTotalTU1xVtx }
            ::= { bFarEndLP-VTTotalTab 1 }

        BFarEndLP-VTTotalEty ::= SEQUENCE {
            bFrLpVtTotalUnit            UnitID,
            bFrLpVtTotalPort            PortID,
            bFrLpVtTotalAug1Sts3        Aug1Sts3Num,
            bFrLpVtTotalVc3Sts1         Vc3Sts1Num,
            bFrLpVtTotalTU1xVtx         TU1xVtxNum,
            bFrLpVtTotalEBs             Counter,
            bFrLpVtTotalBBEs            Counter,
            bFrLpVtTotalESs             Counter,
            bFrLpVtTotalBESs            Counter,
            bFrLpVtTotalSESs            Counter,
            bFrLpVtTotalUASs            Counter
        }

        bFrLpVtTotalUnit  OBJECT-TYPE
            SYNTAX  UnitID
            ACCESS  read-only
            STATUS  mandatory
            DESCRIPTION
            "unit 1 to 4."
            ::= { bFarEndLP-VTTotalEty 1 }

        bFrLpVtTotalPort  OBJECT-TYPE
            SYNTAX  PortID
            ACCESS  read-only
            STATUS  mandatory
            DESCRIPTION
                "PORT #1~#2"
            ::= { bFarEndLP-VTTotalEty 2 }

        bFrLpVtTotalAug1Sts3  OBJECT-TYPE
            SYNTAX  Aug1Sts3Num
            ACCESS  read-only
            STATUS  mandatory
            DESCRIPTION
                "AUG1/STS3 index"
            ::= { bFarEndLP-VTTotalEty 3 }

        bFrLpVtTotalVc3Sts1  OBJECT-TYPE
            SYNTAX  Vc3Sts1Num
            ACCESS  read-only
            STATUS  mandatory
            DESCRIPTION
                "VC3/STS1 index"
            ::= { bFarEndLP-VTTotalEty 4 }

        bFrLpVtTotalTU1xVtx  OBJECT-TYPE
            SYNTAX  TU1xVtxNum
            ACCESS  read-only
            STATUS  mandatory
            DESCRIPTION
                "VC1x/Vtx index"
            ::= { bFarEndLP-VTTotalEty 5 }

        bFrLpVtTotalEBs  OBJECT-TYPE
            SYNTAX  Counter
            ACCESS  read-only
            STATUS  mandatory
            DESCRIPTION
                "LP-REI/REI-V Error Block"
            ::= { bFarEndLP-VTTotalEty 6 }

        bFrLpVtTotalBBEs  OBJECT-TYPE
            SYNTAX  Counter
            ACCESS  read-only
            STATUS  mandatory
            DESCRIPTION
                "LP-REI/REI-V Background Block Error"
            ::= { bFarEndLP-VTTotalEty 7 }

        bFrLpVtTotalESs  OBJECT-TYPE
            SYNTAX  Counter
            ACCESS  read-only
            STATUS  mandatory
            DESCRIPTION
                "LP-REI/REI-V Error Second"
            ::= { bFarEndLP-VTTotalEty 8 }

        bFrLpVtTotalBESs  OBJECT-TYPE
            SYNTAX  Counter
            ACCESS  read-only
            STATUS  mandatory
            DESCRIPTION
                "LP-REI/REI-V Background Error Second"
            ::= { bFarEndLP-VTTotalEty 9 }

        bFrLpVtTotalSESs  OBJECT-TYPE
            SYNTAX  Counter
            ACCESS  read-only
            STATUS  mandatory
            DESCRIPTION
                "LP-REI/REI-V Severly Error Second"
            ::= { bFarEndLP-VTTotalEty 10 }

        bFrLpVtTotalUASs  OBJECT-TYPE
            SYNTAX  Counter
            ACCESS  read-only
            STATUS  mandatory
            DESCRIPTION
                "LP-REI/REI-V Unavailable Second"
            ::= { bFarEndLP-VTTotalEty 11 }

--
--   B155/622 Line/Section Performance Summary Hex Table
--
        bLnSecPerfSummaryHexTab  OBJECT-TYPE
            SYNTAX  SEQUENCE OF  BLnSecPerfSummaryHexEty
            ACCESS  not-accessible
            STATUS  mandatory
            DESCRIPTION
                "B155/622 Line/Section Performance Summary HEX Table "
            ::= { b155-622PerfDisplayTab 29 }

        bLnSecPerfSummaryHexEty OBJECT-TYPE
            SYNTAX  BLnSecPerfSummaryHexEty
            ACCESS  not-accessible
            STATUS  mandatory
            DESCRIPTION
                "An entry in the B155/622 Line/Section Performance summary hex table."
            INDEX { bLnSecSummUnitIdx , bLnSecSummPortIdx }
            ::= { bLnSecPerfSummaryHexTab 1 }

        BLnSecPerfSummaryHexEty ::= SEQUENCE  {
            bLnSecSummUnitIdx           UnitID,
            bLnSecSummPortIdx           PortNum,
            bLnSecSummSummary           OCTET STRING
        }

        bLnSecSummUnitIdx  OBJECT-TYPE
            SYNTAX  UnitID
            ACCESS  read-only
            STATUS  mandatory
            DESCRIPTION
                "unit index"
            ::= { bLnSecPerfSummaryHexEty  1 }

        bLnSecSummPortIdx  OBJECT-TYPE
            SYNTAX  PortNum
            ACCESS  read-only
            STATUS  mandatory
            DESCRIPTION
                "port index"
            ::= { bLnSecPerfSummaryHexEty  2 }

        bLnSecSummSummary  OBJECT-TYPE
            SYNTAX  OCTET STRING(SIZE(40))
            ACCESS  read-only
            STATUS  mandatory
            DESCRIPTION
                "Line/Section Perf Summary"
            ::= { bLnSecPerfSummaryHexEty  3 }

--
--   B155/622 HP/STS Performance Summary Hex Table
--
        bHpStsPerfSummaryHexTab  OBJECT-TYPE
            SYNTAX  SEQUENCE OF  BHpStsPerfSummaryHexEty
            ACCESS  not-accessible
            STATUS  mandatory
            DESCRIPTION
                "B155/622 HP/STS Performance Summary HEX Table "
            ::= { b155-622PerfDisplayTab 30 }

        bHpStsPerfSummaryHexEty OBJECT-TYPE
            SYNTAX  BHpStsPerfSummaryHexEty
            ACCESS  not-accessible
            STATUS  mandatory
            DESCRIPTION
                "An entry in the B155/622 HP/STS Performance summary hex table."
            INDEX { bHpStsSummUnitIdx , bHpStsSummPortIdx , bHpStsSummAug1Sts3Idx }
            ::= { bHpStsPerfSummaryHexTab 1 }

        BHpStsPerfSummaryHexEty ::= SEQUENCE  {
            bHpStsSummUnitIdx           UnitID,
            bHpStsSummPortIdx           PortNum,
            bHpStsSummAug1Sts3Idx       Aug1Sts3Num,
            bHpStsSummSummary           OCTET STRING
        }

        bHpStsSummUnitIdx  OBJECT-TYPE
            SYNTAX  UnitID
            ACCESS  read-only
            STATUS  mandatory
            DESCRIPTION
                "unit index"
            ::= { bHpStsPerfSummaryHexEty  1 }

        bHpStsSummPortIdx  OBJECT-TYPE
            SYNTAX  PortNum
            ACCESS  read-only
            STATUS  mandatory
            DESCRIPTION
                "port index"
            ::= { bHpStsPerfSummaryHexEty  2 }

        bHpStsSummAug1Sts3Idx  OBJECT-TYPE
            SYNTAX  Aug1Sts3Num
            ACCESS  read-only
            STATUS  mandatory
            DESCRIPTION
                "AUG1/STS3 index"
            ::= { bHpStsPerfSummaryHexEty  3 }

        bHpStsSummSummary  OBJECT-TYPE
            SYNTAX  OCTET STRING(SIZE(79))
            ACCESS  read-only
            STATUS  mandatory
            DESCRIPTION
                "HP/STS Perf Summary"
            ::= { bHpStsPerfSummaryHexEty  4 }

--
--   B155/622 LP/VT Performance Summary Hex Table
--
        bLpVtPerfSummaryHexTab  OBJECT-TYPE
            SYNTAX  SEQUENCE OF  BLpVtPerfSummaryHexEty
            ACCESS  not-accessible
            STATUS  mandatory
            DESCRIPTION
                "B155/622 LP/VT Performance Summary HEX Table "
            ::= { b155-622PerfDisplayTab 31 }

        bLpVtPerfSummaryHexEty OBJECT-TYPE
            SYNTAX  BLpVtPerfSummaryHexEty
            ACCESS  not-accessible
            STATUS  mandatory
            DESCRIPTION
                "An entry in the B155/622 LP/VT Performance summary hex table."
            INDEX { bLpVtSummUnitIdx , bLpVtSummPortIdx , bLpVtSummAug1Sts3Idx , bLpVtSummVc3Sts1Idx }
            ::= { bLpVtPerfSummaryHexTab 1 }

        BLpVtPerfSummaryHexEty ::= SEQUENCE  {
            bLpVtSummUnitIdx            UnitID,
            bLpVtSummPortIdx            PortNum,
            bLpVtSummAug1Sts3Idx        Aug1Sts3Num,
            bLpVtSummVc3Sts1Idx         Vc3Sts1Num,
            bLpVtSummSummary            OCTET STRING
        }

        bLpVtSummUnitIdx  OBJECT-TYPE
            SYNTAX  UnitID
            ACCESS  read-only
            STATUS  mandatory
            DESCRIPTION
                "unit index"
            ::= { bLpVtPerfSummaryHexEty  1 }

        bLpVtSummPortIdx  OBJECT-TYPE
            SYNTAX  PortNum
            ACCESS  read-only
            STATUS  mandatory
            DESCRIPTION
                "port index"
            ::= { bLpVtPerfSummaryHexEty  2 }

        bLpVtSummAug1Sts3Idx  OBJECT-TYPE
            SYNTAX  Aug1Sts3Num
            ACCESS  read-only
            STATUS  mandatory
            DESCRIPTION
                "AUG1/STS3 index"
            ::= { bLpVtPerfSummaryHexEty  3 }

        bLpVtSummVc3Sts1Idx  OBJECT-TYPE
            SYNTAX  Vc3Sts1Num
            ACCESS  read-only
            STATUS  mandatory
            DESCRIPTION
                "VC3/STS1 index"
            ::= { bLpVtPerfSummaryHexEty  4 }

        bLpVtSummSummary  OBJECT-TYPE
            SYNTAX  OCTET STRING(SIZE(729))
            ACCESS  read-only
            STATUS  mandatory
            DESCRIPTION
                "LP/VT Perf Summary"
            ::= { bLpVtPerfSummaryHexEty  5 }

--
--  B155/622 Command Control Table
--
        b155-622CmdControlTab  OBJECT-TYPE
            SYNTAX  SEQUENCE OF  B155-622CmdControlEty
            ACCESS  not-accessible
            STATUS  mandatory
            DESCRIPTION
                "B155/622 command control table "
            ::= { b155-622-card 16 }

        b155-622CmdControlEty  OBJECT-TYPE
            SYNTAX  B155-622CmdControlEty
            ACCESS  not-accessible
            STATUS  mandatory
            DESCRIPTION
                "B155/622 command control entry"
            INDEX { bCmdCtrlUnit }
            ::= { b155-622CmdControlTab 1 }

        B155-622CmdControlEty ::= SEQUENCE {
            bCmdCtrlUnit                UnitID,
            bCmdCtrlReset               INTEGER,
            bCmdCtrlLoadDefault         INTEGER,
            bCmdCtrlLoopbackTimer       INTEGER
        }

        bCmdCtrlUnit  OBJECT-TYPE
            SYNTAX  UnitID
            ACCESS  read-only
            STATUS  mandatory
            DESCRIPTION
            "unit 1 to 4."
            ::= { b155-622CmdControlEty 1 }

        bCmdCtrlReset  OBJECT-TYPE
            SYNTAX  INTEGER {
                    no(1),
                    warm-reset(2),
                    cold-reset(3)
                }
            ACCESS  read-write
            STATUS  mandatory
            DESCRIPTION
                "Unit Reset"
            ::= { b155-622CmdControlEty 2 }

        bCmdCtrlLoadDefault  OBJECT-TYPE
            SYNTAX  INTEGER {
                    no(1),
                    load-default(2)
                }
            ACCESS  read-write
            STATUS  mandatory
            DESCRIPTION
                "Unit load default"
            ::= { b155-622CmdControlEty 3 }

        bCmdCtrlLoopbackTimer  OBJECT-TYPE
            SYNTAX  INTEGER (0..99999)
            ACCESS  read-write
            STATUS  mandatory
            DESCRIPTION
                "Loopback timer"
            ::= { b155-622CmdControlEty 4 }

--
--   Diagnostics Setup and Monitor Table
--

        b155-622DiagnosticsTab OBJECT-TYPE
            SYNTAX  SEQUENCE OF B155-622DiagnosticsEty
            ACCESS  not-accessible
            STATUS  mandatory
            DESCRIPTION
                "Diagnostics Table."
            ::= { b155-622-card 17 }

        b155-622DiagnosticsEty OBJECT-TYPE
            SYNTAX  B155-622DiagnosticsEty
            ACCESS  not-accessible
            STATUS  mandatory
            DESCRIPTION
                "Diagnostics Entry."
            INDEX { bDiagUnit }
            ::= { b155-622DiagnosticsTab 1 }

        B155-622DiagnosticsEty ::= SEQUENCE {
            bDiagUnit                   UnitID,
            bDiagPort                   INTEGER,
            bDiagAUG1STS3               Aug1Sts3Num,
            bDiagVC4VC3-STS3STS1        INTEGER,
            bDiagBERTOnOff              INTEGER,
            bDiagInsert-Error           INTEGER,
            bDiagSyncStatus             INTEGER,
            bDiagElapsed-Seconds        INTEGER,
            bDiagBitErrorCount          INTEGER,
            bDiagBER                    DisplayString (SIZE (0..25) ),
            bDiagES                     INTEGER,
            bDiagESR                    DisplayString (SIZE (0..25) ),
            bDiagSES                    INTEGER,
            bDiagSESR                   DisplayString (SIZE (0..25) ),
            bDiagUAS                    INTEGER,
            bDiagInsert-Error-Count     INTEGER
        }
        bDiagUnit  OBJECT-TYPE
            SYNTAX  UnitID
            ACCESS  read-only
            STATUS  mandatory
            DESCRIPTION
            "unit 1 to 4."
            ::= { b155-622DiagnosticsEty 1 }

        bDiagPort  OBJECT-TYPE
            SYNTAX  INTEGER{
                    port1(1),
                    port1-Full(2),
                    port2(3),
                    port2-Full(4)
                }
            ACCESS  read-write
            STATUS  mandatory
            DESCRIPTION
                "Port#1,Port#1 Full mode, Port#2,Port#2 Full mode,"
            ::= { b155-622DiagnosticsEty 2 }

        bDiagAUG1STS3  OBJECT-TYPE
            SYNTAX  Aug1Sts3Num
            ACCESS  read-write
            STATUS  mandatory
            DESCRIPTION
                "aug1/STS3#1~4"
            ::= { b155-622DiagnosticsEty 3 }

        bDiagVC4VC3-STS3STS1  OBJECT-TYPE
            SYNTAX  INTEGER{
                    vc4STS3-Full(1),
                    vc3STS1-Full(2),
                    vc3STS1-1(3),
                    vc3STS1-2(4),
                    vc3STS1-3(5),
                    not-available(100)
                }
            ACCESS  read-write
            STATUS  mandatory
            DESCRIPTION
                ""
            ::= { b155-622DiagnosticsEty 4 }

        bDiagBERTOnOff  OBJECT-TYPE
            SYNTAX  INTEGER{
                    off(1),
                    on(2),
                    reset(3)
                }
            ACCESS  read-write
            STATUS  mandatory
            DESCRIPTION
                "Pattern OFF on PRBS"
            ::= { b155-622DiagnosticsEty 5 }

        bDiagInsert-Error  OBJECT-TYPE
            SYNTAX  INTEGER{
                    none(1),
                    insert(2)
                }
            ACCESS  read-write
            STATUS  mandatory
            DESCRIPTION
                "Insert Errors"
            ::= { b155-622DiagnosticsEty 6 }

        bDiagSyncStatus  OBJECT-TYPE
            SYNTAX  INTEGER{
                    unsync(1),
                    sync(2)
                }
            ACCESS  read-only
            STATUS  mandatory
            DESCRIPTION
                "Unsync and sync"
            ::= { b155-622DiagnosticsEty 7 }

        bDiagElapsed-Seconds  OBJECT-TYPE
            SYNTAX  INTEGER
            ACCESS  read-only
            STATUS  mandatory
            DESCRIPTION
                "Elapsed Seconds"
            ::= { b155-622DiagnosticsEty 8 }

        bDiagBitErrorCount  OBJECT-TYPE
            SYNTAX  INTEGER
            ACCESS  read-only
            STATUS  mandatory
            DESCRIPTION
                "Bit Error count"
            ::= { b155-622DiagnosticsEty 9 }

        bDiagBER  OBJECT-TYPE
            SYNTAX  DisplayString (SIZE (0..25) )
            ACCESS  read-only
            STATUS  mandatory
            DESCRIPTION
                "BER"
            ::= { b155-622DiagnosticsEty 10 }

        bDiagES  OBJECT-TYPE
            SYNTAX  INTEGER
            ACCESS  read-only
            STATUS  mandatory
            DESCRIPTION
                "Error seconds"
            ::= { b155-622DiagnosticsEty 11 }

        bDiagESR  OBJECT-TYPE
            SYNTAX  DisplayString (SIZE (0..25) )
            ACCESS  read-only
            STATUS  mandatory
            DESCRIPTION
                "Error seconds ratio"
            ::= { b155-622DiagnosticsEty 12 }

        bDiagSES  OBJECT-TYPE
            SYNTAX  INTEGER
            ACCESS  read-only
            STATUS  mandatory
            DESCRIPTION
                "Severely error second"
            ::= { b155-622DiagnosticsEty 13 }

        bDiagSESR  OBJECT-TYPE
            SYNTAX  DisplayString (SIZE (0..25) )
            ACCESS  read-only
            STATUS  mandatory
            DESCRIPTION
                "Severely error second ratio"
            ::= { b155-622DiagnosticsEty 14 }

        bDiagUAS  OBJECT-TYPE
            SYNTAX  INTEGER
            ACCESS  read-only
            STATUS  mandatory
            DESCRIPTION
                "Unavailable Seconds"
            ::= { b155-622DiagnosticsEty 15 }

        bDiagInsert-Error-Count  OBJECT-TYPE
            SYNTAX  INTEGER
            ACCESS  read-only
            STATUS  mandatory
            DESCRIPTION
                "Inserted Error Count(s)"
            ::= { b155-622DiagnosticsEty 16 }


--
--  B155/622 Loopback Table
--
        b155-622LoopbackTab  OBJECT-TYPE
            SYNTAX  SEQUENCE OF  B155-622LoopbackEty
            ACCESS  not-accessible
            STATUS  mandatory
            DESCRIPTION
                "B155/622 Loopback table"
            ::= { b155-622-card 18 }

        b155-622LoopbackEty  OBJECT-TYPE
            SYNTAX  B155-622LoopbackEty
            ACCESS  not-accessible
            STATUS  mandatory
            DESCRIPTION
                "An entry in the B155/622 Loopback table."
            INDEX { bLoopbackUnit , bLoopbackPort }
            ::= { b155-622LoopbackTab 1 }

        B155-622LoopbackEty ::= SEQUENCE  {
            bLoopbackUnit               UnitID,
            bLoopbackPort               PortID,
            bLoopbackType               INTEGER
        }

        bLoopbackUnit  OBJECT-TYPE
            SYNTAX  UnitID
            ACCESS  read-only
            STATUS  mandatory
            DESCRIPTION
            "unit 1 to 4."
            ::= { b155-622LoopbackEty  1 }

        bLoopbackPort  OBJECT-TYPE
            SYNTAX  PortID
            ACCESS  read-only
            STATUS  mandatory
            DESCRIPTION
                "PORT #1~#2"
            ::= { b155-622LoopbackEty  2 }

        bLoopbackType  OBJECT-TYPE
            SYNTAX  INTEGER {
                    no-loopback(1),
                    local-loopback(2),
                    payload-loopback(3),
                    line-loopback(4)
                }
            ACCESS  read-write
            STATUS  mandatory
            DESCRIPTION
                "Loopback type"
            ::= { b155-622LoopbackEty  3 }

--
--  B155/622 XC Display Table
--
        b155-622XcDisplayTab  OBJECT-TYPE
            SYNTAX  SEQUENCE OF  B155-622XcDisplayEty
            ACCESS  not-accessible
            STATUS  mandatory
            DESCRIPTION
                "B155/622 xc display table "
            ::= { b155-622-card 19 }

        b155-622XcDisplayEty  OBJECT-TYPE
            SYNTAX  B155-622XcDisplayEty
            ACCESS  not-accessible
            STATUS  mandatory
            DESCRIPTION
                "B155/622 xc display entry"
            INDEX { bXcDispMap , bXcDispUnit ,
                    bXcDispPort , bXcDispAug1Sts3 ,
                    bXcDispVc3Sts1 , bXcDispVc1xVtx }
            ::= { b155-622XcDisplayTab 1 }

        B155-622XcDisplayEty ::= SEQUENCE {
            bXcDispMap                  XcMap,
            bXcDispUnit                 UnitID,
            bXcDispPort                 PortID,
            bXcDispAug1Sts3             Aug1Sts3Num,
            bXcDispVc3Sts1              Vc3Sts1Num,
            bXcDispVc1xVtx              Vc1xVtxNum,
            bXcDispSrcType              NewXcModel,
            bXcDispSrcSlot              XcSlot,
            bXcDispSrcPort              PortID,
            bXcDispSrcChannel           ChannelNum,
            bXcDispSrcAug1Sts3Path      Aug1Sts3Num,
            bXcDispSrcVc3Sts1Path       Vc3Sts1Num,
            bXcDispSrcVc1xVtxPath       Vc1xVtxNum,
            bXcDispXcGranularity        INTEGER,
            bXcDispXcType               XcType
        }

        bXcDispMap  OBJECT-TYPE
            SYNTAX  XcMap
            ACCESS  read-only
            STATUS  mandatory
            DESCRIPTION
                "xc map index"
            ::= { b155-622XcDisplayEty 1 }

        bXcDispUnit  OBJECT-TYPE
            SYNTAX  UnitID
            ACCESS  read-only
            STATUS  mandatory
            DESCRIPTION
            "unit 1 to 4."
            ::= { b155-622XcDisplayEty 2 }

        bXcDispPort  OBJECT-TYPE
            SYNTAX  PortID
            ACCESS  read-only
            STATUS  mandatory
            DESCRIPTION
                "PORT #1~#2"
            ::= { b155-622XcDisplayEty 3 }

        bXcDispAug1Sts3  OBJECT-TYPE
            SYNTAX  Aug1Sts3Num
            ACCESS  read-only
            STATUS  mandatory
            DESCRIPTION
                "AUG1/STS3 index"
            ::= { b155-622XcDisplayEty 4 }

        bXcDispVc3Sts1  OBJECT-TYPE
            SYNTAX  Vc3Sts1Num
            ACCESS  read-only
            STATUS  mandatory
            DESCRIPTION
                "VC3/STS1 index"
            ::= { b155-622XcDisplayEty 5 }

        bXcDispVc1xVtx  OBJECT-TYPE
            SYNTAX  Vc1xVtxNum
            ACCESS  read-only
            STATUS  mandatory
            DESCRIPTION
                "VC1x/VTx index"
            ::= { b155-622XcDisplayEty 6 }

        bXcDispSrcType  OBJECT-TYPE
            SYNTAX  NewXcModel
            ACCESS  read-only
            STATUS  mandatory
            DESCRIPTION
                " Xc src Unit Type"
            ::= { b155-622XcDisplayEty 7 }

        bXcDispSrcSlot  OBJECT-TYPE
            SYNTAX  XcSlot
            ACCESS  read-only
            STATUS  mandatory
            DESCRIPTION
                "Xc src Unit "
            ::= { b155-622XcDisplayEty 8 }

        bXcDispSrcPort  OBJECT-TYPE
            SYNTAX  PortID
            ACCESS  read-only
            STATUS  mandatory
            DESCRIPTION
                "Xc src port "
            ::= { b155-622XcDisplayEty 9 }

        bXcDispSrcChannel  OBJECT-TYPE
            SYNTAX  ChannelNum
            ACCESS  read-only
            STATUS  mandatory
            DESCRIPTION
                "Xc src channel "
            ::= { b155-622XcDisplayEty 10 }

        bXcDispSrcAug1Sts3Path  OBJECT-TYPE
            SYNTAX  Aug1Sts3Num
            ACCESS  read-only
            STATUS  mandatory
            DESCRIPTION
                "Xc src AUG1/STS3 path"
            ::= { b155-622XcDisplayEty 11 }

        bXcDispSrcVc3Sts1Path  OBJECT-TYPE
            SYNTAX  Vc3Sts1Num
            ACCESS  read-only
            STATUS  mandatory
            DESCRIPTION
                "Xc src VC3/STS1 path"
            ::= { b155-622XcDisplayEty 12 }

        bXcDispSrcVc1xVtxPath  OBJECT-TYPE
            SYNTAX  Vc1xVtxNum
            ACCESS  read-only
            STATUS  mandatory
            DESCRIPTION
                "Xc src VC1x/VTx path"
            ::= { b155-622XcDisplayEty 13 }

        bXcDispXcGranularity  OBJECT-TYPE
            SYNTAX  INTEGER {
                    tu3(2),
                    au3-sts1(3),
                    tu11-vt15(4),
                    tu12-vt2(5),
                    vc4-sts3c(6),
                    not-available(100)
                }
            ACCESS  read-only
            STATUS  mandatory
            DESCRIPTION
                "Xc granularity"
            ::= { b155-622XcDisplayEty 14 }

        bXcDispXcType  OBJECT-TYPE
            SYNTAX  XcType
            ACCESS  read-only
            STATUS  mandatory
            DESCRIPTION
                "Xc type"
            ::= { b155-622XcDisplayEty 15 }

--
--  B155/622 LED Status Table
--
        b155-622LedStatusTab  OBJECT-TYPE
            SYNTAX  SEQUENCE OF  B155-622LedStatusEty
            ACCESS  not-accessible
            STATUS  mandatory
            DESCRIPTION
                "B155/622 LED status table "
            ::= { b155-622-card 20 }

        b155-622LedStatusEty  OBJECT-TYPE
            SYNTAX  B155-622LedStatusEty
            ACCESS  not-accessible
            STATUS  mandatory
            DESCRIPTION
                "B155/622 LED status entry"
            INDEX { bLedStatusUnit }
            ::= { b155-622LedStatusTab 1 }

        B155-622LedStatusEty ::= SEQUENCE {
            bLedStatusUnit              UnitID,
            bLedStatusActiveLED         LedStatusType,
            bLedStatusTestLED           LedStatusType,
            bLedStatusAlmLED            LedStatusType,
            bLedStatusP1LED             LedStatusType,
            bLedStatusP2LED             LedStatusType
        }

        bLedStatusUnit  OBJECT-TYPE
            SYNTAX  UnitID
            ACCESS  read-only
            STATUS  mandatory
            DESCRIPTION
            "unit 1 to 4."
            ::= { b155-622LedStatusEty 1 }

        bLedStatusActiveLED  OBJECT-TYPE
            SYNTAX  LedStatusType
            ACCESS  read-only
            STATUS  mandatory
            DESCRIPTION
                "Active LED status"
            ::= { b155-622LedStatusEty 2 }

        bLedStatusTestLED  OBJECT-TYPE
            SYNTAX  LedStatusType
            ACCESS  read-only
            STATUS  mandatory
            DESCRIPTION
                "Test LED status"
            ::= { b155-622LedStatusEty 3 }

        bLedStatusAlmLED  OBJECT-TYPE
            SYNTAX  LedStatusType
            ACCESS  read-only
            STATUS  mandatory
            DESCRIPTION
                "Alm LED status"
            ::= { b155-622LedStatusEty 4 }

        bLedStatusP1LED  OBJECT-TYPE
            SYNTAX  LedStatusType
            ACCESS  read-only
            STATUS  mandatory
            DESCRIPTION
                "Port 1 LED status"
            ::= { b155-622LedStatusEty 5 }

        bLedStatusP2LED  OBJECT-TYPE
            SYNTAX  LedStatusType
            ACCESS  read-only
            STATUS  mandatory
            DESCRIPTION
                "Port 2 LED status"
            ::= { b155-622LedStatusEty 6 }

--
--  B155/622 SNCP/UPSR APS Table
--
        b155-622SncpApsTab  OBJECT-TYPE
            SYNTAX  SEQUENCE OF  B155-622SncpApsEty
            ACCESS  not-accessible
            STATUS  mandatory
            DESCRIPTION
                "B155/622 SNCP/UPSR APS table "
            ::= { b155-622-card 21 }

        b155-622SncpApsEty  OBJECT-TYPE
            SYNTAX  B155-622SncpApsEty
            ACCESS  not-accessible
            STATUS  mandatory
            DESCRIPTION
                "B155/622 SNCP/UPSR APS entry"
            INDEX { bSncpUnit ,
                    bSncpPort , bSncpAug1Sts3 ,
                    bSncpVc3Sts1 , bSncpTU1xVtx }
            ::= { b155-622SncpApsTab 1 }

        B155-622SncpApsEty ::= SEQUENCE {
            bSncpUnit                   UnitID,
            bSncpPort                   PortID,
            bSncpAug1Sts3               Aug1Sts3Num,
            bSncpVc3Sts1                Vc3Sts1Num,
            bSncpTU1xVtx                TU1xVtxNum,
            bSncpCurrentPathSlot        XcSlot,
            bSncpCurrentPathPort        PortID,
            bSncpPrimaryPathSlot        XcSlot,
            bSncpPrimaryPathPort        PortID,
            bSncpPPType                 XcType,
            bSncpCmd                    SncpUserCmd
        }

        bSncpUnit  OBJECT-TYPE
            SYNTAX  UnitID
            ACCESS  read-only
            STATUS  mandatory
            DESCRIPTION
            "unit 1 to 4."
            ::= { b155-622SncpApsEty 1 }

        bSncpPort  OBJECT-TYPE
            SYNTAX  PortID
            ACCESS  read-only
            STATUS  mandatory
            DESCRIPTION
                "PORT #1~#2"
            ::= { b155-622SncpApsEty 2 }

        bSncpAug1Sts3  OBJECT-TYPE
            SYNTAX  Aug1Sts3Num
            ACCESS  read-only
            STATUS  mandatory
            DESCRIPTION
                "AUG1/STS3 index"
            ::= { b155-622SncpApsEty 3 }

        bSncpVc3Sts1  OBJECT-TYPE
            SYNTAX  Vc3Sts1Num
            ACCESS  read-only
            STATUS  mandatory
            DESCRIPTION
                "VC3/STS1 index"
            ::= { b155-622SncpApsEty 4 }

        bSncpTU1xVtx  OBJECT-TYPE
            SYNTAX  TU1xVtxNum
            ACCESS  read-only
            STATUS  mandatory
            DESCRIPTION
                "VC1x/VTx index"
            ::= { b155-622SncpApsEty 5 }

        bSncpCurrentPathSlot  OBJECT-TYPE
            SYNTAX  XcSlot
            ACCESS  read-only
            STATUS  mandatory
            DESCRIPTION
                "SNCP/UPSR current path"
            ::= { b155-622SncpApsEty 6 }

        bSncpCurrentPathPort  OBJECT-TYPE
            SYNTAX  PortID
            ACCESS  read-only
            STATUS  mandatory
            DESCRIPTION
                "SNCP/UPSR current path"
            ::= { b155-622SncpApsEty 7 }

        bSncpPrimaryPathSlot  OBJECT-TYPE
            SYNTAX  XcSlot
            ACCESS  read-only
            STATUS  mandatory
            DESCRIPTION
                "SNCP/UPSR primary path"
            ::= { b155-622SncpApsEty 8 }

        bSncpPrimaryPathPort  OBJECT-TYPE
            SYNTAX  PortID
            ACCESS  read-only
            STATUS  mandatory
            DESCRIPTION
                "SNCP/UPSR primary path"
            ::= { b155-622SncpApsEty 9 }

        bSncpPPType  OBJECT-TYPE
            SYNTAX  XcType
            ACCESS  read-only
            STATUS  mandatory
            DESCRIPTION
                "SNCP/UPSR path protection type"
            ::= { b155-622SncpApsEty 10 }

        bSncpCmd  OBJECT-TYPE
            SYNTAX  SncpUserCmd
            ACCESS  read-write
            STATUS  mandatory
            DESCRIPTION
                "SNCP/UPSR APS command"
            ::= { b155-622SncpApsEty 11 }

--
--  B155/622 ALS/APSD Table
--
        b155-622AlsTable  OBJECT-TYPE
            SYNTAX  SEQUENCE OF  B155-622AlsEntry
            ACCESS  not-accessible
            STATUS  mandatory
            DESCRIPTION
                "B155/622 ALS/APSD table "
            ::= { b155-622-card 22 }

        b155-622AlsEntry  OBJECT-TYPE
            SYNTAX  B155-622AlsEntry
            ACCESS  not-accessible
            STATUS  mandatory
            DESCRIPTION
                "B155/622 ALS/APSD entry"
            INDEX { bAlsUnit }
            ::= { b155-622AlsTable 1 }

        B155-622AlsEntry ::= SEQUENCE {
            bAlsUnit                    UnitID,
            bAlsEnable                  INTEGER,
            bAlsPulseRepetitionTime     INTEGER,
            bAlsPort1ManualRestart      INTEGER,
            bAlsPort2ManualRestart      INTEGER
        }

        bAlsUnit  OBJECT-TYPE
            SYNTAX  UnitID
            ACCESS  read-only
            STATUS  mandatory
            DESCRIPTION
            "unit 1 to 4."
            ::= { b155-622AlsEntry 1 }

        bAlsEnable  OBJECT-TYPE
            SYNTAX  INTEGER {
                    off(1),
                    on(2)
                }
            ACCESS  read-write
            STATUS  mandatory
            DESCRIPTION
                "APSD enable"
            ::= { b155-622AlsEntry 2 }

        bAlsPulseRepetitionTime  OBJECT-TYPE
            SYNTAX  INTEGER (60..300)
            ACCESS  read-write
            STATUS  mandatory
            DESCRIPTION
                "ALS/APSD pulse repetition time for automatic restart(sec)"
            ::= { b155-622AlsEntry 3 }

        bAlsPort1ManualRestart  OBJECT-TYPE
            SYNTAX  INTEGER {
                    off(1),
                    start(2)
                }
            ACCESS  read-write
            STATUS  mandatory
            DESCRIPTION
                "ALS Port1 manual restart"
            ::= { b155-622AlsEntry 4 }

        bAlsPort2ManualRestart  OBJECT-TYPE
            SYNTAX  INTEGER {
                    off(1),
                    start(2)
                }
            ACCESS  read-write
            STATUS  mandatory
            DESCRIPTION
                "ALS Port2 manual restart"
            ::= { b155-622AlsEntry 5 }

--
--  B155/622 Summary Hex Table
--
        b155-622XcSummaryHexTab  OBJECT-TYPE
            SYNTAX  SEQUENCE OF  B155-622XcSummaryHexEty
            ACCESS  not-accessible
            STATUS  mandatory
            DESCRIPTION
                "B155/622 Xc Summary HEX Table "
            ::= { b155-622-card 23 }

        b155-622XcSummaryHexEty OBJECT-TYPE
            SYNTAX  B155-622XcSummaryHexEty
            ACCESS  not-accessible
            STATUS  mandatory
            DESCRIPTION
                "An entry in the B155/622 xc summary hex table."
            INDEX { bXcSummMapIndex , bXcSummUnitIndex , bXcSummPortIndex ,
                    bXcSummAug1Sts3Index }
            ::= { b155-622XcSummaryHexTab 1 }

        B155-622XcSummaryHexEty ::= SEQUENCE  {
            bXcSummMapIndex             XcMap,
            bXcSummUnitIndex            UnitID,
            bXcSummPortIndex            PortID,
            bXcSummAug1Sts3Index        Aug1Sts3Num,
            bXcSummSummary              OCTET STRING
        }

        bXcSummMapIndex  OBJECT-TYPE
            SYNTAX  XcMap
            ACCESS  read-only
            STATUS  mandatory
            DESCRIPTION
                "xc map index"
            ::= { b155-622XcSummaryHexEty  1 }

        bXcSummUnitIndex  OBJECT-TYPE
            SYNTAX  UnitID
            ACCESS  read-only
            STATUS  mandatory
            DESCRIPTION
                "Optical unit"
            ::= { b155-622XcSummaryHexEty  2 }

        bXcSummPortIndex  OBJECT-TYPE
            SYNTAX  PortID
            ACCESS  read-only
            STATUS  mandatory
            DESCRIPTION
                "Optical port index"
            ::= { b155-622XcSummaryHexEty  3 }

        bXcSummAug1Sts3Index  OBJECT-TYPE
            SYNTAX  Aug1Sts3Num
            ACCESS  read-only
            STATUS  mandatory
            DESCRIPTION
                "Optical Aug1/sts3 path index"
            ::= { b155-622XcSummaryHexEty  4 }

        bXcSummSummary  OBJECT-TYPE
            SYNTAX  OCTET STRING(SIZE(15))
            ACCESS  read-only
            STATUS  mandatory
            DESCRIPTION
                "B155/622 XC Summary"
            ::= { b155-622XcSummaryHexEty  5 }

--
--  B155/622 Mode Table
--
        b155-622ModeTab  OBJECT-TYPE
            SYNTAX  SEQUENCE OF  B155-622ModeEty
            ACCESS  not-accessible
            STATUS  mandatory
            DESCRIPTION
                "B155/622 Mode Table "
            ::= { b155-622-card 24 }

        b155-622ModeEty OBJECT-TYPE
            SYNTAX  B155-622ModeEty
            ACCESS  not-accessible
            STATUS  mandatory
            DESCRIPTION
                "An entry in the B155/622 Mode table."
            INDEX { bModeUnitIndex }
            ::= { b155-622ModeTab 1 }

        B155-622ModeEty ::= SEQUENCE  {
            bModeUnitIndex              UnitID,
            bModeAdmMode                INTEGER,
            bModeMspWtrTimer            INTEGER
        }

        bModeUnitIndex  OBJECT-TYPE
            SYNTAX  UnitID
            ACCESS  read-only
            STATUS  mandatory
            DESCRIPTION
                "unit index"
            ::= { b155-622ModeEty  1 }

        bModeAdmMode  OBJECT-TYPE
            SYNTAX  INTEGER {
                    off(1),
                    adm-sncp(2)
                }
            ACCESS  read-only
            STATUS  mandatory
            DESCRIPTION
                "ADM Mode"
            ::= { b155-622ModeEty  2 }

        bModeMspWtrTimer  OBJECT-TYPE
            SYNTAX  INTEGER (3..900)
            ACCESS  read-write
            STATUS  mandatory
            DESCRIPTION
                "MSP 1+1 WTR Timer"
            ::= { b155-622ModeEty  3 }

--
--  B155/622 Customer Information Table
--
        b155-622CustomerInfoTab  OBJECT-TYPE
            SYNTAX  SEQUENCE OF  B155-622CustomerInfoEty
            ACCESS  not-accessible
            STATUS  mandatory
            DESCRIPTION
                "B155/622 Mode Table "
            ::= { b155-622-card 25 }

        b155-622CustomerInfoEty OBJECT-TYPE
            SYNTAX  B155-622CustomerInfoEty
            ACCESS  not-accessible
            STATUS  mandatory
            DESCRIPTION
                "An entry in the B155/622 Custimer information table."
            INDEX { bCusInfoUnitIndex , bCusInfoPortIndex }
            ::= { b155-622CustomerInfoTab 1 }

        B155-622CustomerInfoEty ::= SEQUENCE  {
            bCusInfoUnitIndex           UnitID,
            bCusInfoPortIndex           PortID,
            bCusInfoString              DisplayString (SIZE (1..60))
        }

        bCusInfoUnitIndex  OBJECT-TYPE
            SYNTAX  UnitID
            ACCESS  read-only
            STATUS  mandatory
            DESCRIPTION
                "unit index"
            ::= { b155-622CustomerInfoEty 1 }

        bCusInfoPortIndex  OBJECT-TYPE
            SYNTAX  PortID
            ACCESS  read-only
            STATUS  mandatory
            DESCRIPTION
                "port index"
            ::= { b155-622CustomerInfoEty 2 }

        bCusInfoString  OBJECT-TYPE
            SYNTAX  DisplayString (SIZE (1..60))
            ACCESS  read-write
            STATUS  mandatory
            DESCRIPTION
                "Customer Information String"
            ::= { b155-622CustomerInfoEty 3 }

--
-- B155/622 TPSG Protection Table
--
        b155-622TPSGProtectTab  OBJECT-TYPE
            SYNTAX  SEQUENCE OF B155-622TPSGProtectEty
            ACCESS  not-accessible
            STATUS  mandatory
            DESCRIPTION
                "TPSG protection table"
            ::= { b155-622-card 26 }

        b155-622TPSGProtectEty  OBJECT-TYPE
            SYNTAX  B155-622TPSGProtectEty
            ACCESS  not-accessible
            STATUS  mandatory
            DESCRIPTION
                "An entry in the TPSG protection table"
            INDEX { bTPSGProtectUnit }
            ::= { b155-622TPSGProtectTab 1 }

        B155-622TPSGProtectEty ::= SEQUENCE {
            bTPSGProtectUnit            UnitID,
            bTPSGProtectActive          INTEGER,
            bTPSGProtectStatus          INTEGER
        }

        bTPSGProtectUnit  OBJECT-TYPE
            SYNTAX  UnitID
            ACCESS  read-only
            STATUS  mandatory
            DESCRIPTION
            "unit 1 to 4."
            ::= { b155-622TPSGProtectEty 1 }

        bTPSGProtectActive  OBJECT-TYPE
            SYNTAX  INTEGER{
                    none(0),
                    standby(1),
                    working(2)
                }
            ACCESS  read-only
            STATUS  mandatory
            DESCRIPTION
                "TPSG active working/standby"
            ::= { b155-622TPSGProtectEty 2 }

        bTPSGProtectStatus  OBJECT-TYPE
            SYNTAX  INTEGER{
                    sync-failed(1),
                    sync-ok(2),
                    start-sync(3),
                    during-sync(4),
                    update-failed(5),
                    unsync(6)
                }
            ACCESS  read-only
            STATUS  mandatory
            DESCRIPTION
                "TPSG Status"
            ::= { b155-622TPSGProtectEty 3 }
--2011-3-17 elvis below
--
--  New B155/622 XC Display Table
--
        new-b155-622XcDisplayTab  OBJECT-TYPE
            SYNTAX  SEQUENCE OF  NewB155-622XcDisplayEty
            ACCESS  not-accessible
            STATUS  mandatory
            DESCRIPTION
                "B155/622 xc display table "
            ::= { b155-622-card 27 }

        new-b155-622XcDisplayEty  OBJECT-TYPE
            SYNTAX  NewB155-622XcDisplayEty
            ACCESS  not-accessible
            STATUS  mandatory
            DESCRIPTION
                "B155/622 xc display entry"
            INDEX { new-bXcDispMap , new-bXcDispUnit ,
                    new-bXcDispPort , new-bXcDispAug1Sts3 ,
                    new-bXcDispVc3Sts1 , new-bXcDispVc1xVtx }
            ::= { new-b155-622XcDisplayTab 1 }

        NewB155-622XcDisplayEty ::= SEQUENCE {
            new-bXcDispMap              XcMap,
            new-bXcDispUnit             UnitID,
            new-bXcDispPort             PortID,
            new-bXcDispAug1Sts3         Aug1Sts3Num,
            new-bXcDispVc3Sts1          Vc3Sts1Num,
            new-bXcDispVc1xVtx          Vc1xVtxNum,
            new-bXcDispPriType          NewXcModel,
            new-bXcDispPriSlot          XcSlot,
            new-bXcDispPriPort          PortID,
            new-bXcDispPriChannel       ChannelNum,
            new-bXcDispPriAug1Sts3Path  Aug1Sts3Num,
            new-bXcDispPriVc3Sts1Path   Vc3Sts1Num,
            new-bXcDispPriVc1xVtxPath   Vc1xVtxNum,
            new-bXcDispXcGranularity    INTEGER,
            new-bXcDispXcType           XcType,
            new-bXcDispSecType          NewXcModel,
            new-bXcDispSecSlot          XcSlot,
            new-bXcDispSecPort          PortID,
            new-bXcDispSecChannel       ChannelNum,
            new-bXcDispSecAug1Sts3Path  Aug1Sts3Num,
            new-bXcDispSecVc3Sts1Path   Vc3Sts1Num,
            new-bXcDispSecVc1xVtxPath   Vc1xVtxNum
        }

        new-bXcDispMap  OBJECT-TYPE
            SYNTAX  XcMap
            ACCESS  read-only
            STATUS  mandatory
            DESCRIPTION
                "xc map index"
            ::= { new-b155-622XcDisplayEty 1 }

        new-bXcDispUnit  OBJECT-TYPE
            SYNTAX  UnitID
            ACCESS  read-only
            STATUS  mandatory
            DESCRIPTION
                "unit 1 to 8, total 8 units."
            ::= { new-b155-622XcDisplayEty 2 }

        new-bXcDispPort  OBJECT-TYPE
            SYNTAX  PortID
            ACCESS  read-only
            STATUS  mandatory
            DESCRIPTION
                "PORT #1~#2"
            ::= { new-b155-622XcDisplayEty 3 }

        new-bXcDispAug1Sts3  OBJECT-TYPE
            SYNTAX  Aug1Sts3Num
            ACCESS  read-only
            STATUS  mandatory
            DESCRIPTION
                "AUG1/STS3 index"
            ::= { new-b155-622XcDisplayEty 4 }

        new-bXcDispVc3Sts1  OBJECT-TYPE
            SYNTAX  Vc3Sts1Num
            ACCESS  read-only
            STATUS  mandatory
            DESCRIPTION
                "VC3/STS1 index"
            ::= { new-b155-622XcDisplayEty 5 }

        new-bXcDispVc1xVtx  OBJECT-TYPE
            SYNTAX  Vc1xVtxNum
            ACCESS  read-only
            STATUS  mandatory
            DESCRIPTION
                "VC1x/VTx index"
            ::= { new-b155-622XcDisplayEty 6 }

        new-bXcDispPriType  OBJECT-TYPE
            SYNTAX  NewXcModel
            ACCESS  read-only
            STATUS  mandatory
            DESCRIPTION
                " Xc Primary Unit Type"
            ::= { new-b155-622XcDisplayEty 7 }

        new-bXcDispPriSlot  OBJECT-TYPE
            SYNTAX  XcSlot
            ACCESS  read-only
            STATUS  mandatory
            DESCRIPTION
                "Xc Primary Unit "
            ::= { new-b155-622XcDisplayEty 8 }

        new-bXcDispPriPort  OBJECT-TYPE
            SYNTAX  PortID
            ACCESS  read-only
            STATUS  mandatory
            DESCRIPTION
                "Xc Primary port "
            ::= { new-b155-622XcDisplayEty 9 }

        new-bXcDispPriChannel  OBJECT-TYPE
            SYNTAX  ChannelNum
            ACCESS  read-only
            STATUS  mandatory
            DESCRIPTION
                "Xc Primary channel "
            ::= { new-b155-622XcDisplayEty 10 }

        new-bXcDispPriAug1Sts3Path  OBJECT-TYPE
            SYNTAX  Aug1Sts3Num
            ACCESS  read-only
            STATUS  mandatory
            DESCRIPTION
                "Xc Primary AUG1/STS3 path"
            ::= { new-b155-622XcDisplayEty 11 }

        new-bXcDispPriVc3Sts1Path  OBJECT-TYPE
            SYNTAX  Vc3Sts1Num
            ACCESS  read-only
            STATUS  mandatory
            DESCRIPTION
                "Xc Primary VC3/STS1 path"
            ::= { new-b155-622XcDisplayEty 12 }

        new-bXcDispPriVc1xVtxPath  OBJECT-TYPE
            SYNTAX  Vc1xVtxNum
            ACCESS  read-only
            STATUS  mandatory
            DESCRIPTION
                "Xc Primary VC1x/VTx path"
            ::= { new-b155-622XcDisplayEty 13 }

        new-bXcDispXcGranularity  OBJECT-TYPE
            SYNTAX  INTEGER {
                    tu3(2),
                    au3-sts1(3),
                    tu11-vt15(4),
                    tu12-vt2(5),
                    vc4-sts3c(6),
                    not-available(100)
                }
            ACCESS  read-only
            STATUS  mandatory
            DESCRIPTION
                "Xc granularity"
            ::= { new-b155-622XcDisplayEty 14 }

        new-bXcDispXcType  OBJECT-TYPE
            SYNTAX  XcType
            ACCESS  read-only
            STATUS  mandatory
            DESCRIPTION
                "Xc type"
            ::= { new-b155-622XcDisplayEty 15 }

        new-bXcDispSecType  OBJECT-TYPE
            SYNTAX  NewXcModel
            ACCESS  read-only
            STATUS  mandatory
            DESCRIPTION
                " Xc Secondary Unit Type"
            ::= { new-b155-622XcDisplayEty 16 }

        new-bXcDispSecSlot  OBJECT-TYPE
            SYNTAX  XcSlot
            ACCESS  read-only
            STATUS  mandatory
            DESCRIPTION
                "Xc Secondary Unit "
            ::= { new-b155-622XcDisplayEty 17 }

        new-bXcDispSecPort  OBJECT-TYPE
            SYNTAX  PortID
            ACCESS  read-only
            STATUS  mandatory
            DESCRIPTION
                "Xc Secondary port "
            ::= { new-b155-622XcDisplayEty 18 }

        new-bXcDispSecChannel  OBJECT-TYPE
            SYNTAX  ChannelNum
            ACCESS  read-only
            STATUS  mandatory
            DESCRIPTION
                "Xc Secondary channel "
            ::= { new-b155-622XcDisplayEty 19 }

        new-bXcDispSecAug1Sts3Path  OBJECT-TYPE
            SYNTAX  Aug1Sts3Num
            ACCESS  read-only
            STATUS  mandatory
            DESCRIPTION
                "Xc Secondary AUG1/STS3 path"
            ::= { new-b155-622XcDisplayEty 20 }

        new-bXcDispSecVc3Sts1Path  OBJECT-TYPE
            SYNTAX  Vc3Sts1Num
            ACCESS  read-only
            STATUS  mandatory
            DESCRIPTION
                "Xc Secondary VC3/STS1 path"
            ::= { new-b155-622XcDisplayEty 21 }

        new-bXcDispSecVc1xVtxPath  OBJECT-TYPE
            SYNTAX  Vc1xVtxNum
            ACCESS  read-only
            STATUS  mandatory
            DESCRIPTION
                "Xc Secondary VC1x/VTx path"
            ::= { new-b155-622XcDisplayEty 22 }

--
--  New B155/622 SNCP/UPSR APS Table
--
        new-b155-622SncpApsTab  OBJECT-TYPE
            SYNTAX  SEQUENCE OF  NewB155-622SncpApsEty
            ACCESS  not-accessible
            STATUS  mandatory
            DESCRIPTION
                "B155/622 SNCP/UPSR APS table "
            ::= { b155-622-card 28 }

        new-b155-622SncpApsEty  OBJECT-TYPE
            SYNTAX  NewB155-622SncpApsEty
            ACCESS  not-accessible
            STATUS  mandatory
            DESCRIPTION
                "B155/622 SNCP/UPSR APS entry"
            INDEX { new-bSncpUnit ,
                    new-bSncpPort , new-bSncpAug1Sts3 ,
                    new-bSncpVc3Sts1 , new-bSncpTU1xVtx }
            ::= { new-b155-622SncpApsTab 1 }

        NewB155-622SncpApsEty ::= SEQUENCE {
            new-bSncpUnit               UnitID,
            new-bSncpPort               PortID,
            new-bSncpAug1Sts3           Aug1Sts3Num,
            new-bSncpVc3Sts1            Vc3Sts1Num,
            new-bSncpTU1xVtx            TU1xVtxNum,
            new-bSncpCurrSlot           XcSlot,
            new-bSncpCurrPort           PortID,
            new-bSncpCurrChannel        ChannelNum,
            new-bSncpCurrAug1Sts3Path   Aug1Sts3Num,
            new-bSncpCurrVc3Sts1Path    Vc3Sts1Num,
            new-bSncpCurrVc1xVtxPath    Vc1xVtxNum,
            new-bSncpPPType             XcType,
            new-bSncpCmd                SncpUserCmd,
            new-bSncpRevertive          INTEGER
        }

        new-bSncpUnit  OBJECT-TYPE
            SYNTAX  UnitID
            ACCESS  read-only
            STATUS  mandatory
            DESCRIPTION
                "unit 1 to 8, total 8 units."
            ::= { new-b155-622SncpApsEty 1 }

        new-bSncpPort  OBJECT-TYPE
            SYNTAX  PortID
            ACCESS  read-only
            STATUS  mandatory
            DESCRIPTION
                "PORT #1~#2"
            ::= { new-b155-622SncpApsEty 2 }

        new-bSncpAug1Sts3  OBJECT-TYPE
            SYNTAX  Aug1Sts3Num
            ACCESS  read-only
            STATUS  mandatory
            DESCRIPTION
                "AUG1/STS3 index"
            ::= { new-b155-622SncpApsEty 3 }

        new-bSncpVc3Sts1  OBJECT-TYPE
            SYNTAX  Vc3Sts1Num
            ACCESS  read-only
            STATUS  mandatory
            DESCRIPTION
                "VC3/STS1 index"
            ::= { new-b155-622SncpApsEty 4 }

        new-bSncpTU1xVtx  OBJECT-TYPE
            SYNTAX  TU1xVtxNum
            ACCESS  read-only
            STATUS  mandatory
            DESCRIPTION
                "VC1x/VTx index"
            ::= { new-b155-622SncpApsEty 5 }

        new-bSncpCurrSlot  OBJECT-TYPE
            SYNTAX  XcSlot
            ACCESS  read-only
            STATUS  mandatory
            DESCRIPTION
                "SNCP/UPSR current slot"
            ::= { new-b155-622SncpApsEty 6 }

        new-bSncpCurrPort  OBJECT-TYPE
            SYNTAX  PortID
            ACCESS  read-only
            STATUS  mandatory
            DESCRIPTION
                "SNCP/UPSR current port"
            ::= { new-b155-622SncpApsEty 7 }

        new-bSncpCurrChannel  OBJECT-TYPE
            SYNTAX  ChannelNum
            ACCESS  read-only
            STATUS  mandatory
            DESCRIPTION
                "SNCP/UPSR current channel"
            ::= { new-b155-622SncpApsEty 8 }

        new-bSncpCurrAug1Sts3Path  OBJECT-TYPE
            SYNTAX  Aug1Sts3Num
            ACCESS  read-only
            STATUS  mandatory
            DESCRIPTION
                "SNCP/UPSR current Aug1/Sts3"
            ::= { new-b155-622SncpApsEty 9 }

        new-bSncpCurrVc3Sts1Path  OBJECT-TYPE
            SYNTAX  Vc3Sts1Num
            ACCESS  read-only
            STATUS  mandatory
            DESCRIPTION
                "SNCP/UPSR current Vc3/Sts1"
            ::= { new-b155-622SncpApsEty 10 }

        new-bSncpCurrVc1xVtxPath  OBJECT-TYPE
            SYNTAX  Vc1xVtxNum
            ACCESS  read-only
            STATUS  mandatory
            DESCRIPTION
                "SNCP/UPSR current Vc1x/Vtx"
            ::= { new-b155-622SncpApsEty 11 }

        new-bSncpPPType  OBJECT-TYPE
            SYNTAX  XcType
            ACCESS  read-only
            STATUS  mandatory
            DESCRIPTION
                "SNCP/UPSR path protection type"
            ::= { new-b155-622SncpApsEty 12 }

        new-bSncpCmd  OBJECT-TYPE
            SYNTAX  SncpUserCmd
            ACCESS  read-write
            STATUS  mandatory
            DESCRIPTION
                "SNCP/UPSR APS command"
            ::= { new-b155-622SncpApsEty 13 }

        new-bSncpRevertive  OBJECT-TYPE
            SYNTAX  INTEGER {
                    non-revertive(1),
                    revertive(2)
                }
            ACCESS  read-write
            STATUS  mandatory
            DESCRIPTION
                "SNCP/UPSR revertive or non-revertive"
            ::= { new-b155-622SncpApsEty 14 }

--
--  New B155/622 Protection Table
--
        new-b155-622ProtectTab  OBJECT-TYPE
            SYNTAX  SEQUENCE OF  NewB155-622ProtectEty
            ACCESS  not-accessible
            STATUS  mandatory
            DESCRIPTION
                "B155/622 protection table"
            ::= { b155-622-card 29 }

        new-b155-622ProtectEty  OBJECT-TYPE
            SYNTAX  NewB155-622ProtectEty
            ACCESS  not-accessible
            STATUS  mandatory
            DESCRIPTION
                "An entry in the B155/622 Protection table."
            INDEX { new-bProtectUnit , new-bProtectPort }
            ::= { new-b155-622ProtectTab 1 }


        NewB155-622ProtectEty ::= SEQUENCE  {
            new-bProtectUnit            UnitID,
            new-bProtectPort            PortID,
            new-bProtectMspEnable       INTEGER,
            new-bProtectMspRevertive    INTEGER,
            new-bProtectMspDirection    INTEGER
        }

        new-bProtectUnit  OBJECT-TYPE
            SYNTAX  UnitID
            ACCESS  read-only
            STATUS  mandatory
            DESCRIPTION
                "unit 1 to 8, total 8 units."
            ::= { new-b155-622ProtectEty  1 }

        new-bProtectPort  OBJECT-TYPE
            SYNTAX  PortID
            ACCESS  read-only
            STATUS  mandatory
            DESCRIPTION
                "PORT #1~#2"
            ::= { new-b155-622ProtectEty  2 }

        new-bProtectMspEnable  OBJECT-TYPE
            SYNTAX  INTEGER {
                    off(1),
                    on(2)
                }
            ACCESS  read-write
            STATUS  mandatory
            DESCRIPTION
                "MSP 1+1 OFF or ON"
            ::= { new-b155-622ProtectEty 3 }

        new-bProtectMspRevertive  OBJECT-TYPE
            SYNTAX  INTEGER {
                    non-revertive(1),
                    revertive(2)
                }
            ACCESS  read-write
            STATUS  mandatory
            DESCRIPTION
                "MSP 1+1 revertive or non-revertive"
            ::= { new-b155-622ProtectEty 4 }

        new-bProtectMspDirection  OBJECT-TYPE
            SYNTAX  INTEGER {
                    uni-directional(1),
                    bi-directional(2)
                }
            ACCESS  read-write
            STATUS  mandatory
            DESCRIPTION
                "MSP 1+1 direction"
            ::= { new-b155-622ProtectEty 5 }


        b155622TotalCard   OBJECT-TYPE
            SYNTAX  INTEGER
            ACCESS  read-only
            STATUS  mandatory
            DESCRIPTION
                "Total cards of b155-622"
            ::= { b155-622-card 100 }

--2011-3-17 elvis above

--======================================================================--
--======================================================================--
--  e1-card MIB
--======================================================================--
--======================================================================--

--
--  E1 Config
--

    hdE1Config           OBJECT IDENTIFIER ::= { hdE1-card 1 }


--
--  E1 Channel Line Interface Setup Table
--

        e1ChLineIntfSetupTab  OBJECT-TYPE
            SYNTAX  SEQUENCE OF E1ChLineIntfSetupEty
            ACCESS  not-accessible
            STATUS  mandatory
            DESCRIPTION
                "Channel line interface setup table"
            ::= { hdE1Config 1 }

        e1ChLineIntfSetupEty  OBJECT-TYPE
            SYNTAX  E1ChLineIntfSetupEty
            ACCESS  not-accessible
            STATUS  mandatory
            DESCRIPTION
                "An entry in the channel line interface setup table"
            INDEX { e1ChLineIntfUnit ,
                    e1ChLineIntfPort }
            ::= { e1ChLineIntfSetupTab 1 }

        E1ChLineIntfSetupEty ::= SEQUENCE {
            e1ChLineIntfUnit            UnitID,
            e1ChLineIntfPort            PortID,
            e1ChLineIntfCoding          INTEGER,
            e1ChLineIntfEqualizer       INTEGER
        }

        e1ChLineIntfUnit  OBJECT-TYPE
            SYNTAX  UnitID
            ACCESS  read-only
            STATUS  mandatory
            DESCRIPTION
            "unit 1 to 4."
            ::= { e1ChLineIntfSetupEty 1 }

        e1ChLineIntfPort  OBJECT-TYPE
            SYNTAX  PortID
            ACCESS  read-only
            STATUS  mandatory
            DESCRIPTION
                "E1 Port 1 to 63"
            ::= { e1ChLineIntfSetupEty 2 }

        e1ChLineIntfCoding  OBJECT-TYPE
            SYNTAX  INTEGER{
                    hdb3(1),
                    ami(2)
                }
            ACCESS  read-write
            STATUS  mandatory
            DESCRIPTION
                "E1 line coding mode"
            ::= { e1ChLineIntfSetupEty 3 }

        e1ChLineIntfEqualizer  OBJECT-TYPE
            SYNTAX  INTEGER{
                    balance(1),
                    un-balance(2)
                }
            ACCESS  read-write
            STATUS  mandatory
            DESCRIPTION
                "E1 line equalizer"
            ::= { e1ChLineIntfSetupEty 4 }

--
-- E1 Trace Message & Signal Label Setup Table
--

        e1J2SigLabelSetupTab  OBJECT-TYPE
            SYNTAX  SEQUENCE OF E1J2SigLabelSetupEty
            ACCESS  not-accessible
            STATUS  mandatory
            DESCRIPTION
                "Trace message & Signal label setup table"
            ::= { hdE1Config 2 }

        e1J2SigLabelSetupEty  OBJECT-TYPE
            SYNTAX  E1J2SigLabelSetupEty
            ACCESS  not-accessible
            STATUS  mandatory
            DESCRIPTION
                "An entry in the trace message & signal label setup table"
            INDEX { e1J2SigLabelUnit ,
                    e1J2SigLabelPort }
            ::= { e1J2SigLabelSetupTab 1 }

        E1J2SigLabelSetupEty ::= SEQUENCE {
            e1J2SigLabelUnit            UnitID,
            e1J2SigLabelPort            PortID,
            e1J2SigLabelJ2Length        INTEGER,
            e1J2SigLabelExpJ2Msg        DisplayString(SIZE(0..64)),
            e1J2SigLabelTxJ2Msg         DisplayString(SIZE(0..64)),
            e1J2SigLabelRxJ2Msg         DisplayString(SIZE(0..64)),
            e1J2SigLabelExpSigLabel     INTEGER,
            e1J2SigLabelRxSigLabel      INTEGER,
            e1J2SigLabelTxSigLabel      INTEGER
        }

        e1J2SigLabelUnit  OBJECT-TYPE
            SYNTAX  UnitID
            ACCESS  read-only
            STATUS  mandatory
            DESCRIPTION
            "unit 1 to 4."
            ::= { e1J2SigLabelSetupEty 1 }

        e1J2SigLabelPort  OBJECT-TYPE
            SYNTAX  PortID
            ACCESS  read-only
            STATUS  mandatory
            DESCRIPTION
                "E1 Port 1 to 63"
            ::= { e1J2SigLabelSetupEty 2 }

        e1J2SigLabelJ2Length  OBJECT-TYPE
            SYNTAX   INTEGER{
                    null(1),
                    len-16-BYTE-space(2),
                    len-64-BYTE-space(3),
                    len-16-BYTE-null(4),
                    len-64-BYTE-null(5)
--                    len-1-BYTE(6)
                }
            ACCESS  read-write
            STATUS  mandatory
            DESCRIPTION
                "J2 message length"
            ::= { e1J2SigLabelSetupEty 3 }

        e1J2SigLabelExpJ2Msg OBJECT-TYPE
            SYNTAX  DisplayString (SIZE(0..64))
            ACCESS  read-write
            STATUS  mandatory
            DESCRIPTION
                "The expected J2 message"
            ::= { e1J2SigLabelSetupEty 4 }

        e1J2SigLabelTxJ2Msg OBJECT-TYPE
            SYNTAX  DisplayString (SIZE(0..64))
            ACCESS  read-write
            STATUS  mandatory
            DESCRIPTION
                "The tx J2 message"
            ::= { e1J2SigLabelSetupEty 5 }

        e1J2SigLabelRxJ2Msg OBJECT-TYPE
            SYNTAX  DisplayString (SIZE(0..64))
            ACCESS  read-only
            STATUS  mandatory
            DESCRIPTION
                "The rx J2 message"
            ::= { e1J2SigLabelSetupEty 6 }

        e1J2SigLabelExpSigLabel  OBJECT-TYPE
            SYNTAX  INTEGER{
                    unequipped(1),
                    equipped(2),
                    asynchronous(3),
                    bit-synchronous(4),
                    byte-synchronous(5),
                    extended-signal-label(6),
                    test-signal(7),
                    vc-ais(8)
                }
            ACCESS  read-write
            STATUS  mandatory
            DESCRIPTION
                "The expected Path Signal Label"
            ::= { e1J2SigLabelSetupEty 7 }

        e1J2SigLabelRxSigLabel  OBJECT-TYPE
            SYNTAX  INTEGER{
                    unequipped(1),
                    equipped(2),
                    asynchronous(3),
                    bit-synchronous(4),
                    byte-synchronous(5),
                    extended-signal-label(6),
                    test-signal(7),
                    vc-ais(8)
                }
            ACCESS  read-only
            STATUS  mandatory
            DESCRIPTION
                "The rx Path Signal Label"
            ::= { e1J2SigLabelSetupEty 8 }

        e1J2SigLabelTxSigLabel  OBJECT-TYPE
            SYNTAX  INTEGER{
                    unequipped(1),
                    equipped(2),
                    asynchronous(3),
                    bit-synchronous(4),
                    byte-synchronous(5),
                    extended-signal-label(6),
                    test-signal(7),
                    vc-ais(8)
                }
            ACCESS  read-write
            STATUS  mandatory
            DESCRIPTION
                "The tx Path Signal Label"
            ::= { e1J2SigLabelSetupEty 9 }

--
--  E1 Customer Information Setup Table
--

        e1CustomerInfoSetupTab  OBJECT-TYPE
            SYNTAX  SEQUENCE OF E1CustomerInfoSetupEty
            ACCESS  not-accessible
            STATUS  mandatory
            DESCRIPTION
                "Customer information setup table"
            ::= { hdE1Config 3 }

        e1CustomerInfoSetupEty  OBJECT-TYPE
            SYNTAX  E1CustomerInfoSetupEty
            ACCESS  not-accessible
            STATUS  mandatory
            DESCRIPTION
                "An entry in the customer information setup table"
            INDEX { e1CustomerInfoUnit ,
                    e1CustomerInfoPort }
            ::= { e1CustomerInfoSetupTab 1 }

        E1CustomerInfoSetupEty ::= SEQUENCE {
            e1CustomerInfoUnit          UnitID,
            e1CustomerInfoPort          PortID,
            e1CustomerInfoString        DisplayString(SIZE(0..20))
        }

        e1CustomerInfoUnit  OBJECT-TYPE
            SYNTAX  UnitID
            ACCESS  read-only
            STATUS  mandatory
            DESCRIPTION
            "unit 1 to 4."
            ::= { e1CustomerInfoSetupEty 1 }

        e1CustomerInfoPort  OBJECT-TYPE
            SYNTAX  PortID
            ACCESS  read-only
            STATUS  mandatory
            DESCRIPTION
                "E1 Port 1 to 63"
            ::= { e1CustomerInfoSetupEty 2 }

        e1CustomerInfoString OBJECT-TYPE
            SYNTAX  DisplayString (SIZE(0..20))
            ACCESS  read-write
            STATUS  mandatory
            DESCRIPTION
                "Customer information"
            ::= { e1CustomerInfoSetupEty 3 }

--
-- E1 TPSG Protection Setup Table
--
        e1TPSGProtectSetupTab  OBJECT-TYPE
            SYNTAX  SEQUENCE OF E1TPSGProtectSetupEty
            ACCESS  not-accessible
            STATUS  mandatory
            DESCRIPTION
                "TPSG protection setup table"
            ::= { hdE1Config 4 }

        e1TPSGProtectSetupEty  OBJECT-TYPE
            SYNTAX  E1TPSGProtectSetupEty
            ACCESS  not-accessible
            STATUS  mandatory
            DESCRIPTION
                "An entry in the TPSG protection setup table"
            INDEX { e1TPSGProtectUnit }
            ::= { e1TPSGProtectSetupTab 1 }

        E1TPSGProtectSetupEty ::= SEQUENCE {
            e1TPSGProtectUnit           UnitID,
            e1TPSGProtectActive         INTEGER,
            e1TPSGProtectStatus         INTEGER,
            e1TPSGProtectType           INTEGER,
            e1TPSGProtectMode           INTEGER
        }

        e1TPSGProtectUnit  OBJECT-TYPE
            SYNTAX  UnitID
            ACCESS  read-only
            STATUS  mandatory
            DESCRIPTION
            "unit 1 to 4."
            ::= { e1TPSGProtectSetupEty 1 }

        e1TPSGProtectActive  OBJECT-TYPE
            SYNTAX  INTEGER{
                    none(0),
                    standby(1),
                    working(2)
                }
            ACCESS  read-only
            STATUS  mandatory
            DESCRIPTION
                "TPSG active working/standby"
            ::= { e1TPSGProtectSetupEty 2 }

        e1TPSGProtectStatus  OBJECT-TYPE
            SYNTAX  INTEGER{
                    sync-failed(1),
                    sync-ok(2),
                    start-sync(3),
                    during-sync(4),
                    update-failed(5),
                    unsync(6)
                }
            ACCESS  read-only
            STATUS  mandatory
            DESCRIPTION
                "TPSG Status"
            ::= { e1TPSGProtectSetupEty 3 }

        e1TPSGProtectType  OBJECT-TYPE
            SYNTAX  INTEGER{
                    card-base-1-for-1(2),
                    port-circuit-protection(3),
                    line-1-plus-1(4)
                }
            ACCESS  read-write
            STATUS  mandatory
            DESCRIPTION
                "TPSG protection type"
            ::= { e1TPSGProtectSetupEty 4 }

        e1TPSGProtectMode  OBJECT-TYPE
            SYNTAX  INTEGER{
                    non-revertible(1),
                    revertible(2)
                }
            ACCESS  read-write
            STATUS  mandatory
            DESCRIPTION
                "TPSG protection mode"
            ::= { e1TPSGProtectSetupEty 5 }


--
--  E1 TU Mapping Mode Setup Table
--

        e1TuMapModeSetupTab  OBJECT-TYPE
            SYNTAX  SEQUENCE OF E1TuMapModeSetupEty
            ACCESS  not-accessible
            STATUS  mandatory
            DESCRIPTION
                "TU11/TU12 mapping mode setup table"
            ::= { hdE1Config 5 }

        e1TuMapModeSetupEty  OBJECT-TYPE
            SYNTAX  E1TuMapModeSetupEty
            ACCESS  not-accessible
            STATUS  mandatory
            DESCRIPTION
                "An entry in the TU11/TU12 mapping mode setup table"
            INDEX { e1TuMapModeUnit }
            ::= { e1TuMapModeSetupTab 1 }

        E1TuMapModeSetupEty ::= SEQUENCE {
            e1TuMapModeUnit             UnitID,
            e1TuMapModeTuMode           INTEGER
        }

        e1TuMapModeUnit  OBJECT-TYPE
            SYNTAX  UnitID
            ACCESS  read-only
            STATUS  mandatory
            DESCRIPTION
            "unit 1 to 4."
            ::= { e1TuMapModeSetupEty 1 }

        e1TuMapModeTuMode  OBJECT-TYPE
            SYNTAX  INTEGER{
                    tu12(1)
                }
            ACCESS  read-only
            STATUS  mandatory
            DESCRIPTION
                "TU11/TU12 mapping mode"
            ::= { e1TuMapModeSetupEty 2 }

--
-- E1 TPSG Protection Switch Table
--
        e1TPSGProtectSwitchTab  OBJECT-TYPE
            SYNTAX  SEQUENCE OF E1TPSGProtectSwitchEty
            ACCESS  not-accessible
            STATUS  mandatory
            DESCRIPTION
                "TPSG protection switch table"
            ::= { hdE1Config 6 }

        e1TPSGProtectSwitchEty  OBJECT-TYPE
            SYNTAX  E1TPSGProtectSwitchEty
            ACCESS  not-accessible
            STATUS  mandatory
            DESCRIPTION
                "An entry in the TPSG protection switch table"
            INDEX { e1TPSGProSwitchUnit ,
                    e1TPSGProSwitchPort }
            ::= { e1TPSGProtectSwitchTab 1 }

        E1TPSGProtectSwitchEty ::= SEQUENCE {
            e1TPSGProSwitchUnit         UnitID,
            e1TPSGProSwitchPort         PortID,
            e1TPSGProSwitchSide         INTEGER
        }

        e1TPSGProSwitchUnit  OBJECT-TYPE
            SYNTAX  UnitID
            ACCESS  read-only
            STATUS  mandatory
            DESCRIPTION
            "unit 1 to 4."
            ::= { e1TPSGProtectSwitchEty 1 }

        e1TPSGProSwitchPort  OBJECT-TYPE
            SYNTAX  PortID
            ACCESS  read-only
            STATUS  mandatory
            DESCRIPTION
                "E1 Port 1 to 63"
            ::= { e1TPSGProtectSwitchEty 2 }

        e1TPSGProSwitchSide  OBJECT-TYPE
            SYNTAX  INTEGER {
                    left(1),
                    right(2),
                    left-all-port(3),
                    right-all-port(4)
                }
            ACCESS  read-write
            STATUS  mandatory
            DESCRIPTION
                "Switch Side(left/right)"
            ::= { e1TPSGProtectSwitchEty 3 }

--
--  E1 Channel RDI Mode Setup Table
--

        e1ChRDIModeSetupTab  OBJECT-TYPE
            SYNTAX  SEQUENCE OF E1ChRDIModeSetupEty
            ACCESS  not-accessible
            STATUS  mandatory
            DESCRIPTION
                "Channel RDI mode setup table"
            ::= { hdE1Config 7 }

        e1ChRDIModeSetupEty  OBJECT-TYPE
            SYNTAX  E1ChRDIModeSetupEty
            ACCESS  not-accessible
            STATUS  mandatory
            DESCRIPTION
                "An entry in the channel RDI mode setup table"
            INDEX { e1ChRDIModeUnit ,
                    e1ChRDIModePort }
            ::= { e1ChRDIModeSetupTab 1 }

        E1ChRDIModeSetupEty ::= SEQUENCE {
            e1ChRDIModeUnit             UnitID,
            e1ChRDIModePort             PortID,
            e1ChRDIModeMode             INTEGER
        }

        e1ChRDIModeUnit  OBJECT-TYPE
            SYNTAX  UnitID
            ACCESS  read-only
            STATUS  mandatory
            DESCRIPTION
            "unit 1 to 4."
            ::= { e1ChRDIModeSetupEty 1 }

        e1ChRDIModePort  OBJECT-TYPE
            SYNTAX  PortID
            ACCESS  read-only
            STATUS  mandatory
            DESCRIPTION
                "E1 Port 1 to 63"
            ::= { e1ChRDIModeSetupEty 2 }

        e1ChRDIModeMode  OBJECT-TYPE
            SYNTAX  INTEGER{
                    rdi(1),
                    e-rdi(2)
                }
            ACCESS  read-write
            STATUS  mandatory
            DESCRIPTION
                "RDI Monitor Mode(RDI/E-RDI)"
            ::= { e1ChRDIModeSetupEty 3 }

--
--  E1 LIU HighZ Setup Table
--

        e1LiuHighZSetupTab  OBJECT-TYPE
            SYNTAX  SEQUENCE OF E1LiuHighZSetupEty
            ACCESS  not-accessible
            STATUS  mandatory
            DESCRIPTION
                "LIU HighZ setup table"
            ::= { hdE1Config 8 }

        e1LiuHighZSetupEty  OBJECT-TYPE
            SYNTAX  E1LiuHighZSetupEty
            ACCESS  not-accessible
            STATUS  mandatory
            DESCRIPTION
                "An entry in the LIU HighZ setup table"
            INDEX { e1LiuHighZUnit ,
                    e1LiuHighZIndex }
            ::= { e1LiuHighZSetupTab 1 }

        E1LiuHighZSetupEty ::= SEQUENCE {
            e1LiuHighZUnit              UnitID,
            e1LiuHighZIndex             INTEGER,
            e1LiuHighZSetup             INTEGER
        }

        e1LiuHighZUnit  OBJECT-TYPE
            SYNTAX  UnitID
            ACCESS  read-only
            STATUS  mandatory
            DESCRIPTION
            "unit 1 to 4."
            ::= { e1LiuHighZSetupEty 1 }

        e1LiuHighZIndex  OBJECT-TYPE
            SYNTAX  INTEGER
            ACCESS  read-only
            STATUS  mandatory
            DESCRIPTION
                "E1 Port 1 to 63"
            ::= { e1LiuHighZSetupEty 2 }

        e1LiuHighZSetup  OBJECT-TYPE
            SYNTAX  INTEGER {
                    disable(1),
                    enable(2)
                }
            ACCESS  read-write
            STATUS  mandatory
            DESCRIPTION
                "Liu HighZ Setup(Disable/Enable)"
            ::= { e1LiuHighZSetupEty 3 }


--
--  E1 Alarm
--

    hdE1Alarm           OBJECT IDENTIFIER ::= { hdE1-card 2 }

--
--  E1 Alarm Mask Setup Table
--

        e1AlmMaskSetupTab  OBJECT-TYPE
            SYNTAX  SEQUENCE OF E1AlmMaskSetupEty
            ACCESS  not-accessible
            STATUS  mandatory
            DESCRIPTION
                "Alarm mask setup table"
            ::= { hdE1Alarm 1 }

        e1AlmMaskSetupEty  OBJECT-TYPE
            SYNTAX  E1AlmMaskSetupEty
            ACCESS  not-accessible
            STATUS  mandatory
            DESCRIPTION
                "An entry in the alarm mask setup table"
            INDEX { e1AlmMaskUnit ,
                    e1AlmMaskPort }
            ::= { e1AlmMaskSetupTab 1 }

        E1AlmMaskSetupEty ::= SEQUENCE {
            e1AlmMaskUnit               UnitID,
            e1AlmMaskPort               PortID,
            e1AlmMaskLoVT-LOP           INTEGER,
            e1AlmMaskLoVT-AIS           INTEGER,
            e1AlmMaskLoVT-UNEQ          INTEGER,
            e1AlmMaskLoVT-PLM           INTEGER,
            e1AlmMaskLoVT-TIM           INTEGER,
            e1AlmMaskLoVT-RDI-P         INTEGER,
            e1AlmMaskLoVT-RDI-S         INTEGER,
            e1AlmMaskLoVT-RDI-C         INTEGER,
            e1AlmMaskLoVT-V5-REI        INTEGER,
            e1AlmMaskLoVT-V5-BIP        INTEGER,
            e1AlmMaskLine-LOS           INTEGER,
            e1AlmMaskLine-AIS           INTEGER,
            e1AlmMaskLine-UAS           INTEGER,
            e1AlmMaskLine-RAI           INTEGER
        }

        e1AlmMaskUnit  OBJECT-TYPE
            SYNTAX  UnitID
            ACCESS  read-only
            STATUS  mandatory
            DESCRIPTION
            "unit 1 to 4."
            ::= { e1AlmMaskSetupEty 1 }

        e1AlmMaskPort  OBJECT-TYPE
            SYNTAX  PortID
            ACCESS  read-only
            STATUS  mandatory
            DESCRIPTION
                "E1 Port 1 to 63"
            ::= { e1AlmMaskSetupEty 2 }

        e1AlmMaskLoVT-LOP  OBJECT-TYPE
            SYNTAX  INTEGER{
                    disable(1),
                    enable(2)
                }
            ACCESS  read-write
            STATUS  mandatory
            DESCRIPTION
                "tu-lop alarm"
            ::= { e1AlmMaskSetupEty 3 }

        e1AlmMaskLoVT-AIS  OBJECT-TYPE
            SYNTAX  INTEGER{
                    disable(1),
                    enable(2)
                }
            ACCESS  read-write
            STATUS  mandatory
            DESCRIPTION
                "tu-ais alarm"
            ::= { e1AlmMaskSetupEty 4 }

        e1AlmMaskLoVT-UNEQ  OBJECT-TYPE
            SYNTAX  INTEGER{
                    disable(1),
                    enable(2)
                }
            ACCESS  read-write
            STATUS  mandatory
            DESCRIPTION
                "lp-uneq alarm"
            ::= { e1AlmMaskSetupEty 5 }

        e1AlmMaskLoVT-PLM  OBJECT-TYPE
            SYNTAX  INTEGER{
                    disable(1),
                    enable(2)
                }
            ACCESS  read-write
            STATUS  mandatory
            DESCRIPTION
                "lp-plm alarm"
            ::= { e1AlmMaskSetupEty 6 }

        e1AlmMaskLoVT-TIM  OBJECT-TYPE
            SYNTAX  INTEGER{
                    disable(1),
                    enable(2)
                }
            ACCESS  read-write
            STATUS  mandatory
            DESCRIPTION
                "lp-tim alarm"
            ::= { e1AlmMaskSetupEty 7 }

        e1AlmMaskLoVT-RDI-P  OBJECT-TYPE
            SYNTAX  INTEGER{
                    disable(1),
                    enable(2)
                }
            ACCESS  read-write
            STATUS  mandatory
            DESCRIPTION
                "lp-rdi-p alarm"
            ::= { e1AlmMaskSetupEty 8 }

        e1AlmMaskLoVT-RDI-S  OBJECT-TYPE
            SYNTAX  INTEGER{
                    disable(1),
                    enable(2)
                }
            ACCESS  read-write
            STATUS  mandatory
            DESCRIPTION
                "lp-rdi-s alarm"
            ::= { e1AlmMaskSetupEty 9 }

        e1AlmMaskLoVT-RDI-C  OBJECT-TYPE
            SYNTAX  INTEGER{
                    disable(1),
                    enable(2)
                }
            ACCESS  read-write
            STATUS  mandatory
            DESCRIPTION
                "lp-rdi-c alarm"
            ::= { e1AlmMaskSetupEty 10 }

        e1AlmMaskLoVT-V5-REI  OBJECT-TYPE
            SYNTAX  INTEGER{
                    disable(1),
                    enable(2)
                }
            ACCESS  read-write
            STATUS  mandatory
            DESCRIPTION
                "lp-rei alarm"
            ::= { e1AlmMaskSetupEty 11 }

        e1AlmMaskLoVT-V5-BIP  OBJECT-TYPE
            SYNTAX  INTEGER{
                    disable(1),
                    enable(2)
                }
            ACCESS  read-write
            STATUS  mandatory
            DESCRIPTION
                "lp-bip alarm"
            ::= { e1AlmMaskSetupEty 12 }

        e1AlmMaskLine-LOS  OBJECT-TYPE
            SYNTAX  INTEGER{
                    disable(1),
                    enable(2)
                }
            ACCESS  read-write
            STATUS  mandatory
            DESCRIPTION
                "line-los alarm"
            ::= { e1AlmMaskSetupEty 13 }

        e1AlmMaskLine-AIS  OBJECT-TYPE
            SYNTAX  INTEGER{
                    disable(1),
                    enable(2)
                }
            ACCESS  read-write
            STATUS  mandatory
            DESCRIPTION
                "line-ais alarm"
            ::= { e1AlmMaskSetupEty 14 }

        e1AlmMaskLine-UAS  OBJECT-TYPE
            SYNTAX  INTEGER{
                    disable(1),
                    enable(2)
                }
            ACCESS  read-write
            STATUS  mandatory
            DESCRIPTION
                "line-uas alarm"
            ::= { e1AlmMaskSetupEty 15 }

        e1AlmMaskLine-RAI  OBJECT-TYPE
            SYNTAX  INTEGER{
                    disable(1),
                    enable(2)
                }
            ACCESS  read-write
            STATUS  mandatory
            DESCRIPTION
                "line-rai alarm"
            ::= { e1AlmMaskSetupEty 16 }

--
--  E1 Alarm Relay Setup Table
--

        e1AlmRelaySetupTab  OBJECT-TYPE
            SYNTAX  SEQUENCE OF E1AlmRelaySetupEty
            ACCESS  not-accessible
            STATUS  mandatory
            DESCRIPTION
                "Alarm relay setup table"
            ::= { hdE1Alarm 2 }

        e1AlmRelaySetupEty  OBJECT-TYPE
            SYNTAX  E1AlmRelaySetupEty
            ACCESS  not-accessible
            STATUS  mandatory
            DESCRIPTION
                "An entry in the alarm relay setup table"
            INDEX { e1AlmRelayUnit ,
                    e1AlmRelayPort }
            ::= { e1AlmRelaySetupTab 1 }

        E1AlmRelaySetupEty ::= SEQUENCE {
            e1AlmRelayUnit              UnitID,
            e1AlmRelayPort              PortID,
            e1AlmRelayLoVT-LOP          INTEGER,
            e1AlmRelayLoVT-AIS          INTEGER,
            e1AlmRelayLoVT-UNEQ         INTEGER,
            e1AlmRelayLoVT-PLM          INTEGER,
            e1AlmRelayLoVT-TIM          INTEGER,
            e1AlmRelayLoVT-RDI-P        INTEGER,
            e1AlmRelayLoVT-RDI-S        INTEGER,
            e1AlmRelayLoVT-RDI-C        INTEGER,
            e1AlmRelayLoVT-V5-REI       INTEGER,
            e1AlmRelayLoVT-V5-BIP       INTEGER,
            e1AlmRelayLine-LOS          INTEGER,
            e1AlmRelayLine-AIS          INTEGER,
            e1AlmRelayLine-UAS          INTEGER,
            e1AlmRelayLine-RAI          INTEGER
        }

        e1AlmRelayUnit  OBJECT-TYPE
            SYNTAX  UnitID
            ACCESS  read-only
            STATUS  mandatory
            DESCRIPTION
            "unit 1 to 4."
            ::= { e1AlmRelaySetupEty 1 }

        e1AlmRelayPort  OBJECT-TYPE
            SYNTAX  PortID
            ACCESS  read-only
            STATUS  mandatory
            DESCRIPTION
                "E1 Port 1 to 63"
            ::= { e1AlmRelaySetupEty 2 }

        e1AlmRelayLoVT-LOP  OBJECT-TYPE
            SYNTAX  INTEGER{
                    disable(1),
                    enable(2)
                }
            ACCESS  read-write
            STATUS  mandatory
            DESCRIPTION
                "tu-lop alarm"
            ::= { e1AlmRelaySetupEty 3 }

        e1AlmRelayLoVT-AIS  OBJECT-TYPE
            SYNTAX  INTEGER{
                    disable(1),
                    enable(2)
                }
            ACCESS  read-write
            STATUS  mandatory
            DESCRIPTION
                "tu-ais alarm"
            ::= { e1AlmRelaySetupEty 4 }

        e1AlmRelayLoVT-UNEQ  OBJECT-TYPE
            SYNTAX  INTEGER{
                    disable(1),
                    enable(2)
                }
            ACCESS  read-write
            STATUS  mandatory
            DESCRIPTION
                "lp-uneq alarm"
            ::= { e1AlmRelaySetupEty 5 }

        e1AlmRelayLoVT-PLM  OBJECT-TYPE
            SYNTAX  INTEGER{
                    disable(1),
                    enable(2)
                }
            ACCESS  read-write
            STATUS  mandatory
            DESCRIPTION
                "lp-plm alarm"
            ::= { e1AlmRelaySetupEty 6 }

        e1AlmRelayLoVT-TIM  OBJECT-TYPE
            SYNTAX  INTEGER{
                    disable(1),
                    enable(2)
                }
            ACCESS  read-write
            STATUS  mandatory
            DESCRIPTION
                "lp-tim alarm"
            ::= { e1AlmRelaySetupEty 7 }

        e1AlmRelayLoVT-RDI-P  OBJECT-TYPE
            SYNTAX  INTEGER{
                    disable(1),
                    enable(2)
                }
            ACCESS  read-write
            STATUS  mandatory
            DESCRIPTION
                "lp-rdi-p alarm"
            ::= { e1AlmRelaySetupEty 8 }

        e1AlmRelayLoVT-RDI-S  OBJECT-TYPE
            SYNTAX  INTEGER{
                    disable(1),
                    enable(2)
                }
            ACCESS  read-write
            STATUS  mandatory
            DESCRIPTION
                "lp-rdi-s alarm"
            ::= { e1AlmRelaySetupEty 9 }

        e1AlmRelayLoVT-RDI-C  OBJECT-TYPE
            SYNTAX  INTEGER{
                    disable(1),
                    enable(2)
                }
            ACCESS  read-write
            STATUS  mandatory
            DESCRIPTION
                "lp-rdi-c alarm"
            ::= { e1AlmRelaySetupEty 10 }

        e1AlmRelayLoVT-V5-REI  OBJECT-TYPE
            SYNTAX  INTEGER{
                    disable(1),
                    enable(2)
                }
            ACCESS  read-write
            STATUS  mandatory
            DESCRIPTION
                "lp-rei alarm"
            ::= { e1AlmRelaySetupEty 11 }

        e1AlmRelayLoVT-V5-BIP  OBJECT-TYPE
            SYNTAX  INTEGER{
                    disable(1),
                    enable(2)
                }
            ACCESS  read-write
            STATUS  mandatory
            DESCRIPTION
                "lp-bip alarm"
            ::= { e1AlmRelaySetupEty 12 }

        e1AlmRelayLine-LOS  OBJECT-TYPE
            SYNTAX  INTEGER{
                    disable(1),
                    enable(2)
                }
            ACCESS  read-write
            STATUS  mandatory
            DESCRIPTION
                "line-los alarm"
            ::= { e1AlmRelaySetupEty 13 }

        e1AlmRelayLine-AIS  OBJECT-TYPE
            SYNTAX  INTEGER{
                    disable(1),
                    enable(2)
                }
            ACCESS  read-write
            STATUS  mandatory
            DESCRIPTION
                "line-ais alarm"
            ::= { e1AlmRelaySetupEty 14 }

        e1AlmRelayLine-UAS  OBJECT-TYPE
            SYNTAX  INTEGER{
                    disable(1),
                    enable(2)
                }
            ACCESS  read-write
            STATUS  mandatory
            DESCRIPTION
                "line-uas alarm"
            ::= { e1AlmRelaySetupEty 15 }

        e1AlmRelayLine-RAI  OBJECT-TYPE
            SYNTAX  INTEGER{
                    disable(1),
                    enable(2)
                }
            ACCESS  read-write
            STATUS  mandatory
            DESCRIPTION
                "line-rai alarm"
            ::= { e1AlmRelaySetupEty 16 }


--
--  E1 Alarm Severity Setup Table
--

        e1AlmSeveritySetupTab  OBJECT-TYPE
            SYNTAX  SEQUENCE OF E1AlmSeveritySetupEty
            ACCESS  not-accessible
            STATUS  mandatory
            DESCRIPTION
                "Alarm severity setup table"
            ::= { hdE1Alarm 3 }

        e1AlmSeveritySetupEty  OBJECT-TYPE
            SYNTAX  E1AlmSeveritySetupEty
            ACCESS  not-accessible
            STATUS  mandatory
            DESCRIPTION
                "An entry in the alarm severity setup table"
            INDEX { e1AlmSvrityUnit }
            ::= { e1AlmSeveritySetupTab 1 }

        E1AlmSeveritySetupEty ::= SEQUENCE {
            e1AlmSvrityUnit             UnitID,
            e1AlmSvrityLoVT-LOP         Severity,
            e1AlmSvrityLoVT-AIS         Severity,
            e1AlmSvrityLoVT-UNEQ        Severity,
            e1AlmSvrityLoVT-PLM         Severity,
            e1AlmSvrityLoVT-TIM         Severity,
            e1AlmSvrityLoVT-RDI-P       Severity,
            e1AlmSvrityLoVT-RDI-S       Severity,
            e1AlmSvrityLoVT-RDI-C       Severity,
            e1AlmSvrityLoVT-V5-REI      Severity,
            e1AlmSvrityLoVT-V5-BIP      Severity,
            e1AlmSvrityLine-LOS         Severity,
            e1AlmSvrityLine-AIS         Severity,
            e1AlmSvrityLine-UAS         Severity,
            e1AlmSvrityLine-RAI         Severity
        }

        e1AlmSvrityUnit  OBJECT-TYPE
            SYNTAX  UnitID
            ACCESS  read-only
            STATUS  mandatory
            DESCRIPTION
            "unit 1 to 4."
            ::= { e1AlmSeveritySetupEty 1 }

        e1AlmSvrityLoVT-LOP  OBJECT-TYPE
            SYNTAX  Severity
            ACCESS  read-write
            STATUS  mandatory
            DESCRIPTION
                "tu-lop alarm severity type"
            ::= { e1AlmSeveritySetupEty 2 }

        e1AlmSvrityLoVT-AIS  OBJECT-TYPE
            SYNTAX  Severity
            ACCESS  read-write
            STATUS  mandatory
            DESCRIPTION
                "tu-ais alarm severity type"
            ::= { e1AlmSeveritySetupEty 3 }

        e1AlmSvrityLoVT-UNEQ  OBJECT-TYPE
            SYNTAX  Severity
            ACCESS  read-write
            STATUS  mandatory
            DESCRIPTION
                "lp-uneq alarm severity type"
            ::= { e1AlmSeveritySetupEty 4 }

        e1AlmSvrityLoVT-PLM  OBJECT-TYPE
            SYNTAX  Severity
            ACCESS  read-write
            STATUS  mandatory
            DESCRIPTION
                "lp-plm alarm severity type"
            ::= { e1AlmSeveritySetupEty 5 }

        e1AlmSvrityLoVT-TIM  OBJECT-TYPE
            SYNTAX  Severity
            ACCESS  read-write
            STATUS  mandatory
            DESCRIPTION
                "lp-tim alarm severity type"
            ::= { e1AlmSeveritySetupEty 6 }

        e1AlmSvrityLoVT-RDI-P  OBJECT-TYPE
            SYNTAX  Severity
            ACCESS  read-write
            STATUS  mandatory
            DESCRIPTION
                "lp-rdi-p alarm severity type"
            ::= { e1AlmSeveritySetupEty 7 }

        e1AlmSvrityLoVT-RDI-S  OBJECT-TYPE
            SYNTAX  Severity
            ACCESS  read-write
            STATUS  mandatory
            DESCRIPTION
                "lp-rdi-s alarm severity type"
            ::= { e1AlmSeveritySetupEty 8 }

        e1AlmSvrityLoVT-RDI-C  OBJECT-TYPE
            SYNTAX  Severity
            ACCESS  read-write
            STATUS  mandatory
            DESCRIPTION
                "lp-rdi-c alarm severity type"
            ::= { e1AlmSeveritySetupEty 9 }

        e1AlmSvrityLoVT-V5-REI  OBJECT-TYPE
            SYNTAX  Severity
            ACCESS  read-write
            STATUS  mandatory
            DESCRIPTION
                "lp-rei alarm severity type"
            ::= { e1AlmSeveritySetupEty 10 }

        e1AlmSvrityLoVT-V5-BIP  OBJECT-TYPE
            SYNTAX  Severity
            ACCESS  read-write
            STATUS  mandatory
            DESCRIPTION
                "lp-bip alarm severity type"
            ::= { e1AlmSeveritySetupEty 11 }

        e1AlmSvrityLine-LOS  OBJECT-TYPE
            SYNTAX  Severity
            ACCESS  read-write
            STATUS  mandatory
            DESCRIPTION
                "line-los alarm severity type"
            ::= { e1AlmSeveritySetupEty 12 }

        e1AlmSvrityLine-AIS  OBJECT-TYPE
            SYNTAX  Severity
            ACCESS  read-write
            STATUS  mandatory
            DESCRIPTION
                "line-ais alarm severity type"
            ::= { e1AlmSeveritySetupEty 13 }

        e1AlmSvrityLine-UAS  OBJECT-TYPE
            SYNTAX  Severity
            ACCESS  read-write
            STATUS  mandatory
            DESCRIPTION
                "line-uas alarm severity type"
            ::= { e1AlmSeveritySetupEty 14 }

        e1AlmSvrityLine-RAI  OBJECT-TYPE
            SYNTAX  Severity
            ACCESS  read-write
            STATUS  mandatory
            DESCRIPTION
                "line-rai alarm severity type"
            ::= { e1AlmSeveritySetupEty 15 }


--
--  E1 Insert AIS Alarm Setup Table
--

        e1InsertAisAlmSetupTab  OBJECT-TYPE
            SYNTAX  SEQUENCE OF E1InsertAisAlmSetupEty
            ACCESS  not-accessible
            STATUS  mandatory
            DESCRIPTION
                "Insert AIS alarm setup table"
            ::= { hdE1Alarm 4 }

        e1InsertAisAlmSetupEty  OBJECT-TYPE
            SYNTAX  E1InsertAisAlmSetupEty
            ACCESS  not-accessible
            STATUS  mandatory
            DESCRIPTION
                "An entry in the insert AIS alarm setup table"
            INDEX { e1InstUnit }
            ::= { e1InsertAisAlmSetupTab 1 }

        E1InsertAisAlmSetupEty ::= SEQUENCE {
            e1InstUnit                  UnitID,
            e1InstTuLom-LomVToAis       INTEGER,
            e1InstTuLop-LopVToAis       INTEGER,
            e1InstLpUneq-UneqVToAis     INTEGER,
            e1InstLpPlm-PlmVToAis       INTEGER,
            e1InstLineLosToAis          INTEGER
        }

        e1InstUnit  OBJECT-TYPE
            SYNTAX  UnitID
            ACCESS  read-only
            STATUS  mandatory
            DESCRIPTION
            "unit 1 to 4."
            ::= { e1InsertAisAlmSetupEty 1 }

        e1InstTuLom-LomVToAis OBJECT-TYPE
            SYNTAX  INTEGER {
                    disable(1),
                    enable(2)
                }
            ACCESS  read-write
            STATUS  mandatory
            DESCRIPTION
                "tu-lom to ais"
            ::= { e1InsertAisAlmSetupEty 2 }

        e1InstTuLop-LopVToAis OBJECT-TYPE
            SYNTAX  INTEGER {
                    disable(1),
                    enable(2)
                }
            ACCESS  read-write
            STATUS  mandatory
            DESCRIPTION
                "tu-lop to ais"
            ::= { e1InsertAisAlmSetupEty 3 }

        e1InstLpUneq-UneqVToAis OBJECT-TYPE
            SYNTAX  INTEGER {
                    disable(1),
                    enable(2)
                }
            ACCESS  read-write
            STATUS  mandatory
            DESCRIPTION
                "lp-uneq to ais"
            ::= { e1InsertAisAlmSetupEty 4 }

        e1InstLpPlm-PlmVToAis OBJECT-TYPE
            SYNTAX  INTEGER {
                    disable(1),
                    enable(2)
                }
            ACCESS  read-write
            STATUS  mandatory
            DESCRIPTION
                "lp-plm to ais"
            ::= { e1InsertAisAlmSetupEty 5 }

        e1InstLineLosToAis OBJECT-TYPE
            SYNTAX  INTEGER {
                    disable(1),
                    enable(2)
                }
            ACCESS  read-write
            STATUS  mandatory
            DESCRIPTION
                "line-los to ais"
            ::= { e1InsertAisAlmSetupEty 6 }


--
--  E1 Current Alarm Status Table
--

        e1CurrAlmStatusTab  OBJECT-TYPE
            SYNTAX  SEQUENCE OF E1CurrAlmStatusEty
            ACCESS  not-accessible
            STATUS  mandatory
            DESCRIPTION
                "Current alarm status table"
            ::= { hdE1Alarm 5 }

        e1CurrAlmStatusEty  OBJECT-TYPE
            SYNTAX  E1CurrAlmStatusEty
            ACCESS  not-accessible
            STATUS  mandatory
            DESCRIPTION
                "An entry in the current alarm status table"
            INDEX { e1CurrAlmStsUnit ,
                    e1CurrAlmStsPort }
            ::= { e1CurrAlmStatusTab 1 }

        E1CurrAlmStatusEty ::= SEQUENCE {
            e1CurrAlmStsUnit            UnitID,
            e1CurrAlmStsPort            PortID,
            e1CurrAlmStsLoVT-LOP        AlmStatus,
            e1CurrAlmStsLoVT-AIS        AlmStatus,
            e1CurrAlmStsLoVT-UNEQ       AlmStatus,
            e1CurrAlmStsLoVT-PLM        AlmStatus,
            e1CurrAlmStsLoVT-TIM        AlmStatus,
            e1CurrAlmStsLoVT-RDI-P      AlmStatus,
            e1CurrAlmStsLoVT-RDI-S      AlmStatus,
            e1CurrAlmStsLoVT-RDI-C      AlmStatus,
            e1CurrAlmStsLoVT-V5-REI     AlmStatus,
            e1CurrAlmStsLoVT-V5-BIP     AlmStatus,
            e1CurrAlmStsLine-LOS        AlmStatus,
            e1CurrAlmStsLine-AIS        AlmStatus,
            e1CurrAlmStsLine-UAS        AlmStatus,
            e1CurrAlmStsLine-RAI        AlmStatus
        }

        e1CurrAlmStsUnit  OBJECT-TYPE
            SYNTAX  UnitID
            ACCESS  read-only
            STATUS  mandatory
            DESCRIPTION
            "unit 1 to 4."
            ::= { e1CurrAlmStatusEty 1 }

        e1CurrAlmStsPort  OBJECT-TYPE
            SYNTAX  PortID
            ACCESS  read-only
            STATUS  mandatory
            DESCRIPTION
                "E1 Port 1 to 63"
            ::= { e1CurrAlmStatusEty 2 }

        e1CurrAlmStsLoVT-LOP  OBJECT-TYPE
            SYNTAX  AlmStatus
            ACCESS  read-only
            STATUS  mandatory
            DESCRIPTION
                "tu-lop alarm severity status"
            ::= { e1CurrAlmStatusEty 3 }

        e1CurrAlmStsLoVT-AIS  OBJECT-TYPE
            SYNTAX  AlmStatus
            ACCESS  read-only
            STATUS  mandatory
            DESCRIPTION
                "tu-ais alarm severity status"
            ::= { e1CurrAlmStatusEty 4 }

        e1CurrAlmStsLoVT-UNEQ  OBJECT-TYPE
            SYNTAX  AlmStatus
            ACCESS  read-only
            STATUS  mandatory
            DESCRIPTION
                "lp-uneq alarm severity status"
            ::= { e1CurrAlmStatusEty 5 }

        e1CurrAlmStsLoVT-PLM  OBJECT-TYPE
            SYNTAX  AlmStatus
            ACCESS  read-only
            STATUS  mandatory
            DESCRIPTION
                "lp-plm alarm severity status"
            ::= { e1CurrAlmStatusEty 6 }

        e1CurrAlmStsLoVT-TIM  OBJECT-TYPE
            SYNTAX  AlmStatus
            ACCESS  read-only
            STATUS  mandatory
            DESCRIPTION
                "lp-tim alarm severity status"
            ::= { e1CurrAlmStatusEty 7 }

        e1CurrAlmStsLoVT-RDI-P  OBJECT-TYPE
            SYNTAX  AlmStatus
            ACCESS  read-only
            STATUS  mandatory
            DESCRIPTION
                "lp-rdi-p alarm severity status"
            ::= { e1CurrAlmStatusEty 8 }

        e1CurrAlmStsLoVT-RDI-S  OBJECT-TYPE
            SYNTAX  AlmStatus
            ACCESS  read-only
            STATUS  mandatory
            DESCRIPTION
                "lp-rdi-s alarm severity status"
            ::= { e1CurrAlmStatusEty 9 }

        e1CurrAlmStsLoVT-RDI-C  OBJECT-TYPE
            SYNTAX  AlmStatus
            ACCESS  read-only
            STATUS  mandatory
            DESCRIPTION
                "lp-rdi-c alarm severity status"
            ::= { e1CurrAlmStatusEty 10 }

        e1CurrAlmStsLoVT-V5-REI  OBJECT-TYPE
            SYNTAX  AlmStatus
            ACCESS  read-only
            STATUS  mandatory
            DESCRIPTION
                "lp-rei alarm severity status"
            ::= { e1CurrAlmStatusEty 11 }

        e1CurrAlmStsLoVT-V5-BIP  OBJECT-TYPE
            SYNTAX  AlmStatus
            ACCESS  read-only
            STATUS  mandatory
            DESCRIPTION
                "lp-bip alarm severity status"
            ::= { e1CurrAlmStatusEty 12 }

        e1CurrAlmStsLine-LOS  OBJECT-TYPE
            SYNTAX  AlmStatus
            ACCESS  read-only
            STATUS  mandatory
            DESCRIPTION
                "line-los alarm severity status"
            ::= { e1CurrAlmStatusEty 13 }

        e1CurrAlmStsLine-AIS  OBJECT-TYPE
            SYNTAX  AlmStatus
            ACCESS  read-only
            STATUS  mandatory
            DESCRIPTION
                "line-ais alarm severity status"
            ::= { e1CurrAlmStatusEty 14 }

        e1CurrAlmStsLine-UAS  OBJECT-TYPE
            SYNTAX  AlmStatus
            ACCESS  read-only
            STATUS  mandatory
            DESCRIPTION
                "line-uas alarm severity status"
            ::= { e1CurrAlmStatusEty 15 }

        e1CurrAlmStsLine-RAI  OBJECT-TYPE
            SYNTAX  AlmStatus
            ACCESS  read-only
            STATUS  mandatory
            DESCRIPTION
                "line-rai alarm severity status"
            ::= { e1CurrAlmStatusEty 16 }


--
--  E1 Current Active Alarm Summary Table
--
        e1CurrActAlmSummaryTab  OBJECT-TYPE
            SYNTAX  SEQUENCE OF E1CurrActAlmSummaryEty
            ACCESS  not-accessible
            STATUS  mandatory
            DESCRIPTION
                "E1 Current Active Alarm Summary Table."
            ::= { hdE1Alarm 6 }

        e1CurrActAlmSummaryEty  OBJECT-TYPE
            SYNTAX  E1CurrActAlmSummaryEty
            ACCESS  not-accessible
            STATUS  mandatory
            DESCRIPTION
                "e1 current active alarm summary entry"
            INDEX { e1AlmSumUnit ,
                    e1AlmSumIndex }
            ::= { e1CurrActAlmSummaryTab 1 }

        E1CurrActAlmSummaryEty ::= SEQUENCE {
            e1AlmSumUnit                UnitID,
            e1AlmSumIndex               INTEGER,
            e1AlmSumString              DisplayString (SIZE(0..255)),
            e1AlmSumUnitNum             CardID,
            e1AlmSumCardModel           CardModel,
            e1AlmSumPortNum             PortID,
--             e1AlmSumVcChan
--               INTEGER,
            e1AlmSumAlmNum              AlarmNum,
--             e1AlmSumVC43STS31Type
--               INTEGER,
--             e1AlmSumVC1xVTxTyp
--               INTEGER,
--             e1AlmSumVC4STS3
--               INTEGER,
--             e1AlmSumTUG3
--               INTEGER,
--             e1AlmSumTUG2VTG
--               INTEGER,
--             e1AlmSumVC1xVTx
--               INTEGER,
            e1AlmSumStatus              AlmStatus,
            e1AlmSumSeverity            Severity
        }

        e1AlmSumUnit  OBJECT-TYPE
            SYNTAX  UnitID
            ACCESS  read-only
            STATUS  mandatory
            DESCRIPTION
            "unit 1 to 4."
            ::= { e1CurrActAlmSummaryEty 1 }

        e1AlmSumIndex  OBJECT-TYPE
            SYNTAX  INTEGER
            ACCESS  read-only
            STATUS  mandatory
            DESCRIPTION
                "Select Alarm Summary Index"
            ::= { e1CurrActAlmSummaryEty 2 }

        e1AlmSumString  OBJECT-TYPE
            SYNTAX  DisplayString (SIZE (0..255))
            ACCESS  read-only
            STATUS  mandatory
            DESCRIPTION
                "Alarm Summary String"
            ::= { e1CurrActAlmSummaryEty 3 }

        e1AlmSumUnitNum  OBJECT-TYPE
            SYNTAX  CardID
            ACCESS  read-only
            STATUS  mandatory
            DESCRIPTION
            "Xcu or Unit 1~4,11~16"
            ::= { e1CurrActAlmSummaryEty 4 }

        e1AlmSumCardModel  OBJECT-TYPE
            SYNTAX  CardModel
            ACCESS  read-only
            STATUS  mandatory
            DESCRIPTION
                "Card Model"
            ::= { e1CurrActAlmSummaryEty 5 }

        e1AlmSumPortNum  OBJECT-TYPE
            SYNTAX  PortID
            ACCESS  read-only
            STATUS  mandatory
            DESCRIPTION
                "Port number(1..64)"
            ::= { e1CurrActAlmSummaryEty 6 }

--       e1AlmSumVcChan  OBJECT-TYPE
--           SYNTAX  INTEGER
--           ACCESS  read-only
--           STATUS  mandatory
--           DESCRIPTION
--              "VC Channel"
--           ::= { e1CurrActAlmSummaryEty 7 }

        e1AlmSumAlmNum  OBJECT-TYPE
            SYNTAX  AlarmNum
            ACCESS  read-only
            STATUS  mandatory
            DESCRIPTION
                "Alarm Num"
            ::= { e1CurrActAlmSummaryEty 8 }

--       e1AlmSumVC43STS31Type  OBJECT-TYPE
--           SYNTAX  INTEGER
--           ACCESS  read-only
--           STATUS  mandatory
--           DESCRIPTION
--              "AU4 or AU3 type in SDH, STS-3c or STS-1 type in SONET"
--           ::= { e1CurrActAlmSummaryEty 9 }

--       e1AlmSumVC1xVTxType  OBJECT-TYPE
--           SYNTAX  INTEGER
--           ACCESS  read-only
--           STATUS  mandatory
--           DESCRIPTION
--              "Tu1x type"
--           ::= { e1CurrActAlmSummaryEty 10 }

--       e1AlmSumVC4STS3  OBJECT-TYPE
--           SYNTAX  INTEGER(1..4)
--           ACCESS  read-only
--           STATUS  mandatory
--           DESCRIPTION
--              "The number of STM1"
--           ::= { e1CurrActAlmSummaryEty 11 }

--       e1AlmSumTUG3  OBJECT-TYPE
--           SYNTAX  INTEGER(1..3)
--           ACCESS  read-only
--           STATUS  mandatory
--           DESCRIPTION
--              "The number of Tug3"
--           ::= { e1CurrActAlmSummaryEty 12 }

--       e1AlmSumTUG2VTG  OBJECT-TYPE
--           SYNTAX  INTEGER(1..7)
--           ACCESS  read-only
--           STATUS  mandatory
--           DESCRIPTION
--              "The number of Tug2"
--           ::= { e1CurrActAlmSummaryEty 13 }

--       e1AlmSumVC1xVTx  OBJECT-TYPE
--           SYNTAX  INTEGER(1..4)
--           ACCESS  read-only
--           STATUS  mandatory
--           DESCRIPTION
--              "The number of Tu1x"
--           ::= { e1CurrActAlmSummaryEty 14 }

        e1AlmSumStatus  OBJECT-TYPE
            SYNTAX  AlmStatus
            ACCESS  read-only
            STATUS  mandatory
            DESCRIPTION
                "The Status of Alarm"
            ::= { e1CurrActAlmSummaryEty 15 }

        e1AlmSumSeverity  OBJECT-TYPE
            SYNTAX  Severity
            ACCESS  read-only
            STATUS  mandatory
            DESCRIPTION
                "Alarm Severity"
            ::= { e1CurrActAlmSummaryEty 16 }

--
--  E1 Loopback & Diagnostics
--

    e1LoopbackAndDiagnostics           OBJECT IDENTIFIER ::= { hdE1-card 3 }

--
--  E1 Loopback Setup Table
--

        e1LoopbackSetupTab  OBJECT-TYPE
            SYNTAX  SEQUENCE OF E1LoopbackSetupEty
            ACCESS  not-accessible
            STATUS  mandatory
            DESCRIPTION
                "Loopback setup table"
            ::= { e1LoopbackAndDiagnostics 1 }

        e1LoopbackSetupEty  OBJECT-TYPE
            SYNTAX  E1LoopbackSetupEty
            ACCESS  not-accessible
            STATUS  mandatory
            DESCRIPTION
                "An entry in the loopback setup table"
            INDEX { e1LoopbackUnit ,
                    e1LoopbackPort }
            ::= { e1LoopbackSetupTab 1 }

        E1LoopbackSetupEty ::= SEQUENCE {
            e1LoopbackUnit              UnitID,
            e1LoopbackPort              PortID,
            e1LoopbackLoopbackType      INTEGER
        }

        e1LoopbackUnit  OBJECT-TYPE
            SYNTAX  UnitID
            ACCESS  read-only
            STATUS  mandatory
            DESCRIPTION
            "unit 1 to 4."
            ::= { e1LoopbackSetupEty 1 }

        e1LoopbackPort  OBJECT-TYPE
            SYNTAX  PortID
            ACCESS  read-only
            STATUS  mandatory
            DESCRIPTION
                "E1 Port 1 to 63"
            ::= { e1LoopbackSetupEty 2 }

        e1LoopbackLoopbackType  OBJECT-TYPE
            SYNTAX  INTEGER{
                    off(1),
                    local(2),
                    line(3)
                }
            ACCESS  read-write
            STATUS  mandatory
            DESCRIPTION
                "Loopback type"
            ::= { e1LoopbackSetupEty 3 }


--
--  E1 Diagnostics Setup Table
--

        e1DiagnosticsSetupTab  OBJECT-TYPE
            SYNTAX  SEQUENCE OF E1DiagnosticsSetupEty
            ACCESS  not-accessible
            STATUS  mandatory
            DESCRIPTION
                "Diagnostics setup table"
            ::= { e1LoopbackAndDiagnostics 2 }

        e1DiagnosticsSetupEty  OBJECT-TYPE
            SYNTAX  E1DiagnosticsSetupEty
            ACCESS  not-accessible
            STATUS  mandatory
            DESCRIPTION
                "An entry in the diagnostics setup table"
            INDEX { e1DiagUnit ,
                    e1DiagPort }
            ::= { e1DiagnosticsSetupTab 1 }

        E1DiagnosticsSetupEty ::= SEQUENCE {
            e1DiagUnit                  UnitID,
            e1DiagPort                  PortID,
            e1DiagBertDirection         INTEGER,
            e1DiagBertPattern           INTEGER,
            e1DiagBertAction            INTEGER,
            e1DiagBertStatus            INTEGER,
            e1DiagElapseSecond          INTEGER,
            e1DiagBitError              INTEGER,
            e1DiagErrorSecond           INTEGER,
            e1DiagSevereErrorSecond     INTEGER
        }

        e1DiagUnit  OBJECT-TYPE
            SYNTAX  UnitID
            ACCESS  read-only
            STATUS  mandatory
            DESCRIPTION
            "unit 1 to 4."
            ::= { e1DiagnosticsSetupEty 1 }

        e1DiagPort  OBJECT-TYPE
            SYNTAX  PortID
            ACCESS  read-only
            STATUS  mandatory
            DESCRIPTION
                "E1 Port 1 to 63"
            ::= { e1DiagnosticsSetupEty 2 }

        e1DiagBertDirection  OBJECT-TYPE
            SYNTAX  INTEGER{
                    optical-site(1),
                    line-site(2)
                }
            ACCESS  read-write
            STATUS  mandatory
            DESCRIPTION
                "BERT test direction"
            ::= { e1DiagnosticsSetupEty 3 }

        e1DiagBertPattern  OBJECT-TYPE
            SYNTAX  INTEGER{
                    off(0),
                    patt-2exp11-1(1),
                    patt-2exp15-1(2),
                    patt-2exp20-1(3)
                }
            ACCESS  read-write
            STATUS  mandatory
            DESCRIPTION
                "BERT test pattern"
            ::= { e1DiagnosticsSetupEty 4 }

        e1DiagBertAction  OBJECT-TYPE
            SYNTAX  INTEGER{
                    reset(1)
                }
            ACCESS  read-write
            STATUS  mandatory
            DESCRIPTION
                "BERT test action"
            ::= { e1DiagnosticsSetupEty 5 }

        e1DiagBertStatus  OBJECT-TYPE
            SYNTAX  INTEGER{
                    unsync(1),
                    sync(2)
                }
            ACCESS  read-only
            STATUS  mandatory
            DESCRIPTION
                "BERT status"
            ::= { e1DiagnosticsSetupEty 6 }

        e1DiagElapseSecond  OBJECT-TYPE
            SYNTAX  INTEGER
            ACCESS  read-only
            STATUS  mandatory
            DESCRIPTION
                "BERT elapsed time(s)"
            ::= { e1DiagnosticsSetupEty 7 }

        e1DiagBitError  OBJECT-TYPE
            SYNTAX  INTEGER
            ACCESS  read-only
            STATUS  mandatory
            DESCRIPTION
                "BERT Bit Error"
            ::= { e1DiagnosticsSetupEty 8 }

        e1DiagErrorSecond  OBJECT-TYPE
            SYNTAX  INTEGER
            ACCESS  read-only
            STATUS  mandatory
            DESCRIPTION
                "BERT Error Seconds"
            ::= { e1DiagnosticsSetupEty 9 }

        e1DiagSevereErrorSecond  OBJECT-TYPE
            SYNTAX  INTEGER
            ACCESS  read-only
            STATUS  mandatory
            DESCRIPTION
                "BERT SES"
            ::= { e1DiagnosticsSetupEty 10 }

--
--  E1 Performance
--

    e1Performance           OBJECT IDENTIFIER ::= { hdE1-card 4 }

--
--  E1 Performance Report
--

    e1PerformanceReport           OBJECT IDENTIFIER ::= { e1Performance 1 }

--
--  E1 Performance Report LoPath/VTPath Current Table
--

        e1LoPath-VTPathCurrTab  OBJECT-TYPE
            SYNTAX  SEQUENCE OF E1LoPath-VTPathCurrEty
            ACCESS  not-accessible
            STATUS  mandatory
            DESCRIPTION
                "Performance report current"
            ::= { e1PerformanceReport 1 }

        e1LoPath-VTPathCurrEty  OBJECT-TYPE
            SYNTAX  E1LoPath-VTPathCurrEty
            ACCESS  not-accessible
            STATUS  mandatory
            DESCRIPTION
                "An entry in the performance report current table"
            INDEX { e1LoVTCurrUnit ,
                    e1LoVTCurrPort ,
                    e1LoVTCurrAnomalyType }
            ::= { e1LoPath-VTPathCurrTab 1 }

        E1LoPath-VTPathCurrEty ::= SEQUENCE {
            e1LoVTCurrUnit              UnitID,
            e1LoVTCurrPort              PortID,
            e1LoVTCurrAnomalyType       LoPathPerfAnomalyType,
            e1LoVTCurrEB-Count          INTEGER,
            e1LoVTCurrBBE-Count         INTEGER,
            e1LoVTCurrES-Count          INTEGER,
            e1LoVTCurrUAS-Count         INTEGER,
            e1LoVTCurrBES-Count         INTEGER,
            e1LoVTCurrSES-Count         INTEGER,
            e1LoVTCurr15MinTimeElaps    INTEGER,
            e1LoVTCurr24hrValid15Min    INTEGER,
            e1LoVTCurrDayValid15Min     INTEGER,
            e1LoVTCurr7DayValidDays     INTEGER
        }

        e1LoVTCurrUnit  OBJECT-TYPE
            SYNTAX  UnitID
            ACCESS  read-only
            STATUS  mandatory
            DESCRIPTION
            "unit 1 to 4."
            ::= { e1LoPath-VTPathCurrEty 1 }

        e1LoVTCurrPort  OBJECT-TYPE
            SYNTAX  PortID
            ACCESS  read-only
            STATUS  mandatory
            DESCRIPTION
                "E1 Port 1 to 63"
            ::= { e1LoPath-VTPathCurrEty 2 }

        e1LoVTCurrAnomalyType  OBJECT-TYPE
            SYNTAX  LoPathPerfAnomalyType
            ACCESS  read-only
            STATUS  mandatory
            DESCRIPTION
                "Performance report LoPath/VTPath Anomaly Type"
            ::= { e1LoPath-VTPathCurrEty 3 }

        e1LoVTCurrEB-Count  OBJECT-TYPE
            SYNTAX  INTEGER
            ACCESS  read-only
            STATUS  mandatory
            DESCRIPTION
                "Current Error Block"
            ::= { e1LoPath-VTPathCurrEty 4 }

        e1LoVTCurrBBE-Count  OBJECT-TYPE
            SYNTAX  INTEGER
            ACCESS  read-only
            STATUS  mandatory
            DESCRIPTION
                "Current Background Block Error"
            ::= { e1LoPath-VTPathCurrEty 5 }

        e1LoVTCurrES-Count  OBJECT-TYPE
            SYNTAX  INTEGER
            ACCESS  read-only
            STATUS  mandatory
            DESCRIPTION
                "Error Second"
            ::= { e1LoPath-VTPathCurrEty 6 }

        e1LoVTCurrUAS-Count  OBJECT-TYPE
            SYNTAX  INTEGER
            ACCESS  read-only
            STATUS  mandatory
            DESCRIPTION
                "Unavailable Second"
            ::= { e1LoPath-VTPathCurrEty 7 }

        e1LoVTCurrBES-Count  OBJECT-TYPE
            SYNTAX  INTEGER
            ACCESS  read-only
            STATUS  mandatory
            DESCRIPTION
                "Background Error Second"
            ::= { e1LoPath-VTPathCurrEty 8 }

        e1LoVTCurrSES-Count  OBJECT-TYPE
            SYNTAX  INTEGER
            ACCESS  read-only
            STATUS  mandatory
            DESCRIPTION
                "Severly Error Second"
            ::= { e1LoPath-VTPathCurrEty 9 }

        e1LoVTCurr15MinTimeElaps  OBJECT-TYPE
            SYNTAX  INTEGER
            ACCESS  read-only
            STATUS  mandatory
            DESCRIPTION
                "Valid Seconds in Current 15-Min Interval"
            ::= { e1LoPath-VTPathCurrEty 10 }

        e1LoVTCurr24hrValid15Min  OBJECT-TYPE
            SYNTAX  INTEGER
            ACCESS  read-only
            STATUS  mandatory
            DESCRIPTION
                "Valid 15-Min Intervals in Current 24-Hour Interval"
            ::= { e1LoPath-VTPathCurrEty 11 }

        e1LoVTCurrDayValid15Min  OBJECT-TYPE
            SYNTAX  INTEGER
            ACCESS  read-only
            STATUS  mandatory
            DESCRIPTION
                "Valid 15-Min Intervals in Current Day"
            ::= { e1LoPath-VTPathCurrEty 12 }

        e1LoVTCurr7DayValidDays  OBJECT-TYPE
            SYNTAX  INTEGER
            ACCESS  read-only
            STATUS  mandatory
            DESCRIPTION
                "Valid Days in Current Seven Day"
            ::= { e1LoPath-VTPathCurrEty 13 }


--
--  E1 Performance Report LoPath/VTPath Interval Table
--

        e1LoPath-VTPathIntvTab  OBJECT-TYPE
            SYNTAX  SEQUENCE OF E1LoPath-VTPathIntvEty
            ACCESS  not-accessible
            STATUS  mandatory
            DESCRIPTION
                "Performance report Inteval"
            ::= { e1PerformanceReport 2 }

        e1LoPath-VTPathIntvEty  OBJECT-TYPE
            SYNTAX  E1LoPath-VTPathIntvEty
            ACCESS  not-accessible
            STATUS  mandatory
            DESCRIPTION
                "An entry in the performance report interval table"
            INDEX { e1LoVTIntvUnit ,
                    e1LoVTIntvPort ,
                    e1LoVTIntvAnomalyType ,
                    e1LoVTIntvPeriod }
            ::= { e1LoPath-VTPathIntvTab 1 }

        E1LoPath-VTPathIntvEty ::= SEQUENCE {
            e1LoVTIntvUnit              UnitID,
            e1LoVTIntvPort              PortID,
            e1LoVTIntvAnomalyType       LoPathPerfAnomalyType,
            e1LoVTIntvPeriod            INTEGER (1..96),
            e1LoVTIntvEB-Count          INTEGER,
            e1LoVTIntvBBE-Count         INTEGER,
            e1LoVTIntvES-Count          INTEGER,
            e1LoVTIntvUAS-Count         INTEGER,
            e1LoVTIntvBES-Count         INTEGER,
            e1LoVTIntvSES-Count         INTEGER
        }

        e1LoVTIntvUnit  OBJECT-TYPE
            SYNTAX  UnitID
            ACCESS  read-only
            STATUS  mandatory
            DESCRIPTION
            "unit 1 to 4."
            ::= { e1LoPath-VTPathIntvEty 1 }

        e1LoVTIntvPort  OBJECT-TYPE
            SYNTAX  PortID
            ACCESS  read-only
            STATUS  mandatory
            DESCRIPTION
                "E1 Port 1 to 63"
            ::= { e1LoPath-VTPathIntvEty 2 }

        e1LoVTIntvAnomalyType  OBJECT-TYPE
            SYNTAX  LoPathPerfAnomalyType
            ACCESS  read-only
            STATUS  mandatory
            DESCRIPTION
                "Performance report LoPath/VTPath Anomaly Type"
            ::= { e1LoPath-VTPathIntvEty 3 }

        e1LoVTIntvPeriod  OBJECT-TYPE
            SYNTAX  INTEGER (1..96)
            ACCESS  read-only
            STATUS  mandatory
            DESCRIPTION
                "LoPath Interval Period"
            ::= { e1LoPath-VTPathIntvEty 4 }

        e1LoVTIntvEB-Count  OBJECT-TYPE
            SYNTAX  INTEGER
            ACCESS  read-only
            STATUS  mandatory
            DESCRIPTION
                "Current Error Block"
            ::= { e1LoPath-VTPathIntvEty 5 }

        e1LoVTIntvBBE-Count  OBJECT-TYPE
            SYNTAX  INTEGER
            ACCESS  read-only
            STATUS  mandatory
            DESCRIPTION
                "Current Background Block Error"
            ::= { e1LoPath-VTPathIntvEty 6 }

        e1LoVTIntvES-Count  OBJECT-TYPE
            SYNTAX  INTEGER
            ACCESS  read-only
            STATUS  mandatory
            DESCRIPTION
                "Error Second"
            ::= { e1LoPath-VTPathIntvEty 7 }

        e1LoVTIntvUAS-Count  OBJECT-TYPE
            SYNTAX  INTEGER
            ACCESS  read-only
            STATUS  mandatory
            DESCRIPTION
                "Unavailable Second"
            ::= { e1LoPath-VTPathIntvEty 8 }

        e1LoVTIntvBES-Count  OBJECT-TYPE
            SYNTAX  INTEGER
            ACCESS  read-only
            STATUS  mandatory
            DESCRIPTION
                "Background Error Second"
            ::= { e1LoPath-VTPathIntvEty 9 }

        e1LoVTIntvSES-Count  OBJECT-TYPE
            SYNTAX  INTEGER
            ACCESS  read-only
            STATUS  mandatory
            DESCRIPTION
                "Severly Error Second"
            ::= { e1LoPath-VTPathIntvEty 10 }


--
--  E1 Performance Report LoPath/VT-Path Seven Days Table
--

        e1LoPath-VTPath7DaysTab  OBJECT-TYPE
            SYNTAX  SEQUENCE OF E1LoPath-VTPath7DaysEty
            ACCESS  not-accessible
            STATUS  mandatory
            DESCRIPTION
                "Performance report Seven Days"
            ::= { e1PerformanceReport 3 }

        e1LoPath-VTPath7DaysEty  OBJECT-TYPE
            SYNTAX  E1LoPath-VTPath7DaysEty
            ACCESS  not-accessible
            STATUS  mandatory
            DESCRIPTION
                "An entry in the performance report seven days table"
            INDEX { e1LoVT7DaysUnit ,
                    e1LoVT7DaysPort ,
                    e1LoVT7DaysAnomalyType ,
                    e1LoVT7DaysDayIndex }
            ::= { e1LoPath-VTPath7DaysTab 1 }

        E1LoPath-VTPath7DaysEty ::= SEQUENCE {
            e1LoVT7DaysUnit             UnitID,
            e1LoVT7DaysPort             PortID,
            e1LoVT7DaysAnomalyType      LoPathPerfAnomalyType,
            e1LoVT7DaysDayIndex         INTEGER (1..7),
            e1LoVT7DaysDate             DisplayString (SIZE (0..255) ),
            e1LoVT7DaysEB-Count         INTEGER,
            e1LoVT7DaysBBE-Count        INTEGER,
            e1LoVT7DaysES-Count         INTEGER,
            e1LoVT7DaysUAS-Count        INTEGER,
            e1LoVT7DaysBES-Count        INTEGER,
            e1LoVT7DaysSES-Count        INTEGER
        }

        e1LoVT7DaysUnit  OBJECT-TYPE
            SYNTAX  UnitID
            ACCESS  read-only
            STATUS  mandatory
            DESCRIPTION
            "unit 1 to 4."
            ::= { e1LoPath-VTPath7DaysEty 1 }

        e1LoVT7DaysPort  OBJECT-TYPE
            SYNTAX  PortID
            ACCESS  read-only
            STATUS  mandatory
            DESCRIPTION
                "E1 Port 1 to 63"
            ::= { e1LoPath-VTPath7DaysEty 2 }

        e1LoVT7DaysAnomalyType  OBJECT-TYPE
            SYNTAX  LoPathPerfAnomalyType
            ACCESS  read-only
            STATUS  mandatory
            DESCRIPTION
                "Performance report LoPath/VTPath Anomaly Type"
            ::= { e1LoPath-VTPath7DaysEty 3 }

        e1LoVT7DaysDayIndex  OBJECT-TYPE
            SYNTAX  INTEGER (1..7)
            ACCESS  read-only
            STATUS  mandatory
            DESCRIPTION
                "LoPath Seven Days day index"
            ::= { e1LoPath-VTPath7DaysEty 4 }

        e1LoVT7DaysDate  OBJECT-TYPE
            SYNTAX  DisplayString (SIZE (0..255) )
            ACCESS  read-only
            STATUS  mandatory
            DESCRIPTION
                "Seven Days Date"
            ::= { e1LoPath-VTPath7DaysEty 5 }

        e1LoVT7DaysEB-Count  OBJECT-TYPE
            SYNTAX  INTEGER
            ACCESS  read-only
            STATUS  mandatory
            DESCRIPTION
                "Current Error Block"
            ::= { e1LoPath-VTPath7DaysEty 6 }

        e1LoVT7DaysBBE-Count  OBJECT-TYPE
            SYNTAX  INTEGER
            ACCESS  read-only
            STATUS  mandatory
            DESCRIPTION
                "Current Background Block Error"
            ::= { e1LoPath-VTPath7DaysEty 7 }

        e1LoVT7DaysES-Count  OBJECT-TYPE
            SYNTAX  INTEGER
            ACCESS  read-only
            STATUS  mandatory
            DESCRIPTION
                "Error Second"
            ::= { e1LoPath-VTPath7DaysEty 8 }

        e1LoVT7DaysUAS-Count  OBJECT-TYPE
            SYNTAX  INTEGER
            ACCESS  read-only
            STATUS  mandatory
            DESCRIPTION
                "Unavailable Second"
            ::= { e1LoPath-VTPath7DaysEty 9 }

        e1LoVT7DaysBES-Count  OBJECT-TYPE
            SYNTAX  INTEGER
            ACCESS  read-only
            STATUS  mandatory
            DESCRIPTION
                "Background Error Second"
            ::= { e1LoPath-VTPath7DaysEty 10 }

        e1LoVT7DaysSES-Count  OBJECT-TYPE
            SYNTAX  INTEGER
            ACCESS  read-only
            STATUS  mandatory
            DESCRIPTION
                "Severly Error Second"
            ::= { e1LoPath-VTPath7DaysEty 11 }


--
--  E1 Performance Report LoPath/VTPath Total Table
--

        e1LoPath-VTPathTotalTab  OBJECT-TYPE
            SYNTAX  SEQUENCE OF E1LoPath-VTPathTotalEty
            ACCESS  not-accessible
            STATUS  mandatory
            DESCRIPTION
                "Performance report Total"
            ::= { e1PerformanceReport 4 }

        e1LoPath-VTPathTotalEty  OBJECT-TYPE
            SYNTAX  E1LoPath-VTPathTotalEty
            ACCESS  not-accessible
            STATUS  mandatory
            DESCRIPTION
                "An entry in the performance report total table"
            INDEX { e1LoVTTotalUnit ,
                    e1LoVTTotalPort ,
                    e1LoVTTotalAnomalyType }
            ::= { e1LoPath-VTPathTotalTab 1 }

        E1LoPath-VTPathTotalEty ::= SEQUENCE {
            e1LoVTTotalUnit             UnitID,
            e1LoVTTotalPort             PortID,
            e1LoVTTotalAnomalyType      LoPathPerfAnomalyType,
            e1LoVTTotalEB-Count         INTEGER,
            e1LoVTTotalBBE-Count        INTEGER,
            e1LoVTTotalES-Count         INTEGER,
            e1LoVTTotalUAS-Count        INTEGER,
            e1LoVTTotalBES-Count        INTEGER,
            e1LoVTTotalSES-Count        INTEGER
        }

        e1LoVTTotalUnit  OBJECT-TYPE
            SYNTAX  UnitID
            ACCESS  read-only
            STATUS  mandatory
            DESCRIPTION
            "unit 1 to 4."
            ::= { e1LoPath-VTPathTotalEty 1 }

        e1LoVTTotalPort  OBJECT-TYPE
            SYNTAX  PortID
            ACCESS  read-only
            STATUS  mandatory
            DESCRIPTION
                "E1 Port 1 to 63"
            ::= { e1LoPath-VTPathTotalEty 2 }

        e1LoVTTotalAnomalyType  OBJECT-TYPE
            SYNTAX  LoPathPerfAnomalyType
            ACCESS  read-only
            STATUS  mandatory
            DESCRIPTION
                "Performance report LoPath/VTPath Anomaly Type"
            ::= { e1LoPath-VTPathTotalEty 3 }

        e1LoVTTotalEB-Count  OBJECT-TYPE
            SYNTAX  INTEGER
            ACCESS  read-only
            STATUS  mandatory
            DESCRIPTION
                "Current Error Block"
            ::= { e1LoPath-VTPathTotalEty 4 }

        e1LoVTTotalBBE-Count  OBJECT-TYPE
            SYNTAX  INTEGER
            ACCESS  read-only
            STATUS  mandatory
            DESCRIPTION
                "Current Background Block Error"
            ::= { e1LoPath-VTPathTotalEty 5 }

        e1LoVTTotalES-Count  OBJECT-TYPE
            SYNTAX  INTEGER
            ACCESS  read-only
            STATUS  mandatory
            DESCRIPTION
                "Error Second"
            ::= { e1LoPath-VTPathTotalEty 6 }

        e1LoVTTotalUAS-Count  OBJECT-TYPE
            SYNTAX  INTEGER
            ACCESS  read-only
            STATUS  mandatory
            DESCRIPTION
                "Unavailable Second"
            ::= { e1LoPath-VTPathTotalEty 7 }

        e1LoVTTotalBES-Count  OBJECT-TYPE
            SYNTAX  INTEGER
            ACCESS  read-only
            STATUS  mandatory
            DESCRIPTION
                "Background Error Second"
            ::= { e1LoPath-VTPathTotalEty 8 }

        e1LoVTTotalSES-Count  OBJECT-TYPE
            SYNTAX  INTEGER
            ACCESS  read-only
            STATUS  mandatory
            DESCRIPTION
                "Severly Error Second"
            ::= { e1LoPath-VTPathTotalEty 9 }

--
--  E1 Performance Report Line Current Table
--

        e1LineCurrTab  OBJECT-TYPE
            SYNTAX  SEQUENCE OF E1LineCurrEty
            ACCESS  not-accessible
            STATUS  mandatory
            DESCRIPTION
                "Performance report current"
            ::= { e1PerformanceReport 5 }

        e1LineCurrEty  OBJECT-TYPE
            SYNTAX  E1LineCurrEty
            ACCESS  not-accessible
            STATUS  mandatory
            DESCRIPTION
                "An entry in the performance report current table"
            INDEX { e1LineCurrUnit ,
                    e1LineCurrPort }
            ::= { e1LineCurrTab 1 }

        E1LineCurrEty ::= SEQUENCE {
            e1LineCurrUnit              UnitID,
            e1LineCurrPort              PortID,
            e1LineCurrES-Count          INTEGER,
            e1LineCurrUAS-Count         INTEGER,
            e1LineCurrBES-Count         INTEGER,
            e1LineCurrSES-Count         INTEGER,
            e1LineCurrBPV-Count         INTEGER,
            e1LineCurr15MinTimeElaps    INTEGER,
            e1LineCurr24hrValid15Min    INTEGER,
            e1LineCurrDayValid15Min     INTEGER,
            e1LineCurr7DayValidDays     INTEGER
        }

        e1LineCurrUnit  OBJECT-TYPE
            SYNTAX  UnitID
            ACCESS  read-only
            STATUS  mandatory
            DESCRIPTION
            "unit 1 to 4."
            ::= { e1LineCurrEty 1 }

        e1LineCurrPort  OBJECT-TYPE
            SYNTAX  PortID
            ACCESS  read-only
            STATUS  mandatory
            DESCRIPTION
                "E1 Port 1 to 63"
            ::= { e1LineCurrEty 2 }


        e1LineCurrES-Count  OBJECT-TYPE
            SYNTAX  INTEGER
            ACCESS  read-only
            STATUS  mandatory
            DESCRIPTION
                "Error Second"
            ::= { e1LineCurrEty 3 }

        e1LineCurrUAS-Count  OBJECT-TYPE
            SYNTAX  INTEGER
            ACCESS  read-only
            STATUS  mandatory
            DESCRIPTION
                "Unavailable Second"
            ::= { e1LineCurrEty 4 }

        e1LineCurrBES-Count  OBJECT-TYPE
            SYNTAX  INTEGER
            ACCESS  read-only
            STATUS  mandatory
            DESCRIPTION
                "Background Error Second"
            ::= { e1LineCurrEty 5 }

        e1LineCurrSES-Count  OBJECT-TYPE
            SYNTAX  INTEGER
            ACCESS  read-only
            STATUS  mandatory
            DESCRIPTION
                "Severly Error Second"
            ::= { e1LineCurrEty 6 }

        e1LineCurrBPV-Count  OBJECT-TYPE
            SYNTAX  INTEGER
            ACCESS  read-only
            STATUS  mandatory
            DESCRIPTION
                "Bipolar Violation"
            ::= { e1LineCurrEty 7 }

        e1LineCurr15MinTimeElaps  OBJECT-TYPE
            SYNTAX  INTEGER
            ACCESS  read-only
            STATUS  mandatory
            DESCRIPTION
                "Valid Seconds in Current 15-Min Interval"
            ::= { e1LineCurrEty 8 }

        e1LineCurr24hrValid15Min  OBJECT-TYPE
            SYNTAX  INTEGER
            ACCESS  read-only
            STATUS  mandatory
            DESCRIPTION
                "Valid 15-Min Intervals in Current 24-Hour Interval"
            ::= { e1LineCurrEty 9 }

        e1LineCurrDayValid15Min  OBJECT-TYPE
            SYNTAX  INTEGER
            ACCESS  read-only
            STATUS  mandatory
            DESCRIPTION
                "Valid 15-Min Intervals in Current Day"
            ::= { e1LineCurrEty 10 }

        e1LineCurr7DayValidDays  OBJECT-TYPE
            SYNTAX  INTEGER
            ACCESS  read-only
            STATUS  mandatory
            DESCRIPTION
                "Valid Days in Current Seven Day"
            ::= { e1LineCurrEty 11 }


--
--  E1 Performance Report Line Interval Table
--

        e1LineIntervalTab  OBJECT-TYPE
            SYNTAX  SEQUENCE OF E1LineIntervalEty
            ACCESS  not-accessible
            STATUS  mandatory
            DESCRIPTION
                "Performance report Inteval"
            ::= { e1PerformanceReport 6 }

        e1LineIntervalEty  OBJECT-TYPE
            SYNTAX  E1LineIntervalEty
            ACCESS  not-accessible
            STATUS  mandatory
            DESCRIPTION
                "An entry in the performance report interval table"
            INDEX { e1LineIntvUnit ,
                    e1LineIntvPort ,
                    e1LineIntvPeriod }
            ::= { e1LineIntervalTab 1 }

        E1LineIntervalEty ::= SEQUENCE {
            e1LineIntvUnit              UnitID,
            e1LineIntvPort              PortID,
            e1LineIntvPeriod            INTEGER (1..96),
            e1LineIntvES-Count          INTEGER,
            e1LineIntvUAS-Count         INTEGER,
            e1LineIntvBES-Count         INTEGER,
            e1LineIntvSES-Count         INTEGER,
            e1LineIntvBPV-Count         INTEGER
        }

        e1LineIntvUnit  OBJECT-TYPE
            SYNTAX  UnitID
            ACCESS  read-only
            STATUS  mandatory
            DESCRIPTION
            "unit 1 to 4."
            ::= { e1LineIntervalEty 1 }

        e1LineIntvPort  OBJECT-TYPE
            SYNTAX  PortID
            ACCESS  read-only
            STATUS  mandatory
            DESCRIPTION
                "E1 Port 1 to 63"
            ::= { e1LineIntervalEty 2 }

        e1LineIntvPeriod  OBJECT-TYPE
            SYNTAX  INTEGER (1..96)
            ACCESS  read-only
            STATUS  mandatory
            DESCRIPTION
                "Line Interval Period"
            ::= { e1LineIntervalEty 3 }

        e1LineIntvES-Count  OBJECT-TYPE
            SYNTAX  INTEGER
            ACCESS  read-only
            STATUS  mandatory
            DESCRIPTION
                "Error Second"
            ::= { e1LineIntervalEty 4 }

        e1LineIntvUAS-Count  OBJECT-TYPE
            SYNTAX  INTEGER
            ACCESS  read-only
            STATUS  mandatory
            DESCRIPTION
                "Unavailable Second"
            ::= { e1LineIntervalEty 5 }

        e1LineIntvBES-Count  OBJECT-TYPE
            SYNTAX  INTEGER
            ACCESS  read-only
            STATUS  mandatory
            DESCRIPTION
                "Background Error Second"
            ::= { e1LineIntervalEty 6 }

        e1LineIntvSES-Count  OBJECT-TYPE
            SYNTAX  INTEGER
            ACCESS  read-only
            STATUS  mandatory
            DESCRIPTION
                "Severly Error Second"
            ::= { e1LineIntervalEty 7 }

        e1LineIntvBPV-Count  OBJECT-TYPE
            SYNTAX  INTEGER
            ACCESS  read-only
            STATUS  mandatory
            DESCRIPTION
                "Bipolar Violation"
            ::= { e1LineIntervalEty 8 }

--
--  E1 Performance Report Line Seven Days Table
--

        e1Line7DaysTab  OBJECT-TYPE
            SYNTAX  SEQUENCE OF E1Line7DaysEty
            ACCESS  not-accessible
            STATUS  mandatory
            DESCRIPTION
                "Performance report seven days"
            ::= { e1PerformanceReport 7 }

        e1Line7DaysEty  OBJECT-TYPE
            SYNTAX  E1Line7DaysEty
            ACCESS  not-accessible
            STATUS  mandatory
            DESCRIPTION
                "An entry in the performance report seven days table"
            INDEX { e1Line7DaysUnit ,
                    e1Line7DaysPort ,
                    e1Line7DaysDayIndex }
            ::= { e1Line7DaysTab 1 }

        E1Line7DaysEty ::= SEQUENCE {
            e1Line7DaysUnit             UnitID,
            e1Line7DaysPort             PortID,
            e1Line7DaysDayIndex         INTEGER (1..7),
            e1Line7DaysDate             DisplayString (SIZE (0..255) ),
            e1Line7DaysES-Count         INTEGER,
            e1Line7DaysUAS-Count        INTEGER,
            e1Line7DaysBES-Count        INTEGER,
            e1Line7DaysSES-Count        INTEGER,
            e1Line7DaysBPV-Count        INTEGER
        }

        e1Line7DaysUnit  OBJECT-TYPE
            SYNTAX  UnitID
            ACCESS  read-only
            STATUS  mandatory
            DESCRIPTION
            "unit 1 to 4."
            ::= { e1Line7DaysEty 1 }

        e1Line7DaysPort  OBJECT-TYPE
            SYNTAX  PortID
            ACCESS  read-only
            STATUS  mandatory
            DESCRIPTION
                "E1 Port 1 to 63"
            ::= { e1Line7DaysEty 2 }

        e1Line7DaysDayIndex  OBJECT-TYPE
            SYNTAX  INTEGER (1..7)
            ACCESS  read-only
            STATUS  mandatory
            DESCRIPTION
                "Line Seven Days day index"
            ::= { e1Line7DaysEty 3 }

        e1Line7DaysDate  OBJECT-TYPE
            SYNTAX  DisplayString (SIZE (0..255) )
            ACCESS  read-only
            STATUS  mandatory
            DESCRIPTION
                "Seven Days Date"
            ::= { e1Line7DaysEty 4 }

        e1Line7DaysES-Count  OBJECT-TYPE
            SYNTAX  INTEGER
            ACCESS  read-only
            STATUS  mandatory
            DESCRIPTION
                "Error Second"
            ::= { e1Line7DaysEty 5 }

        e1Line7DaysUAS-Count  OBJECT-TYPE
            SYNTAX  INTEGER
            ACCESS  read-only
            STATUS  mandatory
            DESCRIPTION
                "Unavailable Second"
            ::= { e1Line7DaysEty 6 }

        e1Line7DaysBES-Count  OBJECT-TYPE
            SYNTAX  INTEGER
            ACCESS  read-only
            STATUS  mandatory
            DESCRIPTION
                "Background Error Second"
            ::= { e1Line7DaysEty 7 }

        e1Line7DaysSES-Count  OBJECT-TYPE
            SYNTAX  INTEGER
            ACCESS  read-only
            STATUS  mandatory
            DESCRIPTION
                "Severly Error Second"
            ::= { e1Line7DaysEty 8 }

        e1Line7DaysBPV-Count  OBJECT-TYPE
            SYNTAX  INTEGER
            ACCESS  read-only
            STATUS  mandatory
            DESCRIPTION
                "Bipolar Violation"
            ::= { e1Line7DaysEty 9 }


--
--  E1 Performance Report Line Total Table
--

        e1LineTotalTab  OBJECT-TYPE
            SYNTAX  SEQUENCE OF E1LineTotalEty
            ACCESS  not-accessible
            STATUS  mandatory
            DESCRIPTION
                "Performance report Total"
            ::= { e1PerformanceReport 8 }

        e1LineTotalEty  OBJECT-TYPE
            SYNTAX  E1LineTotalEty
            ACCESS  not-accessible
            STATUS  mandatory
            DESCRIPTION
                "An entry in the performance report total table"
            INDEX { e1LineTotalUnit ,
                    e1LineTotalPort }
            ::= { e1LineTotalTab 1 }

        E1LineTotalEty ::= SEQUENCE {
            e1LineTotalUnit             UnitID,
            e1LineTotalPort             PortID,
            e1LineTotalES-Count         INTEGER,
            e1LineTotalUAS-Count        INTEGER,
            e1LineTotalBES-Count        INTEGER,
            e1LineTotalSES-Count        INTEGER,
            e1LineTotalBPV-Count        INTEGER
        }

        e1LineTotalUnit  OBJECT-TYPE
            SYNTAX  UnitID
            ACCESS  read-only
            STATUS  mandatory
            DESCRIPTION
            "unit 1 to 4."
            ::= { e1LineTotalEty 1 }

        e1LineTotalPort  OBJECT-TYPE
            SYNTAX  PortID
            ACCESS  read-only
            STATUS  mandatory
            DESCRIPTION
                "E1 Port 1 to 63"
            ::= { e1LineTotalEty 2 }

        e1LineTotalES-Count  OBJECT-TYPE
            SYNTAX  INTEGER
            ACCESS  read-only
            STATUS  mandatory
            DESCRIPTION
                "Error Second"
            ::= { e1LineTotalEty 3 }

        e1LineTotalUAS-Count  OBJECT-TYPE
            SYNTAX  INTEGER
            ACCESS  read-only
            STATUS  mandatory
            DESCRIPTION
                "Unavailable Second"
            ::= { e1LineTotalEty 4 }

        e1LineTotalBES-Count  OBJECT-TYPE
            SYNTAX  INTEGER
            ACCESS  read-only
            STATUS  mandatory
            DESCRIPTION
                "Background Error Second"
            ::= { e1LineTotalEty 5 }

        e1LineTotalSES-Count  OBJECT-TYPE
            SYNTAX  INTEGER
            ACCESS  read-only
            STATUS  mandatory
            DESCRIPTION
                "Severly Error Second"
            ::= { e1LineTotalEty 6 }

        e1LineTotalBPV-Count  OBJECT-TYPE
            SYNTAX  INTEGER
            ACCESS  read-only
            STATUS  mandatory
            DESCRIPTION
                "Bipolar Violation"
            ::= { e1LineTotalEty 7 }

--
--  E1 Performance Threshold Setup Table
--

        e1PerfThreshSetupTab  OBJECT-TYPE
            SYNTAX  SEQUENCE OF E1PerfThreshSetupEty
            ACCESS  not-accessible
            STATUS  mandatory
            DESCRIPTION
                "Performance threshold setup"
            ::= { e1Performance 2 }

        e1PerfThreshSetupEty  OBJECT-TYPE
            SYNTAX  E1PerfThreshSetupEty
            ACCESS  not-accessible
            STATUS  mandatory
            DESCRIPTION
                "An entry in the performance threshold setup table"
            INDEX { e1PerfTCAUnit ,
                    e1PerfTCAMonitorPoint }
            ::= { e1PerfThreshSetupTab 1 }

        E1PerfThreshSetupEty ::= SEQUENCE {
            e1PerfTCAUnit               UnitID,
            e1PerfTCAMonitorPoint       INTEGER,
            e1PerfTCAEnable             INTEGER,
            e1PerfTCASeverity           Severity,
            e1PerfTCAThreshold          INTEGER
        }

        e1PerfTCAUnit  OBJECT-TYPE
            SYNTAX  UnitID
            ACCESS  read-only
            STATUS  mandatory
            DESCRIPTION
            "unit 1 to 4."
            ::= { e1PerfThreshSetupEty 1 }

        e1PerfTCAMonitorPoint  OBJECT-TYPE
            SYNTAX  INTEGER {
                    bip(1),
                    rei(2),
                    bpv(3)
                }
            ACCESS  read-only
            STATUS  mandatory
            DESCRIPTION
                "TCA monitor point index"
            ::= { e1PerfThreshSetupEty 2 }

        e1PerfTCAEnable  OBJECT-TYPE
            SYNTAX  INTEGER {
                    disable(1),
                    enable(2)
                }
            ACCESS  read-write
            STATUS  mandatory
            DESCRIPTION
                "TCA disable/enable"
            ::= { e1PerfThreshSetupEty 3 }

        e1PerfTCASeverity  OBJECT-TYPE
            SYNTAX  Severity
            ACCESS  read-write
            STATUS  mandatory
            DESCRIPTION
                "TCA Severity"
            ::= { e1PerfThreshSetupEty 4 }

        e1PerfTCAThreshold  OBJECT-TYPE
            SYNTAX  INTEGER (1..99999)
            ACCESS  read-write
            STATUS  mandatory
            DESCRIPTION
                "TCA threshold"
            ::= { e1PerfThreshSetupEty 5 }


--
--  E1 Performance Line Monitor Framer Setup Table
--

        e1LineMonFramerSetupTab  OBJECT-TYPE
            SYNTAX  SEQUENCE OF E1LineMonFramerSetupEty
            ACCESS  not-accessible
            STATUS  mandatory
            DESCRIPTION
                "Performance line monitor framer setup"
            ::= { e1Performance 3 }

        e1LineMonFramerSetupEty  OBJECT-TYPE
            SYNTAX  E1LineMonFramerSetupEty
            ACCESS  not-accessible
            STATUS  mandatory
            DESCRIPTION
                "An entry in the performance line monitor framer setup table"
            INDEX { e1LineMonFramerUnit ,
                    e1LineMonFramerPort }
            ::= { e1LineMonFramerSetupTab 1 }

        E1LineMonFramerSetupEty ::= SEQUENCE {
            e1LineMonFramerUnit         UnitID,
            e1LineMonFramerPort         PortID,
            e1LineMonFramerFrame        INTEGER,
            e1LineMonFramerCRC          INTEGER,
            e1LineMonFramerCAS          INTEGER
        }

        e1LineMonFramerUnit  OBJECT-TYPE
            SYNTAX  UnitID
            ACCESS  read-only
            STATUS  mandatory
            DESCRIPTION
            "unit 1 to 4."
            ::= { e1LineMonFramerSetupEty 1 }

        e1LineMonFramerPort  OBJECT-TYPE
            SYNTAX  PortID
            ACCESS  read-only
            STATUS  mandatory
            DESCRIPTION
                "E1 Port 1 to 63"
            ::= { e1LineMonFramerSetupEty 2 }

        e1LineMonFramerFrame  OBJECT-TYPE
            SYNTAX  INTEGER {
                    off(1),
                    on(2)
                }
            ACCESS  read-write
            STATUS  mandatory
            DESCRIPTION
                "E1 line frame mode"
            ::= { e1LineMonFramerSetupEty 3 }

        e1LineMonFramerCRC  OBJECT-TYPE
            SYNTAX  INTEGER {
                    off(1),
                    on(2)
                }
            ACCESS  read-write
            STATUS  mandatory
            DESCRIPTION
                "E1 line cycle Redundancy check"
            ::= { e1LineMonFramerSetupEty 4 }

        e1LineMonFramerCAS  OBJECT-TYPE
            SYNTAX  INTEGER {
                    off(1),
                    on(2)
                }
            ACCESS  read-write
            STATUS  mandatory
            DESCRIPTION
                "E1 Line CAS"
            ::= { e1LineMonFramerSetupEty 5 }

--
--  E1 Performance Control Setup Table
--

        e1PerfControlTab  OBJECT-TYPE
            SYNTAX  SEQUENCE OF E1PerfControlEty
            ACCESS  not-accessible
            STATUS  mandatory
            DESCRIPTION
                "Performance control"
            ::= { e1Performance 4 }

        e1PerfControlEty  OBJECT-TYPE
            SYNTAX  E1PerfControlEty
            ACCESS  not-accessible
            STATUS  mandatory
            DESCRIPTION
                "An entry in the performance control table"
            INDEX { e1PerfCtrlUnit }
            ::= { e1PerfControlTab 1 }

        E1PerfControlEty ::= SEQUENCE {
            e1PerfCtrlUnit              UnitID,
            e1PerfCtrlClearPerf         INTEGER
        }

        e1PerfCtrlUnit  OBJECT-TYPE
            SYNTAX  UnitID
            ACCESS  read-only
            STATUS  mandatory
            DESCRIPTION
            "unit 1 to 4."
            ::= { e1PerfControlEty 1 }

        e1PerfCtrlClearPerf  OBJECT-TYPE
            SYNTAX  INTEGER {
                    clear(1)
                }
            ACCESS  read-write
            STATUS  mandatory
            DESCRIPTION
                "Clear performance data"
            ::= { e1PerfControlEty 2 }

--
-- E1 SNCP/UPSR APS Table
--

        e1SncpApsTab  OBJECT-TYPE
            SYNTAX  SEQUENCE OF  E1SncpApsEty
            ACCESS  not-accessible
            STATUS  mandatory
            DESCRIPTION
                "E1 SNCP/UPSR APS table "
            ::= { hdE1-card 5 }

        e1SncpApsEty  OBJECT-TYPE
            SYNTAX  E1SncpApsEty
            ACCESS  not-accessible
            STATUS  mandatory
            DESCRIPTION
                "E1 SNCP/UPSR APS entry"
            INDEX { e1SncpUnit , e1SncpPort }
            ::= { e1SncpApsTab 1 }

        E1SncpApsEty ::= SEQUENCE {
            e1SncpUnit                  UnitID,
            e1SncpPort                  PortID,
            e1SncpCurrentPathSlot       XcSlot,
            e1SncpCurrentPathPort       PortID,
            e1SncpPrimaryPathSlot       XcSlot,
            e1SncpPrimaryPathPort       PortID,
            e1SncpPPType                XcType,
            e1SncpCmd                   SncpUserCmd
        }

        e1SncpUnit  OBJECT-TYPE
            SYNTAX  UnitID
            ACCESS  read-only
            STATUS  mandatory
            DESCRIPTION
            "unit 1 to 4."
            ::= { e1SncpApsEty 1 }

        e1SncpPort  OBJECT-TYPE
            SYNTAX  PortID
            ACCESS  read-only
            STATUS  mandatory
            DESCRIPTION
                "PORT #1~#63"
            ::= { e1SncpApsEty 2 }

        e1SncpCurrentPathSlot  OBJECT-TYPE
            SYNTAX  XcSlot
            ACCESS  read-only
            STATUS  mandatory
            DESCRIPTION
                "SNCP/UPSR current path"
            ::= { e1SncpApsEty 3 }

        e1SncpCurrentPathPort  OBJECT-TYPE
            SYNTAX  PortID
            ACCESS  read-only
            STATUS  mandatory
            DESCRIPTION
                "SNCP/UPSR current path"
            ::= { e1SncpApsEty 4 }

        e1SncpPrimaryPathSlot  OBJECT-TYPE
            SYNTAX  XcSlot
            ACCESS  read-only
            STATUS  mandatory
            DESCRIPTION
                "SNCP/UPSR primary path"
            ::= { e1SncpApsEty 5 }

        e1SncpPrimaryPathPort  OBJECT-TYPE
            SYNTAX  PortID
            ACCESS  read-only
            STATUS  mandatory
            DESCRIPTION
                "SNCP/UPSR primary path"
            ::= { e1SncpApsEty 6 }

        e1SncpPPType  OBJECT-TYPE
            SYNTAX  XcType
            ACCESS  read-only
            STATUS  mandatory
            DESCRIPTION
                "SNCP/UPSR path protection type"
            ::= { e1SncpApsEty 7 }

        e1SncpCmd  OBJECT-TYPE
            SYNTAX  SncpUserCmd
            ACCESS  read-write
            STATUS  mandatory
            DESCRIPTION
                "SNCP/UPSR APS command"
            ::= { e1SncpApsEty 8 }

--
-- E1 LED Status Table
--

        e1LedStatusTab OBJECT-TYPE
            SYNTAX  SEQUENCE OF E1LedStatusEty
            ACCESS  not-accessible
            STATUS  mandatory
            DESCRIPTION
                "Led Status"
            ::= { hdE1-card 6 }

        e1LedStatusEty  OBJECT-TYPE
            SYNTAX  E1LedStatusEty
            ACCESS  not-accessible
            STATUS  mandatory
            DESCRIPTION
                "An entry in the led status table"
            INDEX { e1LedStsUnit }
            ::= { e1LedStatusTab 1 }

        E1LedStatusEty ::= SEQUENCE {
            e1LedStsUnit                UnitID,
            e1LedStsActiveLED           LedStatusType,
            e1LedStsTestLED             LedStatusType,
            e1LedStsAlarmLED            LedStatusType,
            e1LedStsE1-IndicatorLED     LedStatusType
        }

        e1LedStsUnit  OBJECT-TYPE
            SYNTAX  UnitID
            ACCESS  read-only
            STATUS  mandatory
            DESCRIPTION
            "unit 1 to 4."
            ::= { e1LedStatusEty 1 }

        e1LedStsActiveLED  OBJECT-TYPE
            SYNTAX  LedStatusType
            ACCESS  read-only
            STATUS  mandatory
            DESCRIPTION
                "Active Led Status"
            ::= { e1LedStatusEty 2 }

        e1LedStsTestLED  OBJECT-TYPE
            SYNTAX  LedStatusType
            ACCESS  read-only
            STATUS  mandatory
            DESCRIPTION
                "Test Led Status"
            ::= { e1LedStatusEty 3 }

        e1LedStsAlarmLED  OBJECT-TYPE
            SYNTAX  LedStatusType
            ACCESS  read-only
            STATUS  mandatory
            DESCRIPTION
                "Alarm Led Status"
            ::= { e1LedStatusEty 4 }

        e1LedStsE1-IndicatorLED  OBJECT-TYPE
            SYNTAX  LedStatusType
            ACCESS  read-only
            STATUS  mandatory
            DESCRIPTION
                "E1-Indicator Led Status"
            ::= { e1LedStatusEty 5 }

--
-- E1 Command Control Table
--

        e1CommandControlTab  OBJECT-TYPE
            SYNTAX  SEQUENCE OF E1CommandControlEty
            ACCESS  not-accessible
            STATUS  mandatory
            DESCRIPTION
                "Command control"
            ::= { hdE1-card 7 }

        e1CommandControlEty  OBJECT-TYPE
            SYNTAX  E1CommandControlEty
            ACCESS  not-accessible
            STATUS  mandatory
            DESCRIPTION
                "An entry in the command control table"
            INDEX { e1CmdCtrlUnit }
            ::= { e1CommandControlTab 1 }

        E1CommandControlEty ::= SEQUENCE {
            e1CmdCtrlUnit               UnitID,
            e1CmdCtrlUnitReset          INTEGER,
            e1CmdCtrlUnitLoadDefault    INTEGER
        }

        e1CmdCtrlUnit  OBJECT-TYPE
            SYNTAX  UnitID
            ACCESS  read-only
            STATUS  mandatory
            DESCRIPTION
            "unit 1 to 4."
            ::= { e1CommandControlEty 1 }

        e1CmdCtrlUnitReset  OBJECT-TYPE
            SYNTAX  INTEGER {
                    warm(1),
                    cold(2)
                }
            ACCESS  read-write
            STATUS  mandatory
            DESCRIPTION
                "Unit reset"
            ::= { e1CommandControlEty 2 }

        e1CmdCtrlUnitLoadDefault  OBJECT-TYPE
            SYNTAX  INTEGER {
                    load-default(1)
                }
            ACCESS  read-write
            STATUS  mandatory
            DESCRIPTION
                "Unit load default"
            ::= { e1CommandControlEty 3 }

--
--  E1 XC Display Table
--
        e1XcDisplayTab  OBJECT-TYPE
            SYNTAX  SEQUENCE OF  E1XcDisplayEty
            ACCESS  not-accessible
            STATUS  mandatory
            DESCRIPTION
                "E1 xc display table "
            ::= { hdE1-card 8 }

        e1XcDisplayEty  OBJECT-TYPE
            SYNTAX  E1XcDisplayEty
            ACCESS  not-accessible
            STATUS  mandatory
            DESCRIPTION
                "E1 xc display entry"
            INDEX { e1XcDispMapIndex ,
                    e1XcDispUnitIndex ,
                    e1XcDispPortIndex }
            ::= { e1XcDisplayTab 1 }

        E1XcDisplayEty ::= SEQUENCE {
            e1XcDispMapIndex            XcMap,
            e1XcDispUnitIndex           UnitID,
            e1XcDispPortIndex           PortID,
            e1XcDispSrcSlotType         NewXcModel,
            e1XcDispSrcSlot             XcSlot,
            e1XcDispSrcPort             PortID,
            e1XcDispSrcChannel          ChannelNum,
            e1XcDispSrcAug1Sts3Path     Aug1Sts3Num,
            e1XcDispSrcVc3Sts1Path      Vc3Sts1Num,
            e1XcDispSrcVc1xVtxPath      Vc1xVtxNum,
            e1XcDispXcGranularity       INTEGER,
            e1XcDispXcType              XcType
        }

        e1XcDispMapIndex  OBJECT-TYPE
            SYNTAX  XcMap
            ACCESS  read-only
            STATUS  mandatory
            DESCRIPTION
                "xc map index"
            ::= { e1XcDisplayEty 1 }

        e1XcDispUnitIndex  OBJECT-TYPE
            SYNTAX  UnitID
            ACCESS  read-only
            STATUS  mandatory
            DESCRIPTION
            "unit 1 to 4."
            ::= { e1XcDisplayEty 2 }

        e1XcDispPortIndex  OBJECT-TYPE
            SYNTAX  PortID
            ACCESS  read-only
            STATUS  mandatory
            DESCRIPTION
                "PORT index"
            ::= { e1XcDisplayEty 3 }

        e1XcDispSrcSlotType  OBJECT-TYPE
            SYNTAX  NewXcModel
            ACCESS  read-only
            STATUS  mandatory
            DESCRIPTION
                " Xc src Unit Type"
            ::= { e1XcDisplayEty 4 }

        e1XcDispSrcSlot  OBJECT-TYPE
            SYNTAX  XcSlot
            ACCESS  read-only
            STATUS  mandatory
            DESCRIPTION
                "Xc src Unit "
            ::= { e1XcDisplayEty 5 }

        e1XcDispSrcPort  OBJECT-TYPE
            SYNTAX  PortID
            ACCESS  read-only
            STATUS  mandatory
            DESCRIPTION
                "Xc src port "
            ::= { e1XcDisplayEty 6 }

        e1XcDispSrcChannel  OBJECT-TYPE
            SYNTAX  ChannelNum
            ACCESS  read-only
            STATUS  mandatory
            DESCRIPTION
                "Xc src channel "
            ::= { e1XcDisplayEty 7 }

        e1XcDispSrcAug1Sts3Path  OBJECT-TYPE
            SYNTAX  Aug1Sts3Num
            ACCESS  read-only
            STATUS  mandatory
            DESCRIPTION
                "Xc src AUG1/STS3 path"
            ::= { e1XcDisplayEty 8 }

        e1XcDispSrcVc3Sts1Path  OBJECT-TYPE
            SYNTAX  Vc3Sts1Num
            ACCESS  read-only
            STATUS  mandatory
            DESCRIPTION
                "Xc src VC3/STS1 path"
            ::= { e1XcDisplayEty 9 }

        e1XcDispSrcVc1xVtxPath  OBJECT-TYPE
            SYNTAX  Vc1xVtxNum
            ACCESS  read-only
            STATUS  mandatory
            DESCRIPTION
                "Xc src VC1x/VTx path"
            ::= { e1XcDisplayEty 10 }

        e1XcDispXcGranularity  OBJECT-TYPE
            SYNTAX  INTEGER {
                    tu3(2),
                    au3-sts1(3),
                    tu11-vt15(4),
                    tu12-vt2(5),
                    vc4-sts3c(6),
                    not-available(100)
                }
            ACCESS  read-only
            STATUS  mandatory
            DESCRIPTION
                "Xc granularity"
            ::= { e1XcDisplayEty 11 }

        e1XcDispXcType  OBJECT-TYPE
            SYNTAX  XcType
            ACCESS  read-only
            STATUS  mandatory
            DESCRIPTION
                "Xc type"
            ::= { e1XcDisplayEty 12 }

--
-- E1 Consolidation
--

    e1Consolidation      OBJECT IDENTIFIER ::= { hdE1-card 9 }

--
--  E1 XC Summary Hex Table
--
        e1XcSummaryHexTab  OBJECT-TYPE
            SYNTAX  SEQUENCE OF  E1XcSummaryHexEty
            ACCESS  not-accessible
            STATUS  mandatory
            DESCRIPTION
                "E1 Xc Summary HEX Table "
            ::= { e1Consolidation 1 }

        e1XcSummaryHexEty OBJECT-TYPE
            SYNTAX  E1XcSummaryHexEty
            ACCESS  not-accessible
            STATUS  mandatory
            DESCRIPTION
                "An entry in the E1 xc summary hex table."
            INDEX { e1XcSummMapIndex , e1XcSummUnitIndex }
            ::= { e1XcSummaryHexTab 1 }

        E1XcSummaryHexEty ::= SEQUENCE  {
            e1XcSummMapIndex            XcMap,
            e1XcSummUnitIndex           UnitID,
            e1XcSummSummary             OCTET STRING
        }

        e1XcSummMapIndex  OBJECT-TYPE
            SYNTAX  XcMap
            ACCESS  read-only
            STATUS  mandatory
            DESCRIPTION
                "xc map index"
            ::= { e1XcSummaryHexEty  1 }

        e1XcSummUnitIndex  OBJECT-TYPE
            SYNTAX  UnitID
            ACCESS  read-only
            STATUS  mandatory
            DESCRIPTION
                "unit index"
            ::= { e1XcSummaryHexEty  2 }

        e1XcSummSummary  OBJECT-TYPE
            SYNTAX  OCTET STRING(SIZE(9))
            ACCESS  read-only
            STATUS  mandatory
            DESCRIPTION
                "E1 XC Summary"
            ::= { e1XcSummaryHexEty  3 }

--
--  E1 LED Status Hex Table
--

        e1LedStatusHexTab  OBJECT-TYPE
            SYNTAX  SEQUENCE OF  E1LedStatusHexEty
            ACCESS  not-accessible
            STATUS  mandatory
            DESCRIPTION
                "E1 led status hex Table "
            ::= { e1Consolidation 2 }

        e1LedStatusHexEty OBJECT-TYPE
            SYNTAX  E1LedStatusHexEty
            ACCESS  not-accessible
            STATUS  mandatory
            DESCRIPTION
                "An entry in the E1 led status hex table."
            INDEX { e1LedStsHexUnit }
            ::= { e1LedStatusHexTab 1 }

        E1LedStatusHexEty ::= SEQUENCE  {
            e1LedStsHexUnit             UnitID,
            e1LedStsHexData             OCTET STRING
        }

        e1LedStsHexUnit  OBJECT-TYPE
            SYNTAX  UnitID
            ACCESS  read-only
            STATUS  mandatory
            DESCRIPTION
                "unit index"
            ::= { e1LedStatusHexEty  1 }

        e1LedStsHexData  OBJECT-TYPE
            SYNTAX  OCTET STRING
            ACCESS  read-only
            STATUS  mandatory
            DESCRIPTION
                "Hex data"
            ::= { e1LedStatusHexEty  2 }

--
--  E1 General Config Hex Table
--

        e1GeneralCfgHexTab  OBJECT-TYPE
            SYNTAX  SEQUENCE OF  E1GeneralCfgHexEty
            ACCESS  not-accessible
            STATUS  mandatory
            DESCRIPTION
                "E1 general config hex Table "
            ::= { e1Consolidation 3 }

        e1GeneralCfgHexEty OBJECT-TYPE
            SYNTAX  E1GeneralCfgHexEty
            ACCESS  not-accessible
            STATUS  mandatory
            DESCRIPTION
                "An entry in the E1 general config hex table."
            INDEX { e1GenCfgHexUnit }
            ::= { e1GeneralCfgHexTab 1 }

        E1GeneralCfgHexEty ::= SEQUENCE  {
            e1GenCfgHexUnit             UnitID,
            e1GenCfgHexData             OCTET STRING
        }

        e1GenCfgHexUnit  OBJECT-TYPE
            SYNTAX  UnitID
            ACCESS  read-only
            STATUS  mandatory
            DESCRIPTION
                "unit index"
            ::= { e1GeneralCfgHexEty  1 }

        e1GenCfgHexData  OBJECT-TYPE
            SYNTAX  OCTET STRING
            ACCESS  read-only
            STATUS  mandatory
            DESCRIPTION
                "Hex data"
            ::= { e1GeneralCfgHexEty  2 }

--
--  E1 Alarm Hex Table
--

    e1AlarmHex      OBJECT IDENTIFIER ::= { e1Consolidation 4 }

--
--  E1 Alarm Mask Hex Table
--

        e1AlmMaskHexTab  OBJECT-TYPE
            SYNTAX  SEQUENCE OF  E1AlmMaskHexEty
            ACCESS  not-accessible
            STATUS  mandatory
            DESCRIPTION
                "E1 alarm mask hex Table "
            ::= { e1AlarmHex 1 }

        e1AlmMaskHexEty OBJECT-TYPE
            SYNTAX  E1AlmMaskHexEty
            ACCESS  not-accessible
            STATUS  mandatory
            DESCRIPTION
                "An entry in the E1 alarm mask hex table."
            INDEX { e1AlmMaskHexUnit }
            ::= { e1AlmMaskHexTab 1 }

        E1AlmMaskHexEty ::= SEQUENCE  {
            e1AlmMaskHexUnit            UnitID,
            e1AlmMaskHexData            OCTET STRING
        }

        e1AlmMaskHexUnit  OBJECT-TYPE
            SYNTAX  UnitID
            ACCESS  read-only
            STATUS  mandatory
            DESCRIPTION
                "unit index"
            ::= { e1AlmMaskHexEty  1 }

        e1AlmMaskHexData  OBJECT-TYPE
            SYNTAX  OCTET STRING
            ACCESS  read-only
            STATUS  mandatory
            DESCRIPTION
                "Hex data"
            ::= { e1AlmMaskHexEty  2 }

--
--  E1 Alarm Relay Hex Table
--

        e1AlmRelayHexTab  OBJECT-TYPE
            SYNTAX  SEQUENCE OF  E1AlmRelayHexEty
            ACCESS  not-accessible
            STATUS  mandatory
            DESCRIPTION
                "E1 alarm relay hex Table "
            ::= { e1AlarmHex 2 }

        e1AlmRelayHexEty OBJECT-TYPE
            SYNTAX  E1AlmRelayHexEty
            ACCESS  not-accessible
            STATUS  mandatory
            DESCRIPTION
                "An entry in the E1 alarm relay hex table."
            INDEX { e1AlmRelayHexUnit }
            ::= { e1AlmRelayHexTab 1 }

        E1AlmRelayHexEty ::= SEQUENCE  {
            e1AlmRelayHexUnit           UnitID,
            e1AlmRelayHexData           OCTET STRING
        }

        e1AlmRelayHexUnit  OBJECT-TYPE
            SYNTAX  UnitID
            ACCESS  read-only
            STATUS  mandatory
            DESCRIPTION
                "unit index"
            ::= { e1AlmRelayHexEty  1 }

        e1AlmRelayHexData  OBJECT-TYPE
            SYNTAX  OCTET STRING
            ACCESS  read-only
            STATUS  mandatory
            DESCRIPTION
                "Hex data"
            ::= { e1AlmRelayHexEty  2 }

--
--  E1 Alarm Severity Hex Table
--

        e1AlmSeverityHexTab  OBJECT-TYPE
            SYNTAX  SEQUENCE OF  E1AlmSeverityHexEty
            ACCESS  not-accessible
            STATUS  mandatory
            DESCRIPTION
                "E1 alarm severity hex Table "
            ::= { e1AlarmHex 3 }

        e1AlmSeverityHexEty OBJECT-TYPE
            SYNTAX  E1AlmSeverityHexEty
            ACCESS  not-accessible
            STATUS  mandatory
            DESCRIPTION
                "An entry in the E1 alarm severity hex table."
            INDEX { e1AlmSeverityHexUnit }
            ::= { e1AlmSeverityHexTab 1 }

        E1AlmSeverityHexEty ::= SEQUENCE  {
            e1AlmSeverityHexUnit        UnitID,
            e1AlmSeverityHexData        OCTET STRING
        }

        e1AlmSeverityHexUnit  OBJECT-TYPE
            SYNTAX  UnitID
            ACCESS  read-only
            STATUS  mandatory
            DESCRIPTION
                "unit index"
            ::= { e1AlmSeverityHexEty  1 }

        e1AlmSeverityHexData  OBJECT-TYPE
            SYNTAX  OCTET STRING
            ACCESS  read-only
            STATUS  mandatory
            DESCRIPTION
                "Hex data"
            ::= { e1AlmSeverityHexEty  2 }

--
--  E1 Alarm Status Hex Table
--

        e1AlmStatusHexTab  OBJECT-TYPE
            SYNTAX  SEQUENCE OF  E1AlmStatusHexEty
            ACCESS  not-accessible
            STATUS  mandatory
            DESCRIPTION
                "E1 alarm status hex Table "
            ::= { e1AlarmHex 4 }

        e1AlmStatusHexEty OBJECT-TYPE
            SYNTAX  E1AlmStatusHexEty
            ACCESS  not-accessible
            STATUS  mandatory
            DESCRIPTION
                "An entry in the E1 alarm status hex table."
            INDEX { e1AlmStatusHexUnit }
            ::= { e1AlmStatusHexTab 1 }

        E1AlmStatusHexEty ::= SEQUENCE  {
            e1AlmStatusHexUnit          UnitID,
            e1AlmStatusHexData          OCTET STRING
        }

        e1AlmStatusHexUnit  OBJECT-TYPE
            SYNTAX  UnitID
            ACCESS  read-only
            STATUS  mandatory
            DESCRIPTION
                "unit index"
            ::= { e1AlmStatusHexEty  1 }

        e1AlmStatusHexData  OBJECT-TYPE
            SYNTAX  OCTET STRING
            ACCESS  read-only
            STATUS  mandatory
            DESCRIPTION
                "Hex data"
            ::= { e1AlmStatusHexEty  2 }

--
--  E1 Loopback and Diagnostic Hex Table
--

        e1LoopbackDiagHexTab  OBJECT-TYPE
            SYNTAX  SEQUENCE OF  E1LoopbackDiagHexEty
            ACCESS  not-accessible
            STATUS  mandatory
            DESCRIPTION
                "E1 loopback and diagnostic hex Table "
            ::= { e1Consolidation 5 }

        e1LoopbackDiagHexEty OBJECT-TYPE
            SYNTAX  E1LoopbackDiagHexEty
            ACCESS  not-accessible
            STATUS  mandatory
            DESCRIPTION
                "An entry in the E1 alarm status hex table."
            INDEX { e1LoopBkDiagHexUnit }
            ::= { e1LoopbackDiagHexTab 1 }

        E1LoopbackDiagHexEty ::= SEQUENCE  {
            e1LoopBkDiagHexUnit         UnitID,
            e1LoopBkDiagHexData         OCTET STRING
        }

        e1LoopBkDiagHexUnit  OBJECT-TYPE
            SYNTAX  UnitID
            ACCESS  read-only
            STATUS  mandatory
            DESCRIPTION
                "unit index"
            ::= { e1LoopbackDiagHexEty  1 }

        e1LoopBkDiagHexData  OBJECT-TYPE
            SYNTAX  OCTET STRING
            ACCESS  read-only
            STATUS  mandatory
            DESCRIPTION
                "Hex data"
            ::= { e1LoopbackDiagHexEty  2 }

--
--  E1 Alarm Hex Table
--

    e1PerformanceHex      OBJECT IDENTIFIER ::= { e1Consolidation 6 }

--
--  E1 24hour Performance Summary Hex Table
--

        e1PerfSummaryHexTab  OBJECT-TYPE
            SYNTAX  SEQUENCE OF  E1PerfSummaryHexEty
            ACCESS  not-accessible
            STATUS  mandatory
            DESCRIPTION
                "E1 performance summary hex Table "
            ::= { e1PerformanceHex 1 }

        e1PerfSummaryHexEty OBJECT-TYPE
            SYNTAX  E1PerfSummaryHexEty
            ACCESS  not-accessible
            STATUS  mandatory
            DESCRIPTION
                "An entry in the E1 performance summary hex table."
            INDEX { e1PerfSummaryHexUnit ,
                    e1PerfSummaryHexPort }
            ::= { e1PerfSummaryHexTab 1 }

        E1PerfSummaryHexEty ::= SEQUENCE  {
            e1PerfSummaryHexUnit        UnitID,
            e1PerfSummaryHexPort        PortID,
            e1PerfSummaryHexData        OCTET STRING
        }

        e1PerfSummaryHexUnit  OBJECT-TYPE
            SYNTAX  UnitID
            ACCESS  read-only
            STATUS  mandatory
            DESCRIPTION
                "unit index"
            ::= { e1PerfSummaryHexEty  1 }

        e1PerfSummaryHexPort  OBJECT-TYPE
            SYNTAX  PortID
            ACCESS  read-only
            STATUS  mandatory
            DESCRIPTION
                "unit index"
            ::= { e1PerfSummaryHexEty  2 }

        e1PerfSummaryHexData  OBJECT-TYPE
            SYNTAX  OCTET STRING
            ACCESS  read-only
            STATUS  mandatory
            DESCRIPTION
                "Hex data"
            ::= { e1PerfSummaryHexEty  3 }

--
--  E1 15Min Interval Performance Hex Table
--

        e1Perf15MinIntvHexTab  OBJECT-TYPE
            SYNTAX  SEQUENCE OF  E1Perf15MinIntvHexEty
            ACCESS  not-accessible
            STATUS  mandatory
            DESCRIPTION
                "E1 15 min interval performance hex Table "
            ::= { e1PerformanceHex 2 }

        e1Perf15MinIntvHexEty OBJECT-TYPE
            SYNTAX  E1Perf15MinIntvHexEty
            ACCESS  not-accessible
            STATUS  mandatory
            DESCRIPTION
                "An entry in the E1 15 min interval performance hex table."
            INDEX { e1Perf15MIntvHexUnit ,
                    e1Perf15MIntvHexPort ,
                    e1Perf15MIntvHexAnomaly ,
                    e1Perf15MIntvHexIntv }
            ::= { e1Perf15MinIntvHexTab 1 }

        E1Perf15MinIntvHexEty ::= SEQUENCE  {
            e1Perf15MIntvHexUnit        UnitID,
            e1Perf15MIntvHexPort        PortID,
            e1Perf15MIntvHexAnomaly     INTEGER,
            e1Perf15MIntvHexIntv        INTEGER,
            e1Perf15MIntvHexData        OCTET STRING
        }

        e1Perf15MIntvHexUnit  OBJECT-TYPE
            SYNTAX  UnitID
            ACCESS  read-only
            STATUS  mandatory
            DESCRIPTION
                "unit index"
            ::= { e1Perf15MinIntvHexEty  1 }

        e1Perf15MIntvHexPort  OBJECT-TYPE
            SYNTAX  PortID
            ACCESS  read-only
            STATUS  mandatory
            DESCRIPTION
                "unit index"
            ::= { e1Perf15MinIntvHexEty  2 }

        e1Perf15MIntvHexAnomaly  OBJECT-TYPE
            SYNTAX  INTEGER {
                    bip-v5(1),
                    rei-v5(2),
                    e1-line(3)
                }
            ACCESS  read-only
            STATUS  mandatory
            DESCRIPTION
                "anomal type"
            ::= { e1Perf15MinIntvHexEty  3 }

        e1Perf15MIntvHexIntv  OBJECT-TYPE
            SYNTAX  INTEGER (1..96)
            ACCESS  read-only
            STATUS  mandatory
            DESCRIPTION
                "interval value"
            ::= { e1Perf15MinIntvHexEty  4 }

        e1Perf15MIntvHexData  OBJECT-TYPE
            SYNTAX  OCTET STRING
            ACCESS  read-only
            STATUS  mandatory
            DESCRIPTION
                "Hex data"
            ::= { e1Perf15MinIntvHexEty  5 }

--
--  E1 TPSG Protection Switch Hex Table
--

        e1TPSGProtSwitchHexTab  OBJECT-TYPE
            SYNTAX  SEQUENCE OF  E1TPSGProtSwitchHexEty
            ACCESS  not-accessible
            STATUS  mandatory
            DESCRIPTION
                "E1 TPSG protection switch hex Table "
            ::= { e1Consolidation 7 }

        e1TPSGProtSwitchHexEty OBJECT-TYPE
            SYNTAX  E1TPSGProtSwitchHexEty
            ACCESS  not-accessible
            STATUS  mandatory
            DESCRIPTION
                "An entry in the E1 TPSG protection switch hex table."
            INDEX { e1TPSGSwitchHexUnit }
            ::= { e1TPSGProtSwitchHexTab 1 }

        E1TPSGProtSwitchHexEty ::= SEQUENCE  {
            e1TPSGSwitchHexUnit         UnitID,
            e1TPSGSwitchHexData         OCTET STRING
        }

        e1TPSGSwitchHexUnit  OBJECT-TYPE
            SYNTAX  UnitID
            ACCESS  read-only
            STATUS  mandatory
            DESCRIPTION
                "unit index"
            ::= { e1TPSGProtSwitchHexEty  1 }

        e1TPSGSwitchHexData  OBJECT-TYPE
            SYNTAX  OCTET STRING
            ACCESS  read-only
            STATUS  mandatory
            DESCRIPTION
                "Hex data"
            ::= { e1TPSGProtSwitchHexEty  2 }
--2011-3-17 elvis below
--
--  New E1 XC Display Table
--
        new-e1XcDisplayTab  OBJECT-TYPE
            SYNTAX  SEQUENCE OF  NewE1XcDisplayEty
            ACCESS  not-accessible
            STATUS  mandatory
            DESCRIPTION
                "E1 xc display table "
            ::= { hdE1-card 10 }

        new-e1XcDisplayEty  OBJECT-TYPE
            SYNTAX  NewE1XcDisplayEty
            ACCESS  not-accessible
            STATUS  mandatory
            DESCRIPTION
                "E1 xc display entry"
            INDEX { new-e1XcDispMapIndex ,
                    new-e1XcDispUnitIndex ,
                    new-e1XcDispPortIndex }
            ::= { new-e1XcDisplayTab 1 }

        NewE1XcDisplayEty ::= SEQUENCE {
            new-e1XcDispMapIndex        XcMap,
            new-e1XcDispUnitIndex       UnitID,
            new-e1XcDispPortIndex       PortID,
            new-e1XcDispPriSlotType     NewXcModel,
            new-e1XcDispPriSlot         XcSlot,
            new-e1XcDispPriPort         PortID,
            new-e1XcDispPriChannel      ChannelNum,
            new-e1XcDispPriAug1Sts3Path Aug1Sts3Num,
            new-e1XcDispPriVc3Sts1Path  Vc3Sts1Num,
            new-e1XcDispPriVc1xVtxPath  Vc1xVtxNum,
            new-e1XcDispXcGranularity   INTEGER,
            new-e1XcDispXcType          XcType,
            new-e1XcDispSecSlotType     NewXcModel,
            new-e1XcDispSecSlot         XcSlot,
            new-e1XcDispSecPort         PortID,
            new-e1XcDispSecChannel      ChannelNum,
            new-e1XcDispSecAug1Sts3Path Aug1Sts3Num,
            new-e1XcDispSecVc3Sts1Path  Vc3Sts1Num,
            new-e1XcDispSecVc1xVtxPath  Vc1xVtxNum
        }

        new-e1XcDispMapIndex  OBJECT-TYPE
            SYNTAX  XcMap
            ACCESS  read-only
            STATUS  mandatory
            DESCRIPTION
                "xc map index"
            ::= { new-e1XcDisplayEty 1 }

        new-e1XcDispUnitIndex  OBJECT-TYPE
            SYNTAX  UnitID
            ACCESS  read-only
            STATUS  mandatory
            DESCRIPTION
                "unit 1 to 8, total 8 units."
            ::= { new-e1XcDisplayEty 2 }

        new-e1XcDispPortIndex  OBJECT-TYPE
            SYNTAX  PortID
            ACCESS  read-only
            STATUS  mandatory
            DESCRIPTION
                "PORT index"
            ::= { new-e1XcDisplayEty 3 }

        new-e1XcDispPriSlotType  OBJECT-TYPE
            SYNTAX  NewXcModel
            ACCESS  read-only
            STATUS  mandatory
            DESCRIPTION
                " Xc Primary Unit Type"
            ::= { new-e1XcDisplayEty 4 }

        new-e1XcDispPriSlot  OBJECT-TYPE
            SYNTAX  XcSlot
            ACCESS  read-only
            STATUS  mandatory
            DESCRIPTION
                "Xc Primary Unit "
            ::= { new-e1XcDisplayEty 5 }

        new-e1XcDispPriPort  OBJECT-TYPE
            SYNTAX  PortID
            ACCESS  read-only
            STATUS  mandatory
            DESCRIPTION
                "Xc Primary port "
            ::= { new-e1XcDisplayEty 6 }

        new-e1XcDispPriChannel  OBJECT-TYPE
            SYNTAX  ChannelNum
            ACCESS  read-only
            STATUS  mandatory
            DESCRIPTION
                "Xc Primary channel "
            ::= { new-e1XcDisplayEty 7 }

        new-e1XcDispPriAug1Sts3Path  OBJECT-TYPE
            SYNTAX  Aug1Sts3Num
            ACCESS  read-only
            STATUS  mandatory
            DESCRIPTION
                "Xc Primary AUG1/STS3 path"
            ::= { new-e1XcDisplayEty 8 }

        new-e1XcDispPriVc3Sts1Path  OBJECT-TYPE
            SYNTAX  Vc3Sts1Num
            ACCESS  read-only
            STATUS  mandatory
            DESCRIPTION
                "Xc Primary VC3/STS1 path"
            ::= { new-e1XcDisplayEty 9 }

        new-e1XcDispPriVc1xVtxPath  OBJECT-TYPE
            SYNTAX  Vc1xVtxNum
            ACCESS  read-only
            STATUS  mandatory
            DESCRIPTION
                "Xc Primary VC1x/VTx path"
            ::= { new-e1XcDisplayEty 10 }

        new-e1XcDispXcGranularity  OBJECT-TYPE
            SYNTAX  INTEGER {
                    tu3(2),
                    au3-sts1(3),
                    tu11-vt15(4),
                    tu12-vt2(5),
                    vc4-sts3c(6),
                    not-available(100)
                }
            ACCESS  read-only
            STATUS  mandatory
            DESCRIPTION
                "Xc granularity"
            ::= { new-e1XcDisplayEty 11 }

        new-e1XcDispXcType  OBJECT-TYPE
            SYNTAX  XcType
            ACCESS  read-only
            STATUS  mandatory
            DESCRIPTION
                "Xc type"
            ::= { new-e1XcDisplayEty 12 }

        new-e1XcDispSecSlotType  OBJECT-TYPE
            SYNTAX  NewXcModel
            ACCESS  read-only
            STATUS  mandatory
            DESCRIPTION
                " Xc Secondary Unit Type"
            ::= { new-e1XcDisplayEty 13 }

        new-e1XcDispSecSlot  OBJECT-TYPE
            SYNTAX  XcSlot
            ACCESS  read-only
            STATUS  mandatory
            DESCRIPTION
                "Xc Secondary Unit "
            ::= { new-e1XcDisplayEty 14 }

        new-e1XcDispSecPort  OBJECT-TYPE
            SYNTAX  PortID
            ACCESS  read-only
            STATUS  mandatory
            DESCRIPTION
                "Xc Secondary port "
            ::= { new-e1XcDisplayEty 15 }

        new-e1XcDispSecChannel  OBJECT-TYPE
            SYNTAX  ChannelNum
            ACCESS  read-only
            STATUS  mandatory
            DESCRIPTION
                "Xc Secondary channel "
            ::= { new-e1XcDisplayEty 16 }

        new-e1XcDispSecAug1Sts3Path  OBJECT-TYPE
            SYNTAX  Aug1Sts3Num
            ACCESS  read-only
            STATUS  mandatory
            DESCRIPTION
                "Xc Secondary AUG1/STS3 path"
            ::= { new-e1XcDisplayEty 17 }

        new-e1XcDispSecVc3Sts1Path  OBJECT-TYPE
            SYNTAX  Vc3Sts1Num
            ACCESS  read-only
            STATUS  mandatory
            DESCRIPTION
                "Xc Secondary VC3/STS1 path"
            ::= { new-e1XcDisplayEty 18 }

        new-e1XcDispSecVc1xVtxPath  OBJECT-TYPE
            SYNTAX  Vc1xVtxNum
            ACCESS  read-only
            STATUS  mandatory
            DESCRIPTION
                "Xc Secondary VC1x/VTx path"
            ::= { new-e1XcDisplayEty 19 }

--
-- New E1 SNCP/UPSR APS Table
--

        new-e1SncpApsTab  OBJECT-TYPE
            SYNTAX  SEQUENCE OF  NewE1SncpApsEty
            ACCESS  not-accessible
            STATUS  mandatory
            DESCRIPTION
                "E1 SNCP/UPSR APS table "
            ::= { hdE1-card 11 }

        new-e1SncpApsEty  OBJECT-TYPE
            SYNTAX  NewE1SncpApsEty
            ACCESS  not-accessible
            STATUS  mandatory
            DESCRIPTION
                "E1 SNCP/UPSR APS entry"
            INDEX { new-e1SncpUnit , new-e1SncpPort }
            ::= { new-e1SncpApsTab 1 }

        NewE1SncpApsEty ::= SEQUENCE {
            new-e1SncpUnit              UnitID,
            new-e1SncpPort              PortID,
            new-e1SncpCurrSlot          XcSlot,
            new-e1SncpCurrPort          PortID,
            new-e1SncpCurrChannel       ChannelNum,
            new-e1SncpCurrAug1Sts3Path  Aug1Sts3Num,
            new-e1SncpCurrVc3Sts1Path   Vc3Sts1Num,
            new-e1SncpCurrVc1xVtxPath   Vc1xVtxNum,
            new-e1SncpPPType            XcType,
            new-e1SncpCmd               SncpUserCmd,
            new-e1SncpRevertive         INTEGER
        }

        new-e1SncpUnit  OBJECT-TYPE
            SYNTAX  UnitID
            ACCESS  read-only
            STATUS  mandatory
            DESCRIPTION
                "unit 1 to 8, total 8 units."
            ::= { new-e1SncpApsEty 1 }

        new-e1SncpPort  OBJECT-TYPE
            SYNTAX  PortID
            ACCESS  read-only
            STATUS  mandatory
            DESCRIPTION
                "PORT #1~#63"
            ::= { new-e1SncpApsEty 2 }

        new-e1SncpCurrSlot  OBJECT-TYPE
            SYNTAX  XcSlot
            ACCESS  read-only
            STATUS  mandatory
            DESCRIPTION
                "SNCP/UPSR current slot"
            ::= { new-e1SncpApsEty 3 }

        new-e1SncpCurrPort  OBJECT-TYPE
            SYNTAX  PortID
            ACCESS  read-only
            STATUS  mandatory
            DESCRIPTION
                "SNCP/UPSR current port"
            ::= { new-e1SncpApsEty 4 }

        new-e1SncpCurrChannel  OBJECT-TYPE
            SYNTAX  ChannelNum
            ACCESS  read-only
            STATUS  mandatory
            DESCRIPTION
                "SNCP/UPSR current channel"
            ::= { new-e1SncpApsEty 5 }

        new-e1SncpCurrAug1Sts3Path  OBJECT-TYPE
            SYNTAX  Aug1Sts3Num
            ACCESS  read-only
            STATUS  mandatory
            DESCRIPTION
                "SNCP/UPSR current Aug1/Sts3"
            ::= { new-e1SncpApsEty 6 }

        new-e1SncpCurrVc3Sts1Path  OBJECT-TYPE
            SYNTAX  Vc3Sts1Num
            ACCESS  read-only
            STATUS  mandatory
            DESCRIPTION
                "SNCP/UPSR current Vc3/Sts1"
            ::= { new-e1SncpApsEty 7 }

        new-e1SncpCurrVc1xVtxPath  OBJECT-TYPE
            SYNTAX  Vc1xVtxNum
            ACCESS  read-only
            STATUS  mandatory
            DESCRIPTION
                "SNCP/UPSR current Vc1x/Vtx"
            ::= { new-e1SncpApsEty 8 }

        new-e1SncpPPType  OBJECT-TYPE
            SYNTAX  XcType
            ACCESS  read-only
            STATUS  mandatory
            DESCRIPTION
                "SNCP/UPSR path protection type"
            ::= { new-e1SncpApsEty 9 }

        new-e1SncpCmd  OBJECT-TYPE
            SYNTAX  SncpUserCmd
            ACCESS  read-write
            STATUS  mandatory
            DESCRIPTION
                "SNCP/UPSR APS command"
            ::= { new-e1SncpApsEty 10 }

        new-e1SncpRevertive  OBJECT-TYPE
            SYNTAX  INTEGER {
                    non-revertive(1),
                    revertive(2)
                }
            ACCESS  read-write
            STATUS  mandatory
            DESCRIPTION
                "SNCP/UPSR revertive or non-revertive"
            ::= { new-e1SncpApsEty 11 }

        hdE1TotalCard   OBJECT-TYPE
            SYNTAX  INTEGER
            ACCESS  read-only
            STATUS  mandatory
            DESCRIPTION
                "Total cards of hdE1"
            ::= { hdE1-card 100 }


--2011-3-17 elvis above

--======================================================================--
--======================================================================--
--  t1-card MIB
--======================================================================--
--======================================================================--

--
--  T1 Config
--

    hdT1Config           OBJECT IDENTIFIER ::= { hdT1-card 1 }


--
--  T1 Channel Line Interface Setup Table
--

        t1ChLineIntfSetupTab  OBJECT-TYPE
            SYNTAX  SEQUENCE OF T1ChLineIntfSetupEty
            ACCESS  not-accessible
            STATUS  mandatory
            DESCRIPTION
                "Channel line interface setup table"
            ::= { hdT1Config 1 }

        t1ChLineIntfSetupEty  OBJECT-TYPE
            SYNTAX  T1ChLineIntfSetupEty
            ACCESS  not-accessible
            STATUS  mandatory
            DESCRIPTION
                "An entry in the channel line interface setup table"
            INDEX { t1ChLineIntfUnit ,
                    t1ChLineIntfPort }
            ::= { t1ChLineIntfSetupTab 1 }

        T1ChLineIntfSetupEty ::= SEQUENCE {
            t1ChLineIntfUnit            UnitID,
            t1ChLineIntfPort            PortID,
            t1ChLineIntfCoding          INTEGER,
            t1ChLineIntfEqualizer       INTEGER
        }

        t1ChLineIntfUnit  OBJECT-TYPE
            SYNTAX  UnitID
            ACCESS  read-only
            STATUS  mandatory
            DESCRIPTION
            "unit 1 to 4."
            ::= { t1ChLineIntfSetupEty 1 }

        t1ChLineIntfPort  OBJECT-TYPE
            SYNTAX  PortID
            ACCESS  read-only
            STATUS  mandatory
            DESCRIPTION
                "T1 Port 1 to 63"
            ::= { t1ChLineIntfSetupEty 2 }

        t1ChLineIntfCoding  OBJECT-TYPE
            SYNTAX  INTEGER{
                    b8zs(1),
                    ami(2)
                }
            ACCESS  read-write
            STATUS  mandatory
            DESCRIPTION
                "T1 line coding mode"
            ::= { t1ChLineIntfSetupEty 3 }

        t1ChLineIntfEqualizer  OBJECT-TYPE
            SYNTAX  INTEGER{
                    equ-0-110ft(1),
                    equ-110-220ft(2),
                    equ-220-330ft(3),
                    equ-330-440ft(4),
                    equ-440-550ft(5),
                    equ-550-660ft(6)
                }
            ACCESS  read-write
            STATUS  mandatory
            DESCRIPTION
                "T1 line Equalizer"
            ::= { t1ChLineIntfSetupEty 4 }

--
-- T1 Trace Message & Signal Label Setup Table
--

        t1J2SigLabelSetupTab  OBJECT-TYPE
            SYNTAX  SEQUENCE OF T1J2SigLabelSetupEty
            ACCESS  not-accessible
            STATUS  mandatory
            DESCRIPTION
                "Trace message & Signal label setup table"
            ::= { hdT1Config 2 }

        t1J2SigLabelSetupEty  OBJECT-TYPE
            SYNTAX  T1J2SigLabelSetupEty
            ACCESS  not-accessible
            STATUS  mandatory
            DESCRIPTION
                "An entry in the trace message & signal label setup table"
            INDEX { t1J2SigLabelUnit ,
                    t1J2SigLabelPort }
            ::= { t1J2SigLabelSetupTab 1 }

        T1J2SigLabelSetupEty ::= SEQUENCE {
            t1J2SigLabelUnit            UnitID,
            t1J2SigLabelPort            PortID,
            t1J2SigLabelJ2Length        INTEGER,
            t1J2SigLabelExpJ2Msg        DisplayString(SIZE(0..64)),
            t1J2SigLabelTxJ2Msg         DisplayString(SIZE(0..64)),
            t1J2SigLabelRxJ2Msg         DisplayString(SIZE(0..64)),
            t1J2SigLabelExpSigLabel     INTEGER,
            t1J2SigLabelRxSigLabel      INTEGER,
            t1J2SigLabelTxSigLabel      INTEGER
        }

        t1J2SigLabelUnit  OBJECT-TYPE
            SYNTAX  UnitID
            ACCESS  read-only
            STATUS  mandatory
            DESCRIPTION
            "unit 1 to 4."
            ::= { t1J2SigLabelSetupEty 1 }

        t1J2SigLabelPort  OBJECT-TYPE
            SYNTAX  PortID
            ACCESS  read-only
            STATUS  mandatory
            DESCRIPTION
                "T1 Port 1 to 63"
            ::= { t1J2SigLabelSetupEty 2 }

        t1J2SigLabelJ2Length  OBJECT-TYPE
            SYNTAX  INTEGER{
                    null(1),
                    len-16-BYTE-space(2),
                    len-64-BYTE-space(3),
                    len-16-BYTE-null(4),
                    len-64-BYTE-null(5)
--                    len-1-BYTE(6)
                }
            ACCESS  read-write
            STATUS  mandatory
            DESCRIPTION
                "J2 message length"
            ::= { t1J2SigLabelSetupEty 3 }

        t1J2SigLabelExpJ2Msg OBJECT-TYPE
            SYNTAX  DisplayString (SIZE(0..64))
            ACCESS  read-write
            STATUS  mandatory
            DESCRIPTION
                "The expected J2 message"
            ::= { t1J2SigLabelSetupEty 4 }

        t1J2SigLabelTxJ2Msg OBJECT-TYPE
            SYNTAX  DisplayString (SIZE(0..64))
            ACCESS  read-write
            STATUS  mandatory
            DESCRIPTION
                "The tx J2 message"
            ::= { t1J2SigLabelSetupEty 5 }

        t1J2SigLabelRxJ2Msg OBJECT-TYPE
            SYNTAX  DisplayString (SIZE(0..64))
            ACCESS  read-only
            STATUS  mandatory
            DESCRIPTION
                "The rx J2 message"
            ::= { t1J2SigLabelSetupEty 6 }

        t1J2SigLabelExpSigLabel  OBJECT-TYPE
            SYNTAX  INTEGER{
                    unequipped(1),
                    equipped(2),
                    asynchronous(3),
                    bit-synchronous(4),
                    byte-synchronous(5),
                    extended-signal-label(6),
                    test-signal(7),
                    vc-ais(8)
                }
            ACCESS  read-write
            STATUS  mandatory
            DESCRIPTION
                "The expected Path Signal Label"
            ::= { t1J2SigLabelSetupEty 7 }

        t1J2SigLabelRxSigLabel  OBJECT-TYPE
            SYNTAX  INTEGER{
                    unequipped(1),
                    equipped(2),
                    asynchronous(3),
                    bit-synchronous(4),
                    byte-synchronous(5),
                    extended-signal-label(6),
                    test-signal(7),
                    vc-ais(8)
                }
            ACCESS  read-only
            STATUS  mandatory
            DESCRIPTION
                "The rx Path Signal Label"
            ::= { t1J2SigLabelSetupEty 8 }

        t1J2SigLabelTxSigLabel  OBJECT-TYPE
            SYNTAX  INTEGER{
                    unequipped(1),
                    equipped(2),
                    asynchronous(3),
                    bit-synchronous(4),
                    byte-synchronous(5),
                    extended-signal-label(6),
                    test-signal(7),
                    vc-ais(8)
                }
            ACCESS  read-write
            STATUS  mandatory
            DESCRIPTION
                "The tx Path Signal Label"
            ::= { t1J2SigLabelSetupEty 9 }

--
--  T1 Customer Information Setup Table
--

        t1CustomerInfoSetupTab  OBJECT-TYPE
            SYNTAX  SEQUENCE OF T1CustomerInfoSetupEty
            ACCESS  not-accessible
            STATUS  mandatory
            DESCRIPTION
                "Customer information setup table"
            ::= { hdT1Config 3 }

        t1CustomerInfoSetupEty  OBJECT-TYPE
            SYNTAX  T1CustomerInfoSetupEty
            ACCESS  not-accessible
            STATUS  mandatory
            DESCRIPTION
                "An entry in the customer information setup table"
            INDEX { t1CustomerInfoUnit ,
                    t1CustomerInfoPort }
            ::= { t1CustomerInfoSetupTab 1 }

        T1CustomerInfoSetupEty ::= SEQUENCE {
            t1CustomerInfoUnit          UnitID,
            t1CustomerInfoPort          PortID,
            t1CustomerInfoString        DisplayString(SIZE(0..20))
        }

        t1CustomerInfoUnit  OBJECT-TYPE
            SYNTAX  UnitID
            ACCESS  read-only
            STATUS  mandatory
            DESCRIPTION
            "unit 1 to 4."
            ::= { t1CustomerInfoSetupEty 1 }

        t1CustomerInfoPort  OBJECT-TYPE
            SYNTAX  PortID
            ACCESS  read-only
            STATUS  mandatory
            DESCRIPTION
                "T1 Port 1 to 63"
            ::= { t1CustomerInfoSetupEty 2 }

        t1CustomerInfoString OBJECT-TYPE
            SYNTAX  DisplayString (SIZE(0..20))
            ACCESS  read-write
            STATUS  mandatory
            DESCRIPTION
                "Customer information"
            ::= { t1CustomerInfoSetupEty 3 }

--
-- T1 TPSG Protection Setup Table
--
        t1TPSGProtectSetupTab  OBJECT-TYPE
            SYNTAX  SEQUENCE OF T1TPSGProtectSetupEty
            ACCESS  not-accessible
            STATUS  mandatory
            DESCRIPTION
                "TPSG protection setup table"
            ::= { hdT1Config 4 }

        t1TPSGProtectSetupEty  OBJECT-TYPE
            SYNTAX  T1TPSGProtectSetupEty
            ACCESS  not-accessible
            STATUS  mandatory
            DESCRIPTION
                "An entry in the TPSG protection setup table"
            INDEX { t1TPSGProtectUnit }
            ::= { t1TPSGProtectSetupTab 1 }

        T1TPSGProtectSetupEty ::= SEQUENCE {
            t1TPSGProtectUnit           UnitID,
            t1TPSGProtectActive         INTEGER,
            t1TPSGProtectStatus         INTEGER,
            t1TPSGProtectType           INTEGER,
            t1TPSGProtectMode           INTEGER
        }

        t1TPSGProtectUnit  OBJECT-TYPE
            SYNTAX  UnitID
            ACCESS  read-only
            STATUS  mandatory
            DESCRIPTION
            "unit 1 to 4."
            ::= { t1TPSGProtectSetupEty 1 }

        t1TPSGProtectActive  OBJECT-TYPE
            SYNTAX  INTEGER{
                    none(0),
                    standby(1),
                    working(2)
                }
            ACCESS  read-only
            STATUS  mandatory
            DESCRIPTION
                "TPSG active working/standby"
            ::= { t1TPSGProtectSetupEty 2 }

        t1TPSGProtectStatus  OBJECT-TYPE
            SYNTAX  INTEGER{
                    sync-failed(1),
                    sync-ok(2),
                    start-sync(3),
                    during-sync(4),
                    update-failed(5),
                    unsync(6)
                }
            ACCESS  read-only
            STATUS  mandatory
            DESCRIPTION
                "TPSG Status"
            ::= { t1TPSGProtectSetupEty 3 }

        t1TPSGProtectType  OBJECT-TYPE
            SYNTAX  INTEGER{
                    card-base-1-for-1(2),
                    port-circuit-protection(3),
                    line-1-plus-1(4)
                }
            ACCESS  read-write
            STATUS  mandatory
            DESCRIPTION
                "TPSG protection type"
            ::= { t1TPSGProtectSetupEty 4 }

        t1TPSGProtectMode  OBJECT-TYPE
            SYNTAX  INTEGER{
                    non-revertible(1),
                    revertible(2)
                }
            ACCESS  read-write
            STATUS  mandatory
            DESCRIPTION
                "TPSG protection mode"
            ::= { t1TPSGProtectSetupEty 5 }


--
--  T1 TU Mapping Mode Setup Table
--

        t1TuMapModeSetupTab  OBJECT-TYPE
            SYNTAX  SEQUENCE OF T1TuMapModeSetupEty
            ACCESS  not-accessible
            STATUS  mandatory
            DESCRIPTION
                "TU11/TU12 mapping mode setup table"
            ::= { hdT1Config 5 }

        t1TuMapModeSetupEty  OBJECT-TYPE
            SYNTAX  T1TuMapModeSetupEty
            ACCESS  not-accessible
            STATUS  mandatory
            DESCRIPTION
                "An entry in the TU11/TU12 mapping mode setup table"
            INDEX { t1TuMapModeUnit }
            ::= { t1TuMapModeSetupTab 1 }

        T1TuMapModeSetupEty ::= SEQUENCE {
            t1TuMapModeUnit             UnitID,
            t1TuMapModeTuMode           INTEGER
        }

        t1TuMapModeUnit  OBJECT-TYPE
            SYNTAX  UnitID
            ACCESS  read-only
            STATUS  mandatory
            DESCRIPTION
            "unit 1 to 4."
            ::= { t1TuMapModeSetupEty 1 }

        t1TuMapModeTuMode  OBJECT-TYPE
            SYNTAX  INTEGER{
                    tu12(1),
                    tu11(2)
                }
            ACCESS  read-write
            STATUS  mandatory
            DESCRIPTION
                "TU11/TU12 mapping mode"
            ::= { t1TuMapModeSetupEty 2 }

--
-- T1 TPSG Protection Switch Table
--
        t1TPSGProtectSwitchTab  OBJECT-TYPE
            SYNTAX  SEQUENCE OF T1TPSGProtectSwitchEty
            ACCESS  not-accessible
            STATUS  mandatory
            DESCRIPTION
                "TPSG protection switch table"
            ::= { hdT1Config 6 }

        t1TPSGProtectSwitchEty  OBJECT-TYPE
            SYNTAX  T1TPSGProtectSwitchEty
            ACCESS  not-accessible
            STATUS  mandatory
            DESCRIPTION
                "An entry in the TPSG protection switch table"
            INDEX { t1TPSGProSwitchUnit ,
                    t1TPSGProSwitchPort }
            ::= { t1TPSGProtectSwitchTab 1 }

        T1TPSGProtectSwitchEty ::= SEQUENCE {
            t1TPSGProSwitchUnit         UnitID,
            t1TPSGProSwitchPort         PortID,
            t1TPSGProSwitchSide         INTEGER
        }

        t1TPSGProSwitchUnit  OBJECT-TYPE
            SYNTAX  UnitID
            ACCESS  read-only
            STATUS  mandatory
            DESCRIPTION
            "unit 1 to 4."
            ::= { t1TPSGProtectSwitchEty 1 }

        t1TPSGProSwitchPort  OBJECT-TYPE
            SYNTAX  PortID
            ACCESS  read-only
            STATUS  mandatory
            DESCRIPTION
                "T1 Port 1 to 63"
            ::= { t1TPSGProtectSwitchEty 2 }

        t1TPSGProSwitchSide  OBJECT-TYPE
            SYNTAX  INTEGER {
                    left(1),
                    right(2),
                    left-all-port(3),
                    right-all-port(4)
                }
            ACCESS  read-write
            STATUS  mandatory
            DESCRIPTION
                "Switch Side(left/right)"
            ::= { t1TPSGProtectSwitchEty 3 }

--
--  T1 Channel RDI Mode Setup Table
--

        t1ChRDIModeSetupTab  OBJECT-TYPE
            SYNTAX  SEQUENCE OF T1ChRDIModeSetupEty
            ACCESS  not-accessible
            STATUS  mandatory
            DESCRIPTION
                "Channel RDI mode setup table"
            ::= { hdT1Config 7 }

        t1ChRDIModeSetupEty  OBJECT-TYPE
            SYNTAX  T1ChRDIModeSetupEty
            ACCESS  not-accessible
            STATUS  mandatory
            DESCRIPTION
                "An entry in the channel RDI mode setup table"
            INDEX { t1ChRDIModeUnit ,
                    t1ChRDIModePort }
            ::= { t1ChRDIModeSetupTab 1 }

        T1ChRDIModeSetupEty ::= SEQUENCE {
            t1ChRDIModeUnit             UnitID,
            t1ChRDIModePort             PortID,
            t1ChRDIModeMode             INTEGER
        }

        t1ChRDIModeUnit  OBJECT-TYPE
            SYNTAX  UnitID
            ACCESS  read-only
            STATUS  mandatory
            DESCRIPTION
            "unit 1 to 4."
            ::= { t1ChRDIModeSetupEty 1 }

        t1ChRDIModePort  OBJECT-TYPE
            SYNTAX  PortID
            ACCESS  read-only
            STATUS  mandatory
            DESCRIPTION
                "T1 Port 1 to 63"
            ::= { t1ChRDIModeSetupEty 2 }

        t1ChRDIModeMode  OBJECT-TYPE
            SYNTAX  INTEGER{
                    rdi(1),
                    e-rdi(2)
                }
            ACCESS  read-write
            STATUS  mandatory
            DESCRIPTION
                "RDI Monitor Mode(RDI/E-RDI)"
            ::= { t1ChRDIModeSetupEty 3 }

--
--  T1 LIU HighZ Setup Table
--

        t1LiuHighZSetupTab  OBJECT-TYPE
            SYNTAX  SEQUENCE OF T1LiuHighZSetupEty
            ACCESS  not-accessible
            STATUS  mandatory
            DESCRIPTION
                "LIU HighZ setup table"
            ::= { hdT1Config 8 }

        t1LiuHighZSetupEty  OBJECT-TYPE
            SYNTAX  T1LiuHighZSetupEty
            ACCESS  not-accessible
            STATUS  mandatory
            DESCRIPTION
                "An entry in the LIU HighZ setup table"
            INDEX { t1LiuHighZUnit ,
                    t1LiuHighZIndex }
            ::= { t1LiuHighZSetupTab 1 }

        T1LiuHighZSetupEty ::= SEQUENCE {
            t1LiuHighZUnit              UnitID,
            t1LiuHighZIndex             INTEGER,
            t1LiuHighZSetup             INTEGER
        }

        t1LiuHighZUnit  OBJECT-TYPE
            SYNTAX  UnitID
            ACCESS  read-only
            STATUS  mandatory
            DESCRIPTION
            "unit 1 to 4."
            ::= { t1LiuHighZSetupEty 1 }

        t1LiuHighZIndex  OBJECT-TYPE
            SYNTAX  INTEGER
            ACCESS  read-only
            STATUS  mandatory
            DESCRIPTION
                "T1 Port 1 to 63"
            ::= { t1LiuHighZSetupEty 2 }

        t1LiuHighZSetup  OBJECT-TYPE
            SYNTAX  INTEGER {
                    disable(1),
                    enable(2)
                }
            ACCESS  read-write
            STATUS  mandatory
            DESCRIPTION
                "Liu HighZ Setup(Disable/Enable)"
            ::= { t1LiuHighZSetupEty 3 }


--
--  T1 Alarm
--

    hdT1Alarm           OBJECT IDENTIFIER ::= { hdT1-card 2 }

--
--  T1 Alarm Mask Setup Table
--

        t1AlmMaskSetupTab  OBJECT-TYPE
            SYNTAX  SEQUENCE OF T1AlmMaskSetupEty
            ACCESS  not-accessible
            STATUS  mandatory
            DESCRIPTION
                "Alarm mask setup table"
            ::= { hdT1Alarm 1 }

        t1AlmMaskSetupEty  OBJECT-TYPE
            SYNTAX  T1AlmMaskSetupEty
            ACCESS  not-accessible
            STATUS  mandatory
            DESCRIPTION
                "An entry in the alarm mask setup table"
            INDEX { t1AlmMaskUnit ,
                    t1AlmMaskPort }
            ::= { t1AlmMaskSetupTab 1 }

        T1AlmMaskSetupEty ::= SEQUENCE {
            t1AlmMaskUnit               UnitID,
            t1AlmMaskPort               PortID,
            t1AlmMaskLoVT-LOP           INTEGER,
            t1AlmMaskLoVT-AIS           INTEGER,
            t1AlmMaskLoVT-UNEQ          INTEGER,
            t1AlmMaskLoVT-PLM           INTEGER,
            t1AlmMaskLoVT-TIM           INTEGER,
            t1AlmMaskLoVT-RDI-P         INTEGER,
            t1AlmMaskLoVT-RDI-S         INTEGER,
            t1AlmMaskLoVT-RDI-C         INTEGER,
            t1AlmMaskLoVT-V5-REI        INTEGER,
            t1AlmMaskLoVT-V5-BIP        INTEGER,
            t1AlmMaskLine-LOS           INTEGER,
            t1AlmMaskLine-AIS           INTEGER,
            t1AlmMaskLine-UAS           INTEGER,
            t1AlmMaskLine-YEL           INTEGER
        }

        t1AlmMaskUnit  OBJECT-TYPE
            SYNTAX  UnitID
            ACCESS  read-only
            STATUS  mandatory
            DESCRIPTION
            "unit 1 to 4."
            ::= { t1AlmMaskSetupEty 1 }

        t1AlmMaskPort  OBJECT-TYPE
            SYNTAX  PortID
            ACCESS  read-only
            STATUS  mandatory
            DESCRIPTION
                "T1 Port 1 to 63"
            ::= { t1AlmMaskSetupEty 2 }

        t1AlmMaskLoVT-LOP  OBJECT-TYPE
            SYNTAX  INTEGER{
                    disable(1),
                    enable(2)
                }
            ACCESS  read-write
            STATUS  mandatory
            DESCRIPTION
                "tu-lop alarm"
            ::= { t1AlmMaskSetupEty 3 }

        t1AlmMaskLoVT-AIS  OBJECT-TYPE
            SYNTAX  INTEGER{
                    disable(1),
                    enable(2)
                }
            ACCESS  read-write
            STATUS  mandatory
            DESCRIPTION
                "tu-ais alarm"
            ::= { t1AlmMaskSetupEty 4 }

        t1AlmMaskLoVT-UNEQ  OBJECT-TYPE
            SYNTAX  INTEGER{
                    disable(1),
                    enable(2)
                }
            ACCESS  read-write
            STATUS  mandatory
            DESCRIPTION
                "lp-uneq alarm"
            ::= { t1AlmMaskSetupEty 5 }

        t1AlmMaskLoVT-PLM  OBJECT-TYPE
            SYNTAX  INTEGER{
                    disable(1),
                    enable(2)
                }
            ACCESS  read-write
            STATUS  mandatory
            DESCRIPTION
                "lp-plm alarm"
            ::= { t1AlmMaskSetupEty 6 }

        t1AlmMaskLoVT-TIM  OBJECT-TYPE
            SYNTAX  INTEGER{
                    disable(1),
                    enable(2)
                }
            ACCESS  read-write
            STATUS  mandatory
            DESCRIPTION
                "lp-tim alarm"
            ::= { t1AlmMaskSetupEty 7 }

        t1AlmMaskLoVT-RDI-P  OBJECT-TYPE
            SYNTAX  INTEGER{
                    disable(1),
                    enable(2)
                }
            ACCESS  read-write
            STATUS  mandatory
            DESCRIPTION
                "lp-rdi-p alarm"
            ::= { t1AlmMaskSetupEty 8 }

        t1AlmMaskLoVT-RDI-S  OBJECT-TYPE
            SYNTAX  INTEGER{
                    disable(1),
                    enable(2)
                }
            ACCESS  read-write
            STATUS  mandatory
            DESCRIPTION
                "lp-rdi-s alarm"
            ::= { t1AlmMaskSetupEty 9 }

        t1AlmMaskLoVT-RDI-C  OBJECT-TYPE
            SYNTAX  INTEGER{
                    disable(1),
                    enable(2)
                }
            ACCESS  read-write
            STATUS  mandatory
            DESCRIPTION
                "lp-rdi-c alarm"
            ::= { t1AlmMaskSetupEty 10 }

        t1AlmMaskLoVT-V5-REI  OBJECT-TYPE
            SYNTAX  INTEGER{
                    disable(1),
                    enable(2)
                }
            ACCESS  read-write
            STATUS  mandatory
            DESCRIPTION
                "lp-rei alarm"
            ::= { t1AlmMaskSetupEty 11 }

        t1AlmMaskLoVT-V5-BIP  OBJECT-TYPE
            SYNTAX  INTEGER{
                    disable(1),
                    enable(2)
                }
            ACCESS  read-write
            STATUS  mandatory
            DESCRIPTION
                "lp-bip alarm"
            ::= { t1AlmMaskSetupEty 12 }

        t1AlmMaskLine-LOS  OBJECT-TYPE
            SYNTAX  INTEGER{
                    disable(1),
                    enable(2)
                }
            ACCESS  read-write
            STATUS  mandatory
            DESCRIPTION
                "line-los alarm"
            ::= { t1AlmMaskSetupEty 13 }

        t1AlmMaskLine-AIS  OBJECT-TYPE
            SYNTAX  INTEGER{
                    disable(1),
                    enable(2)
                }
            ACCESS  read-write
            STATUS  mandatory
            DESCRIPTION
                "line-ais alarm"
            ::= { t1AlmMaskSetupEty 14 }

        t1AlmMaskLine-UAS  OBJECT-TYPE
            SYNTAX  INTEGER{
                    disable(1),
                    enable(2)
                }
            ACCESS  read-write
            STATUS  mandatory
            DESCRIPTION
                "line-uas alarm"
            ::= { t1AlmMaskSetupEty 15 }

        t1AlmMaskLine-YEL  OBJECT-TYPE
            SYNTAX  INTEGER{
                    disable(1),
                    enable(2)
                }
            ACCESS  read-write
            STATUS  mandatory
            DESCRIPTION
                "line-yel alarm"
            ::= { t1AlmMaskSetupEty 16 }

--
--  T1 Alarm Relay Setup Table
--

        t1AlmRelaySetupTab  OBJECT-TYPE
            SYNTAX  SEQUENCE OF T1AlmRelaySetupEty
            ACCESS  not-accessible
            STATUS  mandatory
            DESCRIPTION
                "Alarm relay setup table"
            ::= { hdT1Alarm 2 }

        t1AlmRelaySetupEty  OBJECT-TYPE
            SYNTAX  T1AlmRelaySetupEty
            ACCESS  not-accessible
            STATUS  mandatory
            DESCRIPTION
                "An entry in the alarm relay setup table"
            INDEX { t1AlmRelayUnit ,
                    t1AlmRelayPort }
            ::= { t1AlmRelaySetupTab 1 }

        T1AlmRelaySetupEty ::= SEQUENCE {
            t1AlmRelayUnit              UnitID,
            t1AlmRelayPort              PortID,
            t1AlmRelayLoVT-LOP          INTEGER,
            t1AlmRelayLoVT-AIS          INTEGER,
            t1AlmRelayLoVT-UNEQ         INTEGER,
            t1AlmRelayLoVT-PLM          INTEGER,
            t1AlmRelayLoVT-TIM          INTEGER,
            t1AlmRelayLoVT-RDI-P        INTEGER,
            t1AlmRelayLoVT-RDI-S        INTEGER,
            t1AlmRelayLoVT-RDI-C        INTEGER,
            t1AlmRelayLoVT-V5-REI       INTEGER,
            t1AlmRelayLoVT-V5-BIP       INTEGER,
            t1AlmRelayLine-LOS          INTEGER,
            t1AlmRelayLine-AIS          INTEGER,
            t1AlmRelayLine-UAS          INTEGER,
            t1AlmRelayLine-YEL          INTEGER
        }

        t1AlmRelayUnit  OBJECT-TYPE
            SYNTAX  UnitID
            ACCESS  read-only
            STATUS  mandatory
            DESCRIPTION
            "unit 1 to 4."
            ::= { t1AlmRelaySetupEty 1 }

        t1AlmRelayPort  OBJECT-TYPE
            SYNTAX  PortID
            ACCESS  read-only
            STATUS  mandatory
            DESCRIPTION
                "T1 Port 1 to 63"
            ::= { t1AlmRelaySetupEty 2 }

        t1AlmRelayLoVT-LOP  OBJECT-TYPE
            SYNTAX  INTEGER{
                    disable(1),
                    enable(2)
                }
            ACCESS  read-write
            STATUS  mandatory
            DESCRIPTION
                "tu-lop alarm"
            ::= { t1AlmRelaySetupEty 3 }

        t1AlmRelayLoVT-AIS  OBJECT-TYPE
            SYNTAX  INTEGER{
                    disable(1),
                    enable(2)
                }
            ACCESS  read-write
            STATUS  mandatory
            DESCRIPTION
                "tu-ais alarm"
            ::= { t1AlmRelaySetupEty 4 }

        t1AlmRelayLoVT-UNEQ  OBJECT-TYPE
            SYNTAX  INTEGER{
                    disable(1),
                    enable(2)
                }
            ACCESS  read-write
            STATUS  mandatory
            DESCRIPTION
                "lp-uneq alarm"
            ::= { t1AlmRelaySetupEty 5 }

        t1AlmRelayLoVT-PLM  OBJECT-TYPE
            SYNTAX  INTEGER{
                    disable(1),
                    enable(2)
                }
            ACCESS  read-write
            STATUS  mandatory
            DESCRIPTION
                "lp-plm alarm"
            ::= { t1AlmRelaySetupEty 6 }

        t1AlmRelayLoVT-TIM  OBJECT-TYPE
            SYNTAX  INTEGER{
                    disable(1),
                    enable(2)
                }
            ACCESS  read-write
            STATUS  mandatory
            DESCRIPTION
                "lp-tim alarm"
            ::= { t1AlmRelaySetupEty 7 }

        t1AlmRelayLoVT-RDI-P  OBJECT-TYPE
            SYNTAX  INTEGER{
                    disable(1),
                    enable(2)
                }
            ACCESS  read-write
            STATUS  mandatory
            DESCRIPTION
                "lp-rdi-p alarm"
            ::= { t1AlmRelaySetupEty 8 }

        t1AlmRelayLoVT-RDI-S  OBJECT-TYPE
            SYNTAX  INTEGER{
                    disable(1),
                    enable(2)
                }
            ACCESS  read-write
            STATUS  mandatory
            DESCRIPTION
                "lp-rdi-s alarm"
            ::= { t1AlmRelaySetupEty 9 }

        t1AlmRelayLoVT-RDI-C  OBJECT-TYPE
            SYNTAX  INTEGER{
                    disable(1),
                    enable(2)
                }
            ACCESS  read-write
            STATUS  mandatory
            DESCRIPTION
                "lp-rdi-c alarm"
            ::= { t1AlmRelaySetupEty 10 }

        t1AlmRelayLoVT-V5-REI  OBJECT-TYPE
            SYNTAX  INTEGER{
                    disable(1),
                    enable(2)
                }
            ACCESS  read-write
            STATUS  mandatory
            DESCRIPTION
                "lp-rei alarm"
            ::= { t1AlmRelaySetupEty 11 }

        t1AlmRelayLoVT-V5-BIP  OBJECT-TYPE
            SYNTAX  INTEGER{
                    disable(1),
                    enable(2)
                }
            ACCESS  read-write
            STATUS  mandatory
            DESCRIPTION
                "lp-bip alarm"
            ::= { t1AlmRelaySetupEty 12 }

        t1AlmRelayLine-LOS  OBJECT-TYPE
            SYNTAX  INTEGER{
                    disable(1),
                    enable(2)
                }
            ACCESS  read-write
            STATUS  mandatory
            DESCRIPTION
                "line-los alarm"
            ::= { t1AlmRelaySetupEty 13 }

        t1AlmRelayLine-AIS  OBJECT-TYPE
            SYNTAX  INTEGER{
                    disable(1),
                    enable(2)
                }
            ACCESS  read-write
            STATUS  mandatory
            DESCRIPTION
                "line-ais alarm"
            ::= { t1AlmRelaySetupEty 14 }

        t1AlmRelayLine-UAS  OBJECT-TYPE
            SYNTAX  INTEGER{
                    disable(1),
                    enable(2)
                }
            ACCESS  read-write
            STATUS  mandatory
            DESCRIPTION
                "line-uas alarm"
            ::= { t1AlmRelaySetupEty 15 }

        t1AlmRelayLine-YEL  OBJECT-TYPE
            SYNTAX  INTEGER{
                    disable(1),
                    enable(2)
                }
            ACCESS  read-write
            STATUS  mandatory
            DESCRIPTION
                "line-yel alarm"
            ::= { t1AlmRelaySetupEty 16 }


--
--  T1 Alarm Severity Setup Table
--

        t1AlmSeveritySetupTab  OBJECT-TYPE
            SYNTAX  SEQUENCE OF T1AlmSeveritySetupEty
            ACCESS  not-accessible
            STATUS  mandatory
            DESCRIPTION
                "Alarm severity setup table"
            ::= { hdT1Alarm 3 }

        t1AlmSeveritySetupEty  OBJECT-TYPE
            SYNTAX  T1AlmSeveritySetupEty
            ACCESS  not-accessible
            STATUS  mandatory
            DESCRIPTION
                "An entry in the alarm severity setup table"
            INDEX { t1AlmSvrityUnit }
            ::= { t1AlmSeveritySetupTab 1 }

        T1AlmSeveritySetupEty ::= SEQUENCE {
            t1AlmSvrityUnit             UnitID,
            t1AlmSvrityLoVT-LOP         Severity,
            t1AlmSvrityLoVT-AIS         Severity,
            t1AlmSvrityLoVT-UNEQ        Severity,
            t1AlmSvrityLoVT-PLM         Severity,
            t1AlmSvrityLoVT-TIM         Severity,
            t1AlmSvrityLoVT-RDI-P       Severity,
            t1AlmSvrityLoVT-RDI-S       Severity,
            t1AlmSvrityLoVT-RDI-C       Severity,
            t1AlmSvrityLoVT-V5-REI      Severity,
            t1AlmSvrityLoVT-V5-BIP      Severity,
            t1AlmSvrityLine-LOS         Severity,
            t1AlmSvrityLine-AIS         Severity,
            t1AlmSvrityLine-UAS         Severity,
            t1AlmSvrityLine-YEL         Severity
        }

        t1AlmSvrityUnit  OBJECT-TYPE
            SYNTAX  UnitID
            ACCESS  read-only
            STATUS  mandatory
            DESCRIPTION
            "unit 1 to 4."
            ::= { t1AlmSeveritySetupEty 1 }

        t1AlmSvrityLoVT-LOP  OBJECT-TYPE
            SYNTAX  Severity
            ACCESS  read-write
            STATUS  mandatory
            DESCRIPTION
                "tu-lop alarm severity type"
            ::= { t1AlmSeveritySetupEty 2 }

        t1AlmSvrityLoVT-AIS  OBJECT-TYPE
            SYNTAX  Severity
            ACCESS  read-write
            STATUS  mandatory
            DESCRIPTION
                "tu-ais alarm severity type"
            ::= { t1AlmSeveritySetupEty 3 }

        t1AlmSvrityLoVT-UNEQ  OBJECT-TYPE
            SYNTAX  Severity
            ACCESS  read-write
            STATUS  mandatory
            DESCRIPTION
                "lp-uneq alarm severity type"
            ::= { t1AlmSeveritySetupEty 4 }

        t1AlmSvrityLoVT-PLM  OBJECT-TYPE
            SYNTAX  Severity
            ACCESS  read-write
            STATUS  mandatory
            DESCRIPTION
                "lp-plm alarm severity type"
            ::= { t1AlmSeveritySetupEty 5 }

        t1AlmSvrityLoVT-TIM  OBJECT-TYPE
            SYNTAX  Severity
            ACCESS  read-write
            STATUS  mandatory
            DESCRIPTION
                "lp-tim alarm severity type"
            ::= { t1AlmSeveritySetupEty 6 }

        t1AlmSvrityLoVT-RDI-P  OBJECT-TYPE
            SYNTAX  Severity
            ACCESS  read-write
            STATUS  mandatory
            DESCRIPTION
                "lp-rdi-p alarm severity type"
            ::= { t1AlmSeveritySetupEty 7 }

        t1AlmSvrityLoVT-RDI-S  OBJECT-TYPE
            SYNTAX  Severity
            ACCESS  read-write
            STATUS  mandatory
            DESCRIPTION
                "lp-rdi-s alarm severity type"
            ::= { t1AlmSeveritySetupEty 8 }

        t1AlmSvrityLoVT-RDI-C  OBJECT-TYPE
            SYNTAX  Severity
            ACCESS  read-write
            STATUS  mandatory
            DESCRIPTION
                "lp-rdi-c alarm severity type"
            ::= { t1AlmSeveritySetupEty 9 }

        t1AlmSvrityLoVT-V5-REI  OBJECT-TYPE
            SYNTAX  Severity
            ACCESS  read-write
            STATUS  mandatory
            DESCRIPTION
                "lp-rei alarm severity type"
            ::= { t1AlmSeveritySetupEty 10 }

        t1AlmSvrityLoVT-V5-BIP  OBJECT-TYPE
            SYNTAX  Severity
            ACCESS  read-write
            STATUS  mandatory
            DESCRIPTION
                "lp-bip alarm severity type"
            ::= { t1AlmSeveritySetupEty 11 }

        t1AlmSvrityLine-LOS  OBJECT-TYPE
            SYNTAX  Severity
            ACCESS  read-write
            STATUS  mandatory
            DESCRIPTION
                "line-los alarm severity type"
            ::= { t1AlmSeveritySetupEty 12 }

        t1AlmSvrityLine-AIS  OBJECT-TYPE
            SYNTAX  Severity
            ACCESS  read-write
            STATUS  mandatory
            DESCRIPTION
                "line-ais alarm severity type"
            ::= { t1AlmSeveritySetupEty 13 }

        t1AlmSvrityLine-UAS  OBJECT-TYPE
            SYNTAX  Severity
            ACCESS  read-write
            STATUS  mandatory
            DESCRIPTION
                "line-uas alarm severity type"
            ::= { t1AlmSeveritySetupEty 14 }

        t1AlmSvrityLine-YEL  OBJECT-TYPE
            SYNTAX  Severity
            ACCESS  read-write
            STATUS  mandatory
            DESCRIPTION
                "line-yel alarm severity type"
            ::= { t1AlmSeveritySetupEty 15 }


--
--  T1 Insert AIS Alarm Setup Table
--

        t1InsertAisAlmSetupTab  OBJECT-TYPE
            SYNTAX  SEQUENCE OF T1InsertAisAlmSetupEty
            ACCESS  not-accessible
            STATUS  mandatory
            DESCRIPTION
                "Insert AIS alarm setup table"
            ::= { hdT1Alarm 4 }

        t1InsertAisAlmSetupEty  OBJECT-TYPE
            SYNTAX  T1InsertAisAlmSetupEty
            ACCESS  not-accessible
            STATUS  mandatory
            DESCRIPTION
                "An entry in the insert AIS alarm setup table"
            INDEX { t1InstUnit }
            ::= { t1InsertAisAlmSetupTab 1 }

        T1InsertAisAlmSetupEty ::= SEQUENCE {
            t1InstUnit                  UnitID,
            t1InstTuLom-LomVToAis       INTEGER,
            t1InstTuLop-LopVToAis       INTEGER,
            t1InstLpUneq-UneqVToAis     INTEGER,
            t1InstLpPlm-PlmVToAis       INTEGER,
            t1InstLineLosToAis          INTEGER
        }

        t1InstUnit  OBJECT-TYPE
            SYNTAX  UnitID
            ACCESS  read-only
            STATUS  mandatory
            DESCRIPTION
            "unit 1 to 4."
            ::= { t1InsertAisAlmSetupEty 1 }

        t1InstTuLom-LomVToAis OBJECT-TYPE
            SYNTAX  INTEGER {
                    disable(1),
                    enable(2)
                }
            ACCESS  read-write
            STATUS  mandatory
            DESCRIPTION
                "tu-lom to ais"
            ::= { t1InsertAisAlmSetupEty 2 }

        t1InstTuLop-LopVToAis OBJECT-TYPE
            SYNTAX  INTEGER {
                    disable(1),
                    enable(2)
                }
            ACCESS  read-write
            STATUS  mandatory
            DESCRIPTION
                "tu-lop to ais"
            ::= { t1InsertAisAlmSetupEty 3 }

        t1InstLpUneq-UneqVToAis OBJECT-TYPE
            SYNTAX  INTEGER {
                    disable(1),
                    enable(2)
                }
            ACCESS  read-write
            STATUS  mandatory
            DESCRIPTION
                "lp-uneq to ais"
            ::= { t1InsertAisAlmSetupEty 4 }

        t1InstLpPlm-PlmVToAis OBJECT-TYPE
            SYNTAX  INTEGER {
                    disable(1),
                    enable(2)
                }
            ACCESS  read-write
            STATUS  mandatory
            DESCRIPTION
                "lp-plm to ais"
            ::= { t1InsertAisAlmSetupEty 5 }

        t1InstLineLosToAis OBJECT-TYPE
            SYNTAX  INTEGER {
                    disable(1),
                    enable(2)
                }
            ACCESS  read-write
            STATUS  mandatory
            DESCRIPTION
                "line-los to ais"
            ::= { t1InsertAisAlmSetupEty 6 }


--
--  T1 Current Alarm Status Table
--

        t1CurrAlmStatusTab  OBJECT-TYPE
            SYNTAX  SEQUENCE OF T1CurrAlmStatusEty
            ACCESS  not-accessible
            STATUS  mandatory
            DESCRIPTION
                "Current alarm status table"
            ::= { hdT1Alarm 5 }

        t1CurrAlmStatusEty  OBJECT-TYPE
            SYNTAX  T1CurrAlmStatusEty
            ACCESS  not-accessible
            STATUS  mandatory
            DESCRIPTION
                "An entry in the current alarm status table"
            INDEX { t1CurrAlmStsUnit ,
                    t1CurrAlmStsPort }
            ::= { t1CurrAlmStatusTab 1 }

        T1CurrAlmStatusEty ::= SEQUENCE {
            t1CurrAlmStsUnit            UnitID,
            t1CurrAlmStsPort            PortID,
            t1CurrAlmStsLoVT-LOP        AlmStatus,
            t1CurrAlmStsLoVT-AIS        AlmStatus,
            t1CurrAlmStsLoVT-UNEQ       AlmStatus,
            t1CurrAlmStsLoVT-PLM        AlmStatus,
            t1CurrAlmStsLoVT-TIM        AlmStatus,
            t1CurrAlmStsLoVT-RDI-P      AlmStatus,
            t1CurrAlmStsLoVT-RDI-S      AlmStatus,
            t1CurrAlmStsLoVT-RDI-C      AlmStatus,
            t1CurrAlmStsLoVT-V5-REI     AlmStatus,
            t1CurrAlmStsLoVT-V5-BIP     AlmStatus,
            t1CurrAlmStsLine-LOS        AlmStatus,
            t1CurrAlmStsLine-AIS        AlmStatus,
            t1CurrAlmStsLine-UAS        AlmStatus,
            t1CurrAlmStsLine-YEL        AlmStatus
        }

        t1CurrAlmStsUnit  OBJECT-TYPE
            SYNTAX  UnitID
            ACCESS  read-only
            STATUS  mandatory
            DESCRIPTION
            "unit 1 to 4."
            ::= { t1CurrAlmStatusEty 1 }

        t1CurrAlmStsPort  OBJECT-TYPE
            SYNTAX  PortID
            ACCESS  read-only
            STATUS  mandatory
            DESCRIPTION
                "T1 Port 1 to 63"
            ::= { t1CurrAlmStatusEty 2 }

        t1CurrAlmStsLoVT-LOP  OBJECT-TYPE
            SYNTAX  AlmStatus
            ACCESS  read-only
            STATUS  mandatory
            DESCRIPTION
                "tu-lop alarm severity status"
            ::= { t1CurrAlmStatusEty 3 }

        t1CurrAlmStsLoVT-AIS  OBJECT-TYPE
            SYNTAX  AlmStatus
            ACCESS  read-only
            STATUS  mandatory
            DESCRIPTION
                "tu-ais alarm severity status"
            ::= { t1CurrAlmStatusEty 4 }

        t1CurrAlmStsLoVT-UNEQ  OBJECT-TYPE
            SYNTAX  AlmStatus
            ACCESS  read-only
            STATUS  mandatory
            DESCRIPTION
                "lp-uneq alarm severity status"
            ::= { t1CurrAlmStatusEty 5 }

        t1CurrAlmStsLoVT-PLM  OBJECT-TYPE
            SYNTAX  AlmStatus
            ACCESS  read-only
            STATUS  mandatory
            DESCRIPTION
                "lp-plm alarm severity status"
            ::= { t1CurrAlmStatusEty 6 }

        t1CurrAlmStsLoVT-TIM  OBJECT-TYPE
            SYNTAX  AlmStatus
            ACCESS  read-only
            STATUS  mandatory
            DESCRIPTION
                "lp-tim alarm severity status"
            ::= { t1CurrAlmStatusEty 7 }

        t1CurrAlmStsLoVT-RDI-P  OBJECT-TYPE
            SYNTAX  AlmStatus
            ACCESS  read-only
            STATUS  mandatory
            DESCRIPTION
                "lp-rdi-p alarm severity status"
            ::= { t1CurrAlmStatusEty 8 }

        t1CurrAlmStsLoVT-RDI-S  OBJECT-TYPE
            SYNTAX  AlmStatus
            ACCESS  read-only
            STATUS  mandatory
            DESCRIPTION
                "lp-rdi-s alarm severity status"
            ::= { t1CurrAlmStatusEty 9 }

        t1CurrAlmStsLoVT-RDI-C  OBJECT-TYPE
            SYNTAX  AlmStatus
            ACCESS  read-only
            STATUS  mandatory
            DESCRIPTION
                "lp-rdi-c alarm severity status"
            ::= { t1CurrAlmStatusEty 10 }

        t1CurrAlmStsLoVT-V5-REI  OBJECT-TYPE
            SYNTAX  AlmStatus
            ACCESS  read-only
            STATUS  mandatory
            DESCRIPTION
                "lp-rei alarm severity status"
            ::= { t1CurrAlmStatusEty 11 }

        t1CurrAlmStsLoVT-V5-BIP  OBJECT-TYPE
            SYNTAX  AlmStatus
            ACCESS  read-only
            STATUS  mandatory
            DESCRIPTION
                "lp-bip alarm severity status"
            ::= { t1CurrAlmStatusEty 12 }

        t1CurrAlmStsLine-LOS  OBJECT-TYPE
            SYNTAX  AlmStatus
            ACCESS  read-only
            STATUS  mandatory
            DESCRIPTION
                "line-los alarm severity status"
            ::= { t1CurrAlmStatusEty 13 }

        t1CurrAlmStsLine-AIS  OBJECT-TYPE
            SYNTAX  AlmStatus
            ACCESS  read-only
            STATUS  mandatory
            DESCRIPTION
                "line-ais alarm severity status"
            ::= { t1CurrAlmStatusEty 14 }

        t1CurrAlmStsLine-UAS  OBJECT-TYPE
            SYNTAX  AlmStatus
            ACCESS  read-only
            STATUS  mandatory
            DESCRIPTION
                "line-uas alarm severity status"
            ::= { t1CurrAlmStatusEty 15 }

        t1CurrAlmStsLine-YEL  OBJECT-TYPE
            SYNTAX  AlmStatus
            ACCESS  read-only
            STATUS  mandatory
            DESCRIPTION
                "line-yel alarm severity status"
            ::= { t1CurrAlmStatusEty 16 }


--
--  T1 Current Active Alarm Summary Table
--
        t1CurrActAlmSummaryTab  OBJECT-TYPE
            SYNTAX  SEQUENCE OF T1CurrActAlmSummaryEty
            ACCESS  not-accessible
            STATUS  mandatory
            DESCRIPTION
                "T1 Current Active Alarm Summary Table."
            ::= { hdT1Alarm 6 }

        t1CurrActAlmSummaryEty  OBJECT-TYPE
            SYNTAX  T1CurrActAlmSummaryEty
            ACCESS  not-accessible
            STATUS  mandatory
            DESCRIPTION
                "t1 current active alarm summary entry"
            INDEX { t1AlmSumUnit ,
                    t1AlmSumIndex }
            ::= { t1CurrActAlmSummaryTab 1 }

        T1CurrActAlmSummaryEty ::= SEQUENCE {
            t1AlmSumUnit                UnitID,
            t1AlmSumIndex               INTEGER,
            t1AlmSumString              DisplayString (SIZE(0..255)),
            t1AlmSumUnitNum             CardID,
            t1AlmSumCardModel           CardModel,
            t1AlmSumPortNum             PortID,
--             t1AlmSumVcChan
--               INTEGER,
            t1AlmSumAlmNum              AlarmNum,
--             t1AlmSumVC43STS31Type
--               INTEGER,
--             t1AlmSumVC1xVTxType
--               INTEGER,
--             t1AlmSumVC4STS3
--               INTEGER,
--             t1AlmSumTUG3
--               INTEGER,
--             t1AlmSumTUG2VTG
--               INTEGER,
--             t1AlmSumVC1xVTx
--               INTEGER,
            t1AlmSumStatus              AlmStatus,
            t1AlmSumSeverity            Severity
        }

        t1AlmSumUnit  OBJECT-TYPE
            SYNTAX  UnitID
            ACCESS  read-only
            STATUS  mandatory
            DESCRIPTION
            "unit 1 to 4."
            ::= { t1CurrActAlmSummaryEty 1 }

        t1AlmSumIndex  OBJECT-TYPE
            SYNTAX  INTEGER
            ACCESS  read-only
            STATUS  mandatory
            DESCRIPTION
                "Select Alarm Summary Index"
            ::= { t1CurrActAlmSummaryEty 2 }

        t1AlmSumString  OBJECT-TYPE
            SYNTAX  DisplayString (SIZE (0..255))
            ACCESS  read-only
            STATUS  mandatory
            DESCRIPTION
                "Alarm Summary String"
            ::= { t1CurrActAlmSummaryEty 3 }

        t1AlmSumUnitNum  OBJECT-TYPE
            SYNTAX  CardID
            ACCESS  read-only
            STATUS  mandatory
            DESCRIPTION
            "Xcu or Unit 1~4,11~16"
            ::= { t1CurrActAlmSummaryEty 4 }

        t1AlmSumCardModel  OBJECT-TYPE
            SYNTAX  CardModel
            ACCESS  read-only
            STATUS  mandatory
            DESCRIPTION
                "Card Model"
            ::= { t1CurrActAlmSummaryEty 5 }

        t1AlmSumPortNum  OBJECT-TYPE
            SYNTAX  PortID
            ACCESS  read-only
            STATUS  mandatory
            DESCRIPTION
                "Port number(1..64)"
            ::= { t1CurrActAlmSummaryEty 6 }

--       t1AlmSumVcChan  OBJECT-TYPE
--           SYNTAX  INTEGER
--           ACCESS  read-only
--           STATUS  mandatory
--           DESCRIPTION
--              "VC Channel"
--           ::= { t1CurrActAlmSummaryEty 7 }

        t1AlmSumAlmNum  OBJECT-TYPE
            SYNTAX  AlarmNum
            ACCESS  read-only
            STATUS  mandatory
            DESCRIPTION
                "Alarm Num"
            ::= { t1CurrActAlmSummaryEty 8 }

--       t1AlmSumVC43STS31Type  OBJECT-TYPE
--           SYNTAX  INTEGER
--           ACCESS  read-only
--           STATUS  mandatory
--           DESCRIPTION
--              "AU4 or AU3 type in SDH, STS-3c or STS-1 type in SONET"
--           ::= { t1CurrActAlmSummaryEty 9 }

--       t1AlmSumVC1xVTxType  OBJECT-TYPE
--           SYNTAX  INTEGER
--           ACCESS  read-only
--           STATUS  mandatory
--           DESCRIPTION
--              "Tu1x type"
--           ::= { t1CurrActAlmSummaryEty 10 }

--       t1AlmSumVC4STS3  OBJECT-TYPE
--           SYNTAX  INTEGER(1..4)
--           ACCESS  read-only
--           STATUS  mandatory
--           DESCRIPTION
--              "The number of STM1"
--           ::= { t1CurrActAlmSummaryEty 11 }

--       t1AlmSumTUG3  OBJECT-TYPE
--           SYNTAX  INTEGER(1..3)
--           ACCESS  read-only
--           STATUS  mandatory
--           DESCRIPTION
--              "The number of Tug3"
--           ::= { t1CurrActAlmSummaryEty 12 }

--       t1AlmSumTUG2VTG  OBJECT-TYPE
--           SYNTAX  INTEGER(1..7)
--           ACCESS  read-only
--           STATUS  mandatory
--           DESCRIPTION
--              "The number of Tug2"
--           ::= { t1CurrActAlmSummaryEty 13 }

--       t1AlmSumVC1xVTx  OBJECT-TYPE
--           SYNTAX  INTEGER(1..4)
--           ACCESS  read-only
--           STATUS  mandatory
--           DESCRIPTION
--              "The number of Tu1x"
--           ::= { t1CurrActAlmSummaryEty 14 }

        t1AlmSumStatus  OBJECT-TYPE
            SYNTAX  AlmStatus
            ACCESS  read-only
            STATUS  mandatory
            DESCRIPTION
                "The Status of Alarm"
            ::= { t1CurrActAlmSummaryEty 15 }

        t1AlmSumSeverity  OBJECT-TYPE
            SYNTAX  Severity
            ACCESS  read-only
            STATUS  mandatory
            DESCRIPTION
                "Alarm Severity"
            ::= { t1CurrActAlmSummaryEty 16 }

--
--  T1 Loopback & Diagnostics
--

    t1LoopbackAndDiagnostics           OBJECT IDENTIFIER ::= { hdT1-card 3 }

--
--  T1 Loopback Setup Table
--

        t1LoopbackSetupTab  OBJECT-TYPE
            SYNTAX  SEQUENCE OF T1LoopbackSetupEty
            ACCESS  not-accessible
            STATUS  mandatory
            DESCRIPTION
                "Loopback setup table"
            ::= { t1LoopbackAndDiagnostics 1 }

        t1LoopbackSetupEty  OBJECT-TYPE
            SYNTAX  T1LoopbackSetupEty
            ACCESS  not-accessible
            STATUS  mandatory
            DESCRIPTION
                "An entry in the loopback setup table"
            INDEX { t1LoopbackUnit ,
                    t1LoopbackPort }
            ::= { t1LoopbackSetupTab 1 }

        T1LoopbackSetupEty ::= SEQUENCE {
            t1LoopbackUnit              UnitID,
            t1LoopbackPort              PortID,
            t1LoopbackLoopbackType      INTEGER
        }

        t1LoopbackUnit  OBJECT-TYPE
            SYNTAX  UnitID
            ACCESS  read-only
            STATUS  mandatory
            DESCRIPTION
            "unit 1 to 4."
            ::= { t1LoopbackSetupEty 1 }

        t1LoopbackPort  OBJECT-TYPE
            SYNTAX  PortID
            ACCESS  read-only
            STATUS  mandatory
            DESCRIPTION
                "T1 Port 1 to 63"
            ::= { t1LoopbackSetupEty 2 }

        t1LoopbackLoopbackType  OBJECT-TYPE
            SYNTAX  INTEGER{
                    off(1),
                    local(2),
                    line(3)
                }
            ACCESS  read-write
            STATUS  mandatory
            DESCRIPTION
                "Loopback type"
            ::= { t1LoopbackSetupEty 3 }


--
--  T1 Diagnostics Setup Table
--

        t1DiagnosticsSetupTab  OBJECT-TYPE
            SYNTAX  SEQUENCE OF T1DiagnosticsSetupEty
            ACCESS  not-accessible
            STATUS  mandatory
            DESCRIPTION
                "Diagnostics setup table"
            ::= { t1LoopbackAndDiagnostics 2 }

        t1DiagnosticsSetupEty  OBJECT-TYPE
            SYNTAX  T1DiagnosticsSetupEty
            ACCESS  not-accessible
            STATUS  mandatory
            DESCRIPTION
                "An entry in the diagnostics setup table"
            INDEX { t1DiagUnit ,
                    t1DiagPort }
            ::= { t1DiagnosticsSetupTab 1 }

        T1DiagnosticsSetupEty ::= SEQUENCE {
            t1DiagUnit                  UnitID,
            t1DiagPort                  PortID,
            t1DiagBertDirection         INTEGER,
            t1DiagBertPattern           INTEGER,
            t1DiagBertAction            INTEGER,
            t1DiagBertStatus            INTEGER,
            t1DiagElapseSecond          INTEGER,
            t1DiagBitError              INTEGER,
            t1DiagErrorSecond           INTEGER,
            t1DiagSevereErrorSecond     INTEGER
        }

        t1DiagUnit  OBJECT-TYPE
            SYNTAX  UnitID
            ACCESS  read-only
            STATUS  mandatory
            DESCRIPTION
            "unit 1 to 4."
            ::= { t1DiagnosticsSetupEty 1 }

        t1DiagPort  OBJECT-TYPE
            SYNTAX  PortID
            ACCESS  read-only
            STATUS  mandatory
            DESCRIPTION
                "T1 Port 1 to 63"
            ::= { t1DiagnosticsSetupEty 2 }

        t1DiagBertDirection  OBJECT-TYPE
            SYNTAX  INTEGER{
                    optical-site(1),
                    line-site(2)
                }
            ACCESS  read-write
            STATUS  mandatory
            DESCRIPTION
                "BERT test direction"
            ::= { t1DiagnosticsSetupEty 3 }

        t1DiagBertPattern  OBJECT-TYPE
            SYNTAX  INTEGER{
                    off(0),
                    patt-2exp11-1(1),
                    patt-2exp15-1(2),
                    patt-2exp20-1(3)
                }
            ACCESS  read-write
            STATUS  mandatory
            DESCRIPTION
                "BERT test pattern"
            ::= { t1DiagnosticsSetupEty 4 }

        t1DiagBertAction  OBJECT-TYPE
            SYNTAX  INTEGER{
                    reset(1)
                }
            ACCESS  read-write
            STATUS  mandatory
            DESCRIPTION
                "BERT test action"
            ::= { t1DiagnosticsSetupEty 5 }

        t1DiagBertStatus  OBJECT-TYPE
            SYNTAX  INTEGER{
                    unsync(1),
                    sync(2)
                }
            ACCESS  read-only
            STATUS  mandatory
            DESCRIPTION
                "BERT status"
            ::= { t1DiagnosticsSetupEty 6 }

        t1DiagElapseSecond  OBJECT-TYPE
            SYNTAX  INTEGER
            ACCESS  read-only
            STATUS  mandatory
            DESCRIPTION
                "BERT elapsed time(s)"
            ::= { t1DiagnosticsSetupEty 7 }

        t1DiagBitError  OBJECT-TYPE
            SYNTAX  INTEGER
            ACCESS  read-only
            STATUS  mandatory
            DESCRIPTION
                "BERT Bit Error"
            ::= { t1DiagnosticsSetupEty 8 }

        t1DiagErrorSecond  OBJECT-TYPE
            SYNTAX  INTEGER
            ACCESS  read-only
            STATUS  mandatory
            DESCRIPTION
                "BERT Error Seconds"
            ::= { t1DiagnosticsSetupEty 9 }

        t1DiagSevereErrorSecond  OBJECT-TYPE
            SYNTAX  INTEGER
            ACCESS  read-only
            STATUS  mandatory
            DESCRIPTION
                "BERT SES"
            ::= { t1DiagnosticsSetupEty 10 }

--
--  T1 Performance
--

    t1Performance           OBJECT IDENTIFIER ::= { hdT1-card 4 }

--
--  T1 Performance Report
--

    t1PerformanceReport           OBJECT IDENTIFIER ::= { t1Performance 1 }

--
--  T1 Performance Report LoPath/VTPath Current Table
--

        t1LoPath-VTPathCurrTab  OBJECT-TYPE
            SYNTAX  SEQUENCE OF T1LoPath-VTPathCurrEty
            ACCESS  not-accessible
            STATUS  mandatory
            DESCRIPTION
                "Performance report current"
            ::= { t1PerformanceReport 1 }

        t1LoPath-VTPathCurrEty  OBJECT-TYPE
            SYNTAX  T1LoPath-VTPathCurrEty
            ACCESS  not-accessible
            STATUS  mandatory
            DESCRIPTION
                "An entry in the performance report current table"
            INDEX { t1LoVTCurrUnit ,
                    t1LoVTCurrPort ,
                    t1LoVTCurrAnomalyType }
            ::= { t1LoPath-VTPathCurrTab 1 }

        T1LoPath-VTPathCurrEty ::= SEQUENCE {
            t1LoVTCurrUnit              UnitID,
            t1LoVTCurrPort              PortID,
            t1LoVTCurrAnomalyType       LoPathPerfAnomalyType,
            t1LoVTCurrEB-Count          INTEGER,
            t1LoVTCurrBBE-Count         INTEGER,
            t1LoVTCurrES-Count          INTEGER,
            t1LoVTCurrUAS-Count         INTEGER,
            t1LoVTCurrBES-Count         INTEGER,
            t1LoVTCurrSES-Count         INTEGER,
            t1LoVTCurr15MinTimeElaps    INTEGER,
            t1LoVTCurr24hrValid15Min    INTEGER,
            t1LoVTCurrDayValid15Min     INTEGER,
            t1LoVTCurr7DayValidDays     INTEGER
        }

        t1LoVTCurrUnit  OBJECT-TYPE
            SYNTAX  UnitID
            ACCESS  read-only
            STATUS  mandatory
            DESCRIPTION
            "unit 1 to 4."
            ::= { t1LoPath-VTPathCurrEty 1 }

        t1LoVTCurrPort  OBJECT-TYPE
            SYNTAX  PortID
            ACCESS  read-only
            STATUS  mandatory
            DESCRIPTION
                "T1 Port 1 to 63"
            ::= { t1LoPath-VTPathCurrEty 2 }

        t1LoVTCurrAnomalyType  OBJECT-TYPE
            SYNTAX  LoPathPerfAnomalyType
            ACCESS  read-only
            STATUS  mandatory
            DESCRIPTION
                "Performance report LoPath/VTPath Anomaly Type"
            ::= { t1LoPath-VTPathCurrEty 3 }

        t1LoVTCurrEB-Count  OBJECT-TYPE
            SYNTAX  INTEGER
            ACCESS  read-only
            STATUS  mandatory
            DESCRIPTION
                "Current Error Block"
            ::= { t1LoPath-VTPathCurrEty 4 }

        t1LoVTCurrBBE-Count  OBJECT-TYPE
            SYNTAX  INTEGER
            ACCESS  read-only
            STATUS  mandatory
            DESCRIPTION
                "Current Background Block Error"
            ::= { t1LoPath-VTPathCurrEty 5 }

        t1LoVTCurrES-Count  OBJECT-TYPE
            SYNTAX  INTEGER
            ACCESS  read-only
            STATUS  mandatory
            DESCRIPTION
                "Error Second"
            ::= { t1LoPath-VTPathCurrEty 6 }

        t1LoVTCurrUAS-Count  OBJECT-TYPE
            SYNTAX  INTEGER
            ACCESS  read-only
            STATUS  mandatory
            DESCRIPTION
                "Unavailable Second"
            ::= { t1LoPath-VTPathCurrEty 7 }

        t1LoVTCurrBES-Count  OBJECT-TYPE
            SYNTAX  INTEGER
            ACCESS  read-only
            STATUS  mandatory
            DESCRIPTION
                "Background Error Second"
            ::= { t1LoPath-VTPathCurrEty 8 }

        t1LoVTCurrSES-Count  OBJECT-TYPE
            SYNTAX  INTEGER
            ACCESS  read-only
            STATUS  mandatory
            DESCRIPTION
                "Severly Error Second"
            ::= { t1LoPath-VTPathCurrEty 9 }

        t1LoVTCurr15MinTimeElaps  OBJECT-TYPE
            SYNTAX  INTEGER
            ACCESS  read-only
            STATUS  mandatory
            DESCRIPTION
                "Valid Seconds in Current 15-Min Interval"
            ::= { t1LoPath-VTPathCurrEty 10 }

        t1LoVTCurr24hrValid15Min  OBJECT-TYPE
            SYNTAX  INTEGER
            ACCESS  read-only
            STATUS  mandatory
            DESCRIPTION
                "Valid 15-Min Intervals in Current 24-Hour Interval"
            ::= { t1LoPath-VTPathCurrEty 11 }

        t1LoVTCurrDayValid15Min  OBJECT-TYPE
            SYNTAX  INTEGER
            ACCESS  read-only
            STATUS  mandatory
            DESCRIPTION
                "Valid 15-Min Intervals in Current Day"
            ::= { t1LoPath-VTPathCurrEty 12 }

        t1LoVTCurr7DayValidDays  OBJECT-TYPE
            SYNTAX  INTEGER
            ACCESS  read-only
            STATUS  mandatory
            DESCRIPTION
                "Valid Days in Current Seven Day"
            ::= { t1LoPath-VTPathCurrEty 13 }


--
--  T1 Performance Report LoPath/VTPath Interval Table
--

        t1LoPath-VTPathIntvTab  OBJECT-TYPE
            SYNTAX  SEQUENCE OF T1LoPath-VTPathIntvEty
            ACCESS  not-accessible
            STATUS  mandatory
            DESCRIPTION
                "Performance report Inteval"
            ::= { t1PerformanceReport 2 }

        t1LoPath-VTPathIntvEty  OBJECT-TYPE
            SYNTAX  T1LoPath-VTPathIntvEty
            ACCESS  not-accessible
            STATUS  mandatory
            DESCRIPTION
                "An entry in the performance report interval table"
            INDEX { t1LoVTIntvUnit ,
                    t1LoVTIntvPort ,
                    t1LoVTIntvAnomalyType ,
                    t1LoVTIntvPeriod }
            ::= { t1LoPath-VTPathIntvTab 1 }

        T1LoPath-VTPathIntvEty ::= SEQUENCE {
            t1LoVTIntvUnit              UnitID,
            t1LoVTIntvPort              PortID,
            t1LoVTIntvAnomalyType       LoPathPerfAnomalyType,
            t1LoVTIntvPeriod            INTEGER (1..96),
            t1LoVTIntvEB-Count          INTEGER,
            t1LoVTIntvBBE-Count         INTEGER,
            t1LoVTIntvES-Count          INTEGER,
            t1LoVTIntvUAS-Count         INTEGER,
            t1LoVTIntvBES-Count         INTEGER,
            t1LoVTIntvSES-Count         INTEGER
        }

        t1LoVTIntvUnit  OBJECT-TYPE
            SYNTAX  UnitID
            ACCESS  read-only
            STATUS  mandatory
            DESCRIPTION
            "unit 1 to 4."
            ::= { t1LoPath-VTPathIntvEty 1 }

        t1LoVTIntvPort  OBJECT-TYPE
            SYNTAX  PortID
            ACCESS  read-only
            STATUS  mandatory
            DESCRIPTION
                "T1 Port 1 to 63"
            ::= { t1LoPath-VTPathIntvEty 2 }

        t1LoVTIntvAnomalyType  OBJECT-TYPE
            SYNTAX  LoPathPerfAnomalyType
            ACCESS  read-only
            STATUS  mandatory
            DESCRIPTION
                "Performance report LoPath/VTPath Anomaly Type"
            ::= { t1LoPath-VTPathIntvEty 3 }

        t1LoVTIntvPeriod  OBJECT-TYPE
            SYNTAX  INTEGER (1..96)
            ACCESS  read-only
            STATUS  mandatory
            DESCRIPTION
                "LoPath Interval Period"
            ::= { t1LoPath-VTPathIntvEty 4 }

        t1LoVTIntvEB-Count  OBJECT-TYPE
            SYNTAX  INTEGER
            ACCESS  read-only
            STATUS  mandatory
            DESCRIPTION
                "Current Error Block"
            ::= { t1LoPath-VTPathIntvEty 5 }

        t1LoVTIntvBBE-Count  OBJECT-TYPE
            SYNTAX  INTEGER
            ACCESS  read-only
            STATUS  mandatory
            DESCRIPTION
                "Current Background Block Error"
            ::= { t1LoPath-VTPathIntvEty 6 }

        t1LoVTIntvES-Count  OBJECT-TYPE
            SYNTAX  INTEGER
            ACCESS  read-only
            STATUS  mandatory
            DESCRIPTION
                "Error Second"
            ::= { t1LoPath-VTPathIntvEty 7 }

        t1LoVTIntvUAS-Count  OBJECT-TYPE
            SYNTAX  INTEGER
            ACCESS  read-only
            STATUS  mandatory
            DESCRIPTION
                "Unavailable Second"
            ::= { t1LoPath-VTPathIntvEty 8 }

        t1LoVTIntvBES-Count  OBJECT-TYPE
            SYNTAX  INTEGER
            ACCESS  read-only
            STATUS  mandatory
            DESCRIPTION
                "Background Error Second"
            ::= { t1LoPath-VTPathIntvEty 9 }

        t1LoVTIntvSES-Count  OBJECT-TYPE
            SYNTAX  INTEGER
            ACCESS  read-only
            STATUS  mandatory
            DESCRIPTION
                "Severly Error Second"
            ::= { t1LoPath-VTPathIntvEty 10 }


--
--  T1 Performance Report LoPath/VT-Path Seven Days Table
--

        t1LoPath-VTPath7DaysTab  OBJECT-TYPE
            SYNTAX  SEQUENCE OF T1LoPath-VTPath7DaysEty
            ACCESS  not-accessible
            STATUS  mandatory
            DESCRIPTION
                "Performance report Seven Days"
            ::= { t1PerformanceReport 3 }

        t1LoPath-VTPath7DaysEty  OBJECT-TYPE
            SYNTAX  T1LoPath-VTPath7DaysEty
            ACCESS  not-accessible
            STATUS  mandatory
            DESCRIPTION
                "An entry in the performance report seven days table"
            INDEX { t1LoVT7DaysUnit ,
                    t1LoVT7DaysPort ,
                    t1LoVT7DaysAnomalyType ,
                    t1LoVT7DaysDayIndex }
            ::= { t1LoPath-VTPath7DaysTab 1 }

        T1LoPath-VTPath7DaysEty ::= SEQUENCE {
            t1LoVT7DaysUnit             UnitID,
            t1LoVT7DaysPort             PortID,
            t1LoVT7DaysAnomalyType      LoPathPerfAnomalyType,
            t1LoVT7DaysDayIndex         INTEGER (1..7),
            t1LoVT7DaysDate             DisplayString (SIZE (0..255) ),
            t1LoVT7DaysEB-Count         INTEGER,
            t1LoVT7DaysBBE-Count        INTEGER,
            t1LoVT7DaysES-Count         INTEGER,
            t1LoVT7DaysUAS-Count        INTEGER,
            t1LoVT7DaysBES-Count        INTEGER,
            t1LoVT7DaysSES-Count        INTEGER
        }

        t1LoVT7DaysUnit  OBJECT-TYPE
            SYNTAX  UnitID
            ACCESS  read-only
            STATUS  mandatory
            DESCRIPTION
            "unit 1 to 4."
            ::= { t1LoPath-VTPath7DaysEty 1 }

        t1LoVT7DaysPort  OBJECT-TYPE
            SYNTAX  PortID
            ACCESS  read-only
            STATUS  mandatory
            DESCRIPTION
                "T1 Port 1 to 63"
            ::= { t1LoPath-VTPath7DaysEty 2 }

        t1LoVT7DaysAnomalyType  OBJECT-TYPE
            SYNTAX  LoPathPerfAnomalyType
            ACCESS  read-only
            STATUS  mandatory
            DESCRIPTION
                "Performance report LoPath/VTPath Anomaly Type"
            ::= { t1LoPath-VTPath7DaysEty 3 }

        t1LoVT7DaysDayIndex  OBJECT-TYPE
            SYNTAX  INTEGER (1..7)
            ACCESS  read-only
            STATUS  mandatory
            DESCRIPTION
                "LoPath Seven Days day index"
            ::= { t1LoPath-VTPath7DaysEty 4 }

        t1LoVT7DaysDate  OBJECT-TYPE
            SYNTAX  DisplayString (SIZE (0..255) )
            ACCESS  read-only
            STATUS  mandatory
            DESCRIPTION
                "Seven Days Date"
            ::= { t1LoPath-VTPath7DaysEty 5 }

        t1LoVT7DaysEB-Count  OBJECT-TYPE
            SYNTAX  INTEGER
            ACCESS  read-only
            STATUS  mandatory
            DESCRIPTION
                "Current Error Block"
            ::= { t1LoPath-VTPath7DaysEty 6 }

        t1LoVT7DaysBBE-Count  OBJECT-TYPE
            SYNTAX  INTEGER
            ACCESS  read-only
            STATUS  mandatory
            DESCRIPTION
                "Current Background Block Error"
            ::= { t1LoPath-VTPath7DaysEty 7 }

        t1LoVT7DaysES-Count  OBJECT-TYPE
            SYNTAX  INTEGER
            ACCESS  read-only
            STATUS  mandatory
            DESCRIPTION
                "Error Second"
            ::= { t1LoPath-VTPath7DaysEty 8 }

        t1LoVT7DaysUAS-Count  OBJECT-TYPE
            SYNTAX  INTEGER
            ACCESS  read-only
            STATUS  mandatory
            DESCRIPTION
                "Unavailable Second"
            ::= { t1LoPath-VTPath7DaysEty 9 }

        t1LoVT7DaysBES-Count  OBJECT-TYPE
            SYNTAX  INTEGER
            ACCESS  read-only
            STATUS  mandatory
            DESCRIPTION
                "Background Error Second"
            ::= { t1LoPath-VTPath7DaysEty 10 }

        t1LoVT7DaysSES-Count  OBJECT-TYPE
            SYNTAX  INTEGER
            ACCESS  read-only
            STATUS  mandatory
            DESCRIPTION
                "Severly Error Second"
            ::= { t1LoPath-VTPath7DaysEty 11 }


--
--  T1 Performance Report LoPath/VTPath Total Table
--

        t1LoPath-VTPathTotalTab  OBJECT-TYPE
            SYNTAX  SEQUENCE OF T1LoPath-VTPathTotalEty
            ACCESS  not-accessible
            STATUS  mandatory
            DESCRIPTION
                "Performance report Total"
            ::= { t1PerformanceReport 4 }

        t1LoPath-VTPathTotalEty  OBJECT-TYPE
            SYNTAX  T1LoPath-VTPathTotalEty
            ACCESS  not-accessible
            STATUS  mandatory
            DESCRIPTION
                "An entry in the performance report total table"
            INDEX { t1LoVTTotalUnit ,
                    t1LoVTTotalPort ,
                    t1LoVTTotalAnomalyType }
            ::= { t1LoPath-VTPathTotalTab 1 }

        T1LoPath-VTPathTotalEty ::= SEQUENCE {
            t1LoVTTotalUnit             UnitID,
            t1LoVTTotalPort             PortID,
            t1LoVTTotalAnomalyType      LoPathPerfAnomalyType,
            t1LoVTTotalEB-Count         INTEGER,
            t1LoVTTotalBBE-Count        INTEGER,
            t1LoVTTotalES-Count         INTEGER,
            t1LoVTTotalUAS-Count        INTEGER,
            t1LoVTTotalBES-Count        INTEGER,
            t1LoVTTotalSES-Count        INTEGER
        }

        t1LoVTTotalUnit  OBJECT-TYPE
            SYNTAX  UnitID
            ACCESS  read-only
            STATUS  mandatory
            DESCRIPTION
            "unit 1 to 4."
            ::= { t1LoPath-VTPathTotalEty 1 }

        t1LoVTTotalPort  OBJECT-TYPE
            SYNTAX  PortID
            ACCESS  read-only
            STATUS  mandatory
            DESCRIPTION
                "T1 Port 1 to 63"
            ::= { t1LoPath-VTPathTotalEty 2 }

        t1LoVTTotalAnomalyType  OBJECT-TYPE
            SYNTAX  LoPathPerfAnomalyType
            ACCESS  read-only
            STATUS  mandatory
            DESCRIPTION
                "Performance report LoPath/VTPath Anomaly Type"
            ::= { t1LoPath-VTPathTotalEty 3 }

        t1LoVTTotalEB-Count  OBJECT-TYPE
            SYNTAX  INTEGER
            ACCESS  read-only
            STATUS  mandatory
            DESCRIPTION
                "Current Error Block"
            ::= { t1LoPath-VTPathTotalEty 4 }

        t1LoVTTotalBBE-Count  OBJECT-TYPE
            SYNTAX  INTEGER
            ACCESS  read-only
            STATUS  mandatory
            DESCRIPTION
                "Current Background Block Error"
            ::= { t1LoPath-VTPathTotalEty 5 }

        t1LoVTTotalES-Count  OBJECT-TYPE
            SYNTAX  INTEGER
            ACCESS  read-only
            STATUS  mandatory
            DESCRIPTION
                "Error Second"
            ::= { t1LoPath-VTPathTotalEty 6 }

        t1LoVTTotalUAS-Count  OBJECT-TYPE
            SYNTAX  INTEGER
            ACCESS  read-only
            STATUS  mandatory
            DESCRIPTION
                "Unavailable Second"
            ::= { t1LoPath-VTPathTotalEty 7 }

        t1LoVTTotalBES-Count  OBJECT-TYPE
            SYNTAX  INTEGER
            ACCESS  read-only
            STATUS  mandatory
            DESCRIPTION
                "Background Error Second"
            ::= { t1LoPath-VTPathTotalEty 8 }

        t1LoVTTotalSES-Count  OBJECT-TYPE
            SYNTAX  INTEGER
            ACCESS  read-only
            STATUS  mandatory
            DESCRIPTION
                "Severly Error Second"
            ::= { t1LoPath-VTPathTotalEty 9 }

--
--  T1 Performance Report Line Current Table
--

        t1LineCurrTab  OBJECT-TYPE
            SYNTAX  SEQUENCE OF T1LineCurrEty
            ACCESS  not-accessible
            STATUS  mandatory
            DESCRIPTION
                "Performance report current"
            ::= { t1PerformanceReport 5 }

        t1LineCurrEty  OBJECT-TYPE
            SYNTAX  T1LineCurrEty
            ACCESS  not-accessible
            STATUS  mandatory
            DESCRIPTION
                "An entry in the performance report current table"
            INDEX { t1LineCurrUnit ,
                    t1LineCurrPort }
            ::= { t1LineCurrTab 1 }

        T1LineCurrEty ::= SEQUENCE {
            t1LineCurrUnit              UnitID,
            t1LineCurrPort              PortID,
            t1LineCurrES-Count          INTEGER,
            t1LineCurrUAS-Count         INTEGER,
            t1LineCurrBES-Count         INTEGER,
            t1LineCurrSES-Count         INTEGER,
            t1LineCurrBPV-Count         INTEGER,
            t1LineCurr15MinTimeElaps    INTEGER,
            t1LineCurr24hrValid15Min    INTEGER,
            t1LineCurrDayValid15Min     INTEGER,
            t1LineCurr7DayValidDays     INTEGER
        }

        t1LineCurrUnit  OBJECT-TYPE
            SYNTAX  UnitID
            ACCESS  read-only
            STATUS  mandatory
            DESCRIPTION
            "unit 1 to 4."
            ::= { t1LineCurrEty 1 }

        t1LineCurrPort  OBJECT-TYPE
            SYNTAX  PortID
            ACCESS  read-only
            STATUS  mandatory
            DESCRIPTION
                "T1 Port 1 to 63"
            ::= { t1LineCurrEty 2 }


        t1LineCurrES-Count  OBJECT-TYPE
            SYNTAX  INTEGER
            ACCESS  read-only
            STATUS  mandatory
            DESCRIPTION
                "Error Second"
            ::= { t1LineCurrEty 3 }

        t1LineCurrUAS-Count  OBJECT-TYPE
            SYNTAX  INTEGER
            ACCESS  read-only
            STATUS  mandatory
            DESCRIPTION
                "Unavailable Second"
            ::= { t1LineCurrEty 4 }

        t1LineCurrBES-Count  OBJECT-TYPE
            SYNTAX  INTEGER
            ACCESS  read-only
            STATUS  mandatory
            DESCRIPTION
                "Background Error Second"
            ::= { t1LineCurrEty 5 }

        t1LineCurrSES-Count  OBJECT-TYPE
            SYNTAX  INTEGER
            ACCESS  read-only
            STATUS  mandatory
            DESCRIPTION
                "Severly Error Second"
            ::= { t1LineCurrEty 6 }

        t1LineCurrBPV-Count  OBJECT-TYPE
            SYNTAX  INTEGER
            ACCESS  read-only
            STATUS  mandatory
            DESCRIPTION
                "Bipolar Violation"
            ::= { t1LineCurrEty 7 }

        t1LineCurr15MinTimeElaps  OBJECT-TYPE
            SYNTAX  INTEGER
            ACCESS  read-only
            STATUS  mandatory
            DESCRIPTION
                "Valid Seconds in Current 15-Min Interval"
            ::= { t1LineCurrEty 8 }

        t1LineCurr24hrValid15Min  OBJECT-TYPE
            SYNTAX  INTEGER
            ACCESS  read-only
            STATUS  mandatory
            DESCRIPTION
                "Valid 15-Min Intervals in Current 24-Hour Interval"
            ::= { t1LineCurrEty 9 }

        t1LineCurrDayValid15Min  OBJECT-TYPE
            SYNTAX  INTEGER
            ACCESS  read-only
            STATUS  mandatory
            DESCRIPTION
                "Valid 15-Min Intervals in Current Day"
            ::= { t1LineCurrEty 10 }

        t1LineCurr7DayValidDays  OBJECT-TYPE
            SYNTAX  INTEGER
            ACCESS  read-only
            STATUS  mandatory
            DESCRIPTION
                "Valid Days in Current Seven Day"
            ::= { t1LineCurrEty 11 }


--
--  T1 Performance Report Line Interval Table
--

        t1LineIntervalTab  OBJECT-TYPE
            SYNTAX  SEQUENCE OF T1LineIntervalEty
            ACCESS  not-accessible
            STATUS  mandatory
            DESCRIPTION
                "Performance report Inteval"
            ::= { t1PerformanceReport 6 }

        t1LineIntervalEty  OBJECT-TYPE
            SYNTAX  T1LineIntervalEty
            ACCESS  not-accessible
            STATUS  mandatory
            DESCRIPTION
                "An entry in the performance report interval table"
            INDEX { t1LineIntvUnit ,
                    t1LineIntvPort ,
                    t1LineIntvPeriod }
            ::= { t1LineIntervalTab 1 }

        T1LineIntervalEty ::= SEQUENCE {
            t1LineIntvUnit              UnitID,
            t1LineIntvPort              PortID,
            t1LineIntvPeriod            INTEGER (1..96),
            t1LineIntvES-Count          INTEGER,
            t1LineIntvUAS-Count         INTEGER,
            t1LineIntvBES-Count         INTEGER,
            t1LineIntvSES-Count         INTEGER,
            t1LineIntvBPV-Count         INTEGER,
            t1LineIntvESF-Count         INTEGER
        }

        t1LineIntvUnit  OBJECT-TYPE
            SYNTAX  UnitID
            ACCESS  read-only
            STATUS  mandatory
            DESCRIPTION
            "unit 1 to 4."
            ::= { t1LineIntervalEty 1 }

        t1LineIntvPort  OBJECT-TYPE
            SYNTAX  PortID
            ACCESS  read-only
            STATUS  mandatory
            DESCRIPTION
                "T1 Port 1 to 63"
            ::= { t1LineIntervalEty 2 }

        t1LineIntvPeriod  OBJECT-TYPE
            SYNTAX  INTEGER (1..96)
            ACCESS  read-only
            STATUS  mandatory
            DESCRIPTION
                "Line Interval Period"
            ::= { t1LineIntervalEty 3 }

        t1LineIntvES-Count  OBJECT-TYPE
            SYNTAX  INTEGER
            ACCESS  read-only
            STATUS  mandatory
            DESCRIPTION
                "Error Second"
            ::= { t1LineIntervalEty 4 }

        t1LineIntvUAS-Count  OBJECT-TYPE
            SYNTAX  INTEGER
            ACCESS  read-only
            STATUS  mandatory
            DESCRIPTION
                "Unavailable Second"
            ::= { t1LineIntervalEty 5 }

        t1LineIntvBES-Count  OBJECT-TYPE
            SYNTAX  INTEGER
            ACCESS  read-only
            STATUS  mandatory
            DESCRIPTION
                "Background Error Second"
            ::= { t1LineIntervalEty 6 }

        t1LineIntvSES-Count  OBJECT-TYPE
            SYNTAX  INTEGER
            ACCESS  read-only
            STATUS  mandatory
            DESCRIPTION
                "Severly Error Second"
            ::= { t1LineIntervalEty 7 }

        t1LineIntvBPV-Count  OBJECT-TYPE
            SYNTAX  INTEGER
            ACCESS  read-only
            STATUS  mandatory
            DESCRIPTION
                "Bipolar Violation"
            ::= { t1LineIntervalEty 8 }

        t1LineIntvESF-Count  OBJECT-TYPE
            SYNTAX  INTEGER
            ACCESS  read-only
            STATUS  mandatory
            DESCRIPTION
                "CRC + OOF Error"
            ::= { t1LineIntervalEty 9 }

--
--  T1 Performance Report Line Seven Days Table
--

        t1Line7DaysTab  OBJECT-TYPE
            SYNTAX  SEQUENCE OF T1Line7DaysEty
            ACCESS  not-accessible
            STATUS  mandatory
            DESCRIPTION
                "Performance report seven days"
            ::= { t1PerformanceReport 7 }

        t1Line7DaysEty  OBJECT-TYPE
            SYNTAX  T1Line7DaysEty
            ACCESS  not-accessible
            STATUS  mandatory
            DESCRIPTION
                "An entry in the performance report seven days table"
            INDEX { t1Line7DaysUnit ,
                    t1Line7DaysPort ,
                    t1Line7DaysDayIndex }
            ::= { t1Line7DaysTab 1 }

        T1Line7DaysEty ::= SEQUENCE {
            t1Line7DaysUnit             UnitID,
            t1Line7DaysPort             PortID,
            t1Line7DaysDayIndex         INTEGER (1..7),
            t1Line7DaysDate             DisplayString (SIZE (0..255) ),
            t1Line7DaysES-Count         INTEGER,
            t1Line7DaysUAS-Count        INTEGER,
            t1Line7DaysBES-Count        INTEGER,
            t1Line7DaysSES-Count        INTEGER,
            t1Line7DaysBPV-Count        INTEGER,
            t1Line7DaysESF-Count        INTEGER
        }

        t1Line7DaysUnit  OBJECT-TYPE
            SYNTAX  UnitID
            ACCESS  read-only
            STATUS  mandatory
            DESCRIPTION
            "unit 1 to 4."
            ::= { t1Line7DaysEty 1 }

        t1Line7DaysPort  OBJECT-TYPE
            SYNTAX  PortID
            ACCESS  read-only
            STATUS  mandatory
            DESCRIPTION
                "T1 Port 1 to 63"
            ::= { t1Line7DaysEty 2 }

        t1Line7DaysDayIndex  OBJECT-TYPE
            SYNTAX  INTEGER (1..7)
            ACCESS  read-only
            STATUS  mandatory
            DESCRIPTION
                "Line Seven Days day index"
            ::= { t1Line7DaysEty 3 }

        t1Line7DaysDate  OBJECT-TYPE
            SYNTAX  DisplayString (SIZE (0..255) )
            ACCESS  read-only
            STATUS  mandatory
            DESCRIPTION
                "Seven Days Date"
            ::= { t1Line7DaysEty 4 }

        t1Line7DaysES-Count  OBJECT-TYPE
            SYNTAX  INTEGER
            ACCESS  read-only
            STATUS  mandatory
            DESCRIPTION
                "Error Second"
            ::= { t1Line7DaysEty 5 }

        t1Line7DaysUAS-Count  OBJECT-TYPE
            SYNTAX  INTEGER
            ACCESS  read-only
            STATUS  mandatory
            DESCRIPTION
                "Unavailable Second"
            ::= { t1Line7DaysEty 6 }

        t1Line7DaysBES-Count  OBJECT-TYPE
            SYNTAX  INTEGER
            ACCESS  read-only
            STATUS  mandatory
            DESCRIPTION
                "Background Error Second"
            ::= { t1Line7DaysEty 7 }

        t1Line7DaysSES-Count  OBJECT-TYPE
            SYNTAX  INTEGER
            ACCESS  read-only
            STATUS  mandatory
            DESCRIPTION
                "Severly Error Second"
            ::= { t1Line7DaysEty 8 }

        t1Line7DaysBPV-Count  OBJECT-TYPE
            SYNTAX  INTEGER
            ACCESS  read-only
            STATUS  mandatory
            DESCRIPTION
                "Bipolar Violation"
            ::= { t1Line7DaysEty 9 }

        t1Line7DaysESF-Count  OBJECT-TYPE
            SYNTAX  INTEGER
            ACCESS  read-only
            STATUS  mandatory
            DESCRIPTION
                "CRC + OOF Error"
            ::= { t1Line7DaysEty 10 }


--
--  T1 Performance Report Line Total Table
--

        t1LineTotalTab  OBJECT-TYPE
            SYNTAX  SEQUENCE OF T1LineTotalEty
            ACCESS  not-accessible
            STATUS  mandatory
            DESCRIPTION
                "Performance report Total"
            ::= { t1PerformanceReport 8 }

        t1LineTotalEty  OBJECT-TYPE
            SYNTAX  T1LineTotalEty
            ACCESS  not-accessible
            STATUS  mandatory
            DESCRIPTION
                "An entry in the performance report total table"
            INDEX { t1LineTotalUnit ,
                    t1LineTotalPort }
            ::= { t1LineTotalTab 1 }

        T1LineTotalEty ::= SEQUENCE {
            t1LineTotalUnit             UnitID,
            t1LineTotalPort             PortID,
            t1LineTotalES-Count         INTEGER,
            t1LineTotalUAS-Count        INTEGER,
            t1LineTotalBES-Count        INTEGER,
            t1LineTotalSES-Count        INTEGER,
            t1LineTotalBPV-Count        INTEGER,
            t1LineTotalESF-Count        INTEGER
        }

        t1LineTotalUnit  OBJECT-TYPE
            SYNTAX  UnitID
            ACCESS  read-only
            STATUS  mandatory
            DESCRIPTION
            "unit 1 to 4."
            ::= { t1LineTotalEty 1 }

        t1LineTotalPort  OBJECT-TYPE
            SYNTAX  PortID
            ACCESS  read-only
            STATUS  mandatory
            DESCRIPTION
                "T1 Port 1 to 63"
            ::= { t1LineTotalEty 2 }

        t1LineTotalES-Count  OBJECT-TYPE
            SYNTAX  INTEGER
            ACCESS  read-only
            STATUS  mandatory
            DESCRIPTION
                "Error Second"
            ::= { t1LineTotalEty 3 }

        t1LineTotalUAS-Count  OBJECT-TYPE
            SYNTAX  INTEGER
            ACCESS  read-only
            STATUS  mandatory
            DESCRIPTION
                "Unavailable Second"
            ::= { t1LineTotalEty 4 }

        t1LineTotalBES-Count  OBJECT-TYPE
            SYNTAX  INTEGER
            ACCESS  read-only
            STATUS  mandatory
            DESCRIPTION
                "Background Error Second"
            ::= { t1LineTotalEty 5 }

        t1LineTotalSES-Count  OBJECT-TYPE
            SYNTAX  INTEGER
            ACCESS  read-only
            STATUS  mandatory
            DESCRIPTION
                "Severly Error Second"
            ::= { t1LineTotalEty 6 }

        t1LineTotalBPV-Count  OBJECT-TYPE
            SYNTAX  INTEGER
            ACCESS  read-only
            STATUS  mandatory
            DESCRIPTION
                "Bipolar Violation"
            ::= { t1LineTotalEty 7 }

        t1LineTotalESF-Count  OBJECT-TYPE
            SYNTAX  INTEGER
            ACCESS  read-only
            STATUS  mandatory
            DESCRIPTION
                "CRC + OOF Error"
            ::= { t1LineTotalEty 8 }

--
--  T1 Performance Threshold Setup Table
--

        t1PerfThreshSetupTab  OBJECT-TYPE
            SYNTAX  SEQUENCE OF T1PerfThreshSetupEty
            ACCESS  not-accessible
            STATUS  mandatory
            DESCRIPTION
                "Performance threshold setup"
            ::= { t1Performance 2 }

        t1PerfThreshSetupEty  OBJECT-TYPE
            SYNTAX  T1PerfThreshSetupEty
            ACCESS  not-accessible
            STATUS  mandatory
            DESCRIPTION
                "An entry in the performance threshold setup table"
            INDEX { t1PerfTCAUnit ,
                    t1PerfTCAMonitorPoint }
            ::= { t1PerfThreshSetupTab 1 }

        T1PerfThreshSetupEty ::= SEQUENCE {
            t1PerfTCAUnit               UnitID,
            t1PerfTCAMonitorPoint       INTEGER,
            t1PerfTCAEnable             INTEGER,
            t1PerfTCASeverity           Severity,
            t1PerfTCAThreshold          INTEGER
        }

        t1PerfTCAUnit  OBJECT-TYPE
            SYNTAX  UnitID
            ACCESS  read-only
            STATUS  mandatory
            DESCRIPTION
            "unit 1 to 4."
            ::= { t1PerfThreshSetupEty 1 }

        t1PerfTCAMonitorPoint  OBJECT-TYPE
            SYNTAX  INTEGER {
                    bip(1),
                    rei(2),
                    bpv(3)
                }
            ACCESS  read-only
            STATUS  mandatory
            DESCRIPTION
                "TCA monitor point index"
            ::= { t1PerfThreshSetupEty 2 }

        t1PerfTCAEnable  OBJECT-TYPE
            SYNTAX  INTEGER {
                    disable(1),
                    enable(2)
                }
            ACCESS  read-write
            STATUS  mandatory
            DESCRIPTION
                "TCA disable/enable"
            ::= { t1PerfThreshSetupEty 3 }

        t1PerfTCASeverity  OBJECT-TYPE
            SYNTAX  Severity
            ACCESS  read-write
            STATUS  mandatory
            DESCRIPTION
                "TCA Severity"
            ::= { t1PerfThreshSetupEty 4 }

        t1PerfTCAThreshold  OBJECT-TYPE
            SYNTAX  INTEGER (1..99999)
            ACCESS  read-write
            STATUS  mandatory
            DESCRIPTION
                "TCA threshold"
            ::= { t1PerfThreshSetupEty 5 }


--
--  T1 Performance Line Monitor Framer Setup Table
--

        t1LineMonFramerSetupTab  OBJECT-TYPE
            SYNTAX  SEQUENCE OF T1LineMonFramerSetupEty
            ACCESS  not-accessible
            STATUS  mandatory
            DESCRIPTION
                "Performance line monitor framer setup"
            ::= { t1Performance 3 }

        t1LineMonFramerSetupEty  OBJECT-TYPE
            SYNTAX  T1LineMonFramerSetupEty
            ACCESS  not-accessible
            STATUS  mandatory
            DESCRIPTION
                "An entry in the performance line monitor framer setup table"
            INDEX { t1LineMonFramerUnit ,
                    t1LineMonFramerPort }
            ::= { t1LineMonFramerSetupTab 1 }

        T1LineMonFramerSetupEty ::= SEQUENCE {
            t1LineMonFramerUnit         UnitID,
            t1LineMonFramerPort         PortID,
            t1LineMonFramerFrame        INTEGER
        }

        t1LineMonFramerUnit  OBJECT-TYPE
            SYNTAX  UnitID
            ACCESS  read-only
            STATUS  mandatory
            DESCRIPTION
            "unit 1 to 4."
            ::= { t1LineMonFramerSetupEty 1 }

        t1LineMonFramerPort  OBJECT-TYPE
            SYNTAX  PortID
            ACCESS  read-only
            STATUS  mandatory
            DESCRIPTION
                "T1 Port 1 to 63"
            ::= { t1LineMonFramerSetupEty 2 }

        t1LineMonFramerFrame  OBJECT-TYPE
            SYNTAX  INTEGER {
                    off(1),
                    d4(2),
                    esf(3)
                }
            ACCESS  read-write
            STATUS  mandatory
            DESCRIPTION
                "T1 line frame mode"
            ::= { t1LineMonFramerSetupEty 3 }

--
--  T1 Performance Control Setup Table
--

        t1PerfControlTab  OBJECT-TYPE
            SYNTAX  SEQUENCE OF T1PerfControlEty
            ACCESS  not-accessible
            STATUS  mandatory
            DESCRIPTION
                "Performance control"
            ::= { t1Performance 4 }

        t1PerfControlEty  OBJECT-TYPE
            SYNTAX  T1PerfControlEty
            ACCESS  not-accessible
            STATUS  mandatory
            DESCRIPTION
                "An entry in the performance control table"
            INDEX { t1PerfCtrlUnit }
            ::= { t1PerfControlTab 1 }

        T1PerfControlEty ::= SEQUENCE {
            t1PerfCtrlUnit              UnitID,
            t1PerfCtrlClearPerf         INTEGER
        }

        t1PerfCtrlUnit  OBJECT-TYPE
            SYNTAX  UnitID
            ACCESS  read-only
            STATUS  mandatory
            DESCRIPTION
            "unit 1 to 4."
            ::= { t1PerfControlEty 1 }

        t1PerfCtrlClearPerf  OBJECT-TYPE
            SYNTAX  INTEGER {
                    clear(1)
                }
            ACCESS  read-write
            STATUS  mandatory
            DESCRIPTION
                "Clear performance data"
            ::= { t1PerfControlEty 2 }

--
-- T1 SNCP APS Table
--

        t1SncpApsTab  OBJECT-TYPE
            SYNTAX  SEQUENCE OF  T1SncpApsEty
            ACCESS  not-accessible
            STATUS  mandatory
            DESCRIPTION
                "T1 SNCP/UPSR APS table "
            ::= { hdT1-card 5 }

        t1SncpApsEty  OBJECT-TYPE
            SYNTAX  T1SncpApsEty
            ACCESS  not-accessible
            STATUS  mandatory
            DESCRIPTION
                "T1 SNCP/UPSR APS entry"
            INDEX { t1SncpUnit , t1SncpPort }
            ::= { t1SncpApsTab 1 }

        T1SncpApsEty ::= SEQUENCE {
            t1SncpUnit                  UnitID,
            t1SncpPort                  PortID,
            t1SncpCurrentPathSlot       XcSlot,
            t1SncpCurrentPathPort       PortID,
            t1SncpPrimaryPathSlot       XcSlot,
            t1SncpPrimaryPathPort       PortID,
            t1SncpPPType                XcType,
            t1SncpCmd                   SncpUserCmd
        }

        t1SncpUnit  OBJECT-TYPE
            SYNTAX  UnitID
            ACCESS  read-only
            STATUS  mandatory
            DESCRIPTION
            "unit 1 to 4."
            ::= { t1SncpApsEty 1 }

        t1SncpPort  OBJECT-TYPE
            SYNTAX  PortID
            ACCESS  read-only
            STATUS  mandatory
            DESCRIPTION
                "PORT #1~#63"
            ::= { t1SncpApsEty 2 }

        t1SncpCurrentPathSlot  OBJECT-TYPE
            SYNTAX  XcSlot
            ACCESS  read-only
            STATUS  mandatory
            DESCRIPTION
                "SNCP/UPSR current path"
            ::= { t1SncpApsEty 3 }

        t1SncpCurrentPathPort  OBJECT-TYPE
            SYNTAX  PortID
            ACCESS  read-only
            STATUS  mandatory
            DESCRIPTION
                "SNCP/UPSR current path"
            ::= { t1SncpApsEty 4 }

        t1SncpPrimaryPathSlot  OBJECT-TYPE
            SYNTAX  XcSlot
            ACCESS  read-only
            STATUS  mandatory
            DESCRIPTION
                "SNCP/UPSR primary path"
            ::= { t1SncpApsEty 5 }

        t1SncpPrimaryPathPort  OBJECT-TYPE
            SYNTAX  PortID
            ACCESS  read-only
            STATUS  mandatory
            DESCRIPTION
                "SNCP/UPSR primary path"
            ::= { t1SncpApsEty 6 }

        t1SncpPPType  OBJECT-TYPE
            SYNTAX  XcType
            ACCESS  read-only
            STATUS  mandatory
            DESCRIPTION
                "SNCP/UPSR path protection type"
            ::= { t1SncpApsEty 7 }

        t1SncpCmd  OBJECT-TYPE
            SYNTAX  SncpUserCmd
            ACCESS  read-write
            STATUS  mandatory
            DESCRIPTION
                "SNCP/UPSR APS command"
            ::= { t1SncpApsEty 8 }

--
-- T1 LED Status Table
--

        t1LedStatusTab OBJECT-TYPE
            SYNTAX  SEQUENCE OF T1LedStatusEty
            ACCESS  not-accessible
            STATUS  mandatory
            DESCRIPTION
                "Led Status"
            ::= { hdT1-card 6 }

        t1LedStatusEty  OBJECT-TYPE
            SYNTAX  T1LedStatusEty
            ACCESS  not-accessible
            STATUS  mandatory
            DESCRIPTION
                "An entry in the led status table"
            INDEX { t1LedStsUnit }
            ::= { t1LedStatusTab 1 }

        T1LedStatusEty ::= SEQUENCE {
            t1LedStsUnit                UnitID,
            t1LedStsActiveLED           LedStatusType,
            t1LedStsTestLED             LedStatusType,
            t1LedStsAlarmLED            LedStatusType,
            t1LedStsE1-IndicatorLED     LedStatusType
        }

        t1LedStsUnit  OBJECT-TYPE
            SYNTAX  UnitID
            ACCESS  read-only
            STATUS  mandatory
            DESCRIPTION
            "unit 1 to 4."
            ::= { t1LedStatusEty 1 }

        t1LedStsActiveLED  OBJECT-TYPE
            SYNTAX  LedStatusType
            ACCESS  read-only
            STATUS  mandatory
            DESCRIPTION
                "Active Led Status"
            ::= { t1LedStatusEty 2 }

        t1LedStsTestLED  OBJECT-TYPE
            SYNTAX  LedStatusType
            ACCESS  read-only
            STATUS  mandatory
            DESCRIPTION
                "Test Led Status"
            ::= { t1LedStatusEty 3 }

        t1LedStsAlarmLED  OBJECT-TYPE
            SYNTAX  LedStatusType
            ACCESS  read-only
            STATUS  mandatory
            DESCRIPTION
                "Alarm Led Status"
            ::= { t1LedStatusEty 4 }

        t1LedStsE1-IndicatorLED  OBJECT-TYPE
            SYNTAX  LedStatusType
            ACCESS  read-only
            STATUS  mandatory
            DESCRIPTION
                "E1-Indicator Led Status"
            ::= { t1LedStatusEty 5 }

--
-- T1 Command Control Table
--

        t1CommandControlTab  OBJECT-TYPE
            SYNTAX  SEQUENCE OF T1CommandControlEty
            ACCESS  not-accessible
            STATUS  mandatory
            DESCRIPTION
                "Command control"
            ::= { hdT1-card 7 }

        t1CommandControlEty  OBJECT-TYPE
            SYNTAX  T1CommandControlEty
            ACCESS  not-accessible
            STATUS  mandatory
            DESCRIPTION
                "An entry in the command control table"
            INDEX { t1CmdCtrlUnit }
            ::= { t1CommandControlTab 1 }

        T1CommandControlEty ::= SEQUENCE {
            t1CmdCtrlUnit               UnitID,
            t1CmdCtrlUnitReset          INTEGER,
            t1CmdCtrlUnitLoadDefault    INTEGER
        }

        t1CmdCtrlUnit  OBJECT-TYPE
            SYNTAX  UnitID
            ACCESS  read-only
            STATUS  mandatory
            DESCRIPTION
            "unit 1 to 4."
            ::= { t1CommandControlEty 1 }

        t1CmdCtrlUnitReset  OBJECT-TYPE
            SYNTAX  INTEGER {
                    warm(1),
                    cold(2)
                }
            ACCESS  read-write
            STATUS  mandatory
            DESCRIPTION
                "Unit reset"
            ::= { t1CommandControlEty 2 }

        t1CmdCtrlUnitLoadDefault  OBJECT-TYPE
            SYNTAX  INTEGER {
                    load-default(1)
                }
            ACCESS  read-write
            STATUS  mandatory
            DESCRIPTION
                "Unit load default"
            ::= { t1CommandControlEty 3 }

--
--  T1 XC Display Table
--
        t1XcDisplayTab  OBJECT-TYPE
            SYNTAX  SEQUENCE OF  T1XcDisplayEty
            ACCESS  not-accessible
            STATUS  mandatory
            DESCRIPTION
                "T1 xc display table "
            ::= { hdT1-card 8 }

        t1XcDisplayEty  OBJECT-TYPE
            SYNTAX  T1XcDisplayEty
            ACCESS  not-accessible
            STATUS  mandatory
            DESCRIPTION
                "T1 xc display entry"
            INDEX { t1XcDispMapIndex ,
                    t1XcDispUnitIndex ,
                    t1XcDispPortIndex }
            ::= { t1XcDisplayTab 1 }

        T1XcDisplayEty ::= SEQUENCE {
            t1XcDispMapIndex            XcMap,
            t1XcDispUnitIndex           UnitID,
            t1XcDispPortIndex           PortID,
            t1XcDispSrcSlotType         NewXcModel,
            t1XcDispSrcSlot             XcSlot,
            t1XcDispSrcPort             PortID,
            t1XcDispSrcChannel          ChannelNum,
            t1XcDispSrcAug1Sts3Path     Aug1Sts3Num,
            t1XcDispSrcVc3Sts1Path      Vc3Sts1Num,
            t1XcDispSrcVc1xVtxPath      Vc1xVtxNum,
            t1XcDispXcGranularity       INTEGER,
            t1XcDispXcType              XcType
        }

        t1XcDispMapIndex  OBJECT-TYPE
            SYNTAX  XcMap
            ACCESS  read-only
            STATUS  mandatory
            DESCRIPTION
                "xc map index"
            ::= { t1XcDisplayEty 1 }

        t1XcDispUnitIndex  OBJECT-TYPE
            SYNTAX  UnitID
            ACCESS  read-only
            STATUS  mandatory
            DESCRIPTION
            "unit 1 to 4."
            ::= { t1XcDisplayEty 2 }

        t1XcDispPortIndex  OBJECT-TYPE
            SYNTAX  PortID
            ACCESS  read-only
            STATUS  mandatory
            DESCRIPTION
                "PORT index"
            ::= { t1XcDisplayEty 3 }

        t1XcDispSrcSlotType  OBJECT-TYPE
            SYNTAX  NewXcModel
            ACCESS  read-only
            STATUS  mandatory
            DESCRIPTION
                " Xc src Unit Type"
            ::= { t1XcDisplayEty 4 }

        t1XcDispSrcSlot  OBJECT-TYPE
            SYNTAX  XcSlot
            ACCESS  read-only
            STATUS  mandatory
            DESCRIPTION
                "Xc src Unit "
            ::= { t1XcDisplayEty 5 }

        t1XcDispSrcPort  OBJECT-TYPE
            SYNTAX  PortID
            ACCESS  read-only
            STATUS  mandatory
            DESCRIPTION
                "Xc src port "
            ::= { t1XcDisplayEty 6 }

        t1XcDispSrcChannel  OBJECT-TYPE
            SYNTAX  ChannelNum
            ACCESS  read-only
            STATUS  mandatory
            DESCRIPTION
                "Xc src channel "
            ::= { t1XcDisplayEty 7 }

        t1XcDispSrcAug1Sts3Path  OBJECT-TYPE
            SYNTAX  Aug1Sts3Num
            ACCESS  read-only
            STATUS  mandatory
            DESCRIPTION
                "Xc src AUG1/STS3 path"
            ::= { t1XcDisplayEty 8 }

        t1XcDispSrcVc3Sts1Path  OBJECT-TYPE
            SYNTAX  Vc3Sts1Num
            ACCESS  read-only
            STATUS  mandatory
            DESCRIPTION
                "Xc src VC3/STS1 path"
            ::= { t1XcDisplayEty 9 }

        t1XcDispSrcVc1xVtxPath  OBJECT-TYPE
            SYNTAX  Vc1xVtxNum
            ACCESS  read-only
            STATUS  mandatory
            DESCRIPTION
                "Xc src VC1x/VTx path"
            ::= { t1XcDisplayEty 10 }

        t1XcDispXcGranularity  OBJECT-TYPE
            SYNTAX  INTEGER {
                    tu3(2),
                    au3-sts1(3),
                    tu11-vt15(4),
                    tu12-vt2(5),
                    vc4-sts3c(6),
                    not-available(100)
                }
            ACCESS  read-only
            STATUS  mandatory
            DESCRIPTION
                "Xc granularity"
            ::= { t1XcDisplayEty 11 }

        t1XcDispXcType  OBJECT-TYPE
            SYNTAX  XcType
            ACCESS  read-only
            STATUS  mandatory
            DESCRIPTION
                "Xc type"
            ::= { t1XcDisplayEty 12 }

--
-- T1 Consolidation
--

    t1Consolidation      OBJECT IDENTIFIER ::= { hdT1-card 9 }

--
--  T1 XC Summary Hex Table
--
        t1XcSummaryHexTab  OBJECT-TYPE
            SYNTAX  SEQUENCE OF  T1XcSummaryHexEty
            ACCESS  not-accessible
            STATUS  mandatory
            DESCRIPTION
                "T1 Xc Summary HEX Table "
            ::= { t1Consolidation 1 }

        t1XcSummaryHexEty OBJECT-TYPE
            SYNTAX  T1XcSummaryHexEty
            ACCESS  not-accessible
            STATUS  mandatory
            DESCRIPTION
                "An entry in the T1 xc summary hex table."
            INDEX { t1XcSummMapIndex , t1XcSummUnitIndex }
            ::= { t1XcSummaryHexTab 1 }

        T1XcSummaryHexEty ::= SEQUENCE  {
            t1XcSummMapIndex            XcMap,
            t1XcSummUnitIndex           UnitID,
            t1XcSummSummary             OCTET STRING
        }

        t1XcSummMapIndex  OBJECT-TYPE
            SYNTAX  XcMap
            ACCESS  read-only
            STATUS  mandatory
            DESCRIPTION
                "xc map index"
            ::= { t1XcSummaryHexEty  1 }

        t1XcSummUnitIndex  OBJECT-TYPE
            SYNTAX  UnitID
            ACCESS  read-only
            STATUS  mandatory
            DESCRIPTION
                "unit index"
            ::= { t1XcSummaryHexEty  2 }

        t1XcSummSummary  OBJECT-TYPE
            SYNTAX  OCTET STRING(SIZE(9))
            ACCESS  read-only
            STATUS  mandatory
            DESCRIPTION
                "T1 XC Summary"
            ::= { t1XcSummaryHexEty  3 }

--
--  T1 LED Status Hex Table
--

        t1LedStatusHexTab  OBJECT-TYPE
            SYNTAX  SEQUENCE OF  T1LedStatusHexEty
            ACCESS  not-accessible
            STATUS  mandatory
            DESCRIPTION
                "T1 led status hex Table "
            ::= { t1Consolidation 2 }

        t1LedStatusHexEty OBJECT-TYPE
            SYNTAX  T1LedStatusHexEty
            ACCESS  not-accessible
            STATUS  mandatory
            DESCRIPTION
                "An entry in the T1 led status hex table."
            INDEX { t1LedStsHexUnit }
            ::= { t1LedStatusHexTab 1 }

        T1LedStatusHexEty ::= SEQUENCE  {
            t1LedStsHexUnit             UnitID,
            t1LedStsHexData             OCTET STRING
        }

        t1LedStsHexUnit  OBJECT-TYPE
            SYNTAX  UnitID
            ACCESS  read-only
            STATUS  mandatory
            DESCRIPTION
                "unit index"
            ::= { t1LedStatusHexEty  1 }

        t1LedStsHexData  OBJECT-TYPE
            SYNTAX  OCTET STRING
            ACCESS  read-only
            STATUS  mandatory
            DESCRIPTION
                "Hex data"
            ::= { t1LedStatusHexEty  2 }

--
--  T1 General Config Hex Table
--

        t1GeneralCfgHexTab  OBJECT-TYPE
            SYNTAX  SEQUENCE OF  T1GeneralCfgHexEty
            ACCESS  not-accessible
            STATUS  mandatory
            DESCRIPTION
                "T1 general config hex Table "
            ::= { t1Consolidation 3 }

        t1GeneralCfgHexEty OBJECT-TYPE
            SYNTAX  T1GeneralCfgHexEty
            ACCESS  not-accessible
            STATUS  mandatory
            DESCRIPTION
                "An entry in the T1 general config hex table."
            INDEX { t1GenCfgHexUnit }
            ::= { t1GeneralCfgHexTab 1 }

        T1GeneralCfgHexEty ::= SEQUENCE  {
            t1GenCfgHexUnit             UnitID,
            t1GenCfgHexData             OCTET STRING
        }

        t1GenCfgHexUnit  OBJECT-TYPE
            SYNTAX  UnitID
            ACCESS  read-only
            STATUS  mandatory
            DESCRIPTION
                "unit index"
            ::= { t1GeneralCfgHexEty  1 }

        t1GenCfgHexData  OBJECT-TYPE
            SYNTAX  OCTET STRING
            ACCESS  read-only
            STATUS  mandatory
            DESCRIPTION
                "Hex data"
            ::= { t1GeneralCfgHexEty  2 }

--
--  T1 Alarm Hex Table
--

    t1AlarmHex      OBJECT IDENTIFIER ::= { t1Consolidation 4 }

--
--  T1 Alarm Mask Hex Table
--

        t1AlmMaskHexTab  OBJECT-TYPE
            SYNTAX  SEQUENCE OF  T1AlmMaskHexEty
            ACCESS  not-accessible
            STATUS  mandatory
            DESCRIPTION
                "T1 alarm mask hex Table "
            ::= { t1AlarmHex 1 }

        t1AlmMaskHexEty OBJECT-TYPE
            SYNTAX  T1AlmMaskHexEty
            ACCESS  not-accessible
            STATUS  mandatory
            DESCRIPTION
                "An entry in the T1 alarm mask hex table."
            INDEX { t1AlmMaskHexUnit }
            ::= { t1AlmMaskHexTab 1 }

        T1AlmMaskHexEty ::= SEQUENCE  {
            t1AlmMaskHexUnit            UnitID,
            t1AlmMaskHexData            OCTET STRING
        }

        t1AlmMaskHexUnit  OBJECT-TYPE
            SYNTAX  UnitID
            ACCESS  read-only
            STATUS  mandatory
            DESCRIPTION
                "unit index"
            ::= { t1AlmMaskHexEty  1 }

        t1AlmMaskHexData  OBJECT-TYPE
            SYNTAX  OCTET STRING
            ACCESS  read-only
            STATUS  mandatory
            DESCRIPTION
                "Hex data"
            ::= { t1AlmMaskHexEty  2 }

--
--  T1 Alarm Relay Hex Table
--

        t1AlmRelayHexTab  OBJECT-TYPE
            SYNTAX  SEQUENCE OF  T1AlmRelayHexEty
            ACCESS  not-accessible
            STATUS  mandatory
            DESCRIPTION
                "T1 alarm relay hex Table "
            ::= { t1AlarmHex 2 }

        t1AlmRelayHexEty OBJECT-TYPE
            SYNTAX  T1AlmRelayHexEty
            ACCESS  not-accessible
            STATUS  mandatory
            DESCRIPTION
                "An entry in the T1 alarm relay hex table."
            INDEX { t1AlmRelayHexUnit }
            ::= { t1AlmRelayHexTab 1 }

        T1AlmRelayHexEty ::= SEQUENCE  {
            t1AlmRelayHexUnit           UnitID,
            t1AlmRelayHexData           OCTET STRING
        }

        t1AlmRelayHexUnit  OBJECT-TYPE
            SYNTAX  UnitID
            ACCESS  read-only
            STATUS  mandatory
            DESCRIPTION
                "unit index"
            ::= { t1AlmRelayHexEty  1 }

        t1AlmRelayHexData  OBJECT-TYPE
            SYNTAX  OCTET STRING
            ACCESS  read-only
            STATUS  mandatory
            DESCRIPTION
                "Hex data"
            ::= { t1AlmRelayHexEty  2 }

--
--  T1 Alarm Severity Hex Table
--

        t1AlmSeverityHexTab  OBJECT-TYPE
            SYNTAX  SEQUENCE OF  T1AlmSeverityHexEty
            ACCESS  not-accessible
            STATUS  mandatory
            DESCRIPTION
                "T1 alarm severity hex Table "
            ::= { t1AlarmHex 3 }

        t1AlmSeverityHexEty OBJECT-TYPE
            SYNTAX  T1AlmSeverityHexEty
            ACCESS  not-accessible
            STATUS  mandatory
            DESCRIPTION
                "An entry in the T1 alarm severity hex table."
            INDEX { t1AlmSeverityHexUnit }
            ::= { t1AlmSeverityHexTab 1 }

        T1AlmSeverityHexEty ::= SEQUENCE  {
            t1AlmSeverityHexUnit        UnitID,
            t1AlmSeverityHexData        OCTET STRING
        }

        t1AlmSeverityHexUnit  OBJECT-TYPE
            SYNTAX  UnitID
            ACCESS  read-only
            STATUS  mandatory
            DESCRIPTION
                "unit index"
            ::= { t1AlmSeverityHexEty  1 }

        t1AlmSeverityHexData  OBJECT-TYPE
            SYNTAX  OCTET STRING
            ACCESS  read-only
            STATUS  mandatory
            DESCRIPTION
                "Hex data"
            ::= { t1AlmSeverityHexEty  2 }

--
--  T1 Alarm Status Hex Table
--

        t1AlmStatusHexTab  OBJECT-TYPE
            SYNTAX  SEQUENCE OF  T1AlmStatusHexEty
            ACCESS  not-accessible
            STATUS  mandatory
            DESCRIPTION
                "T1 alarm status hex Table "
            ::= { t1AlarmHex 4 }

        t1AlmStatusHexEty OBJECT-TYPE
            SYNTAX  T1AlmStatusHexEty
            ACCESS  not-accessible
            STATUS  mandatory
            DESCRIPTION
                "An entry in the T1 alarm status hex table."
            INDEX { t1AlmStatusHexUnit }
            ::= { t1AlmStatusHexTab 1 }

        T1AlmStatusHexEty ::= SEQUENCE  {
            t1AlmStatusHexUnit          UnitID,
            t1AlmStatusHexData          OCTET STRING
        }

        t1AlmStatusHexUnit  OBJECT-TYPE
            SYNTAX  UnitID
            ACCESS  read-only
            STATUS  mandatory
            DESCRIPTION
                "unit index"
            ::= { t1AlmStatusHexEty  1 }

        t1AlmStatusHexData  OBJECT-TYPE
            SYNTAX  OCTET STRING
            ACCESS  read-only
            STATUS  mandatory
            DESCRIPTION
                "Hex data"
            ::= { t1AlmStatusHexEty  2 }

--
--  T1 Loopback and Diagnostic Hex Table
--

        t1LoopbackDiagHexTab  OBJECT-TYPE
            SYNTAX  SEQUENCE OF  T1LoopbackDiagHexEty
            ACCESS  not-accessible
            STATUS  mandatory
            DESCRIPTION
                "T1 loopback and diagnostic hex Table "
            ::= { t1Consolidation 5 }

        t1LoopbackDiagHexEty OBJECT-TYPE
            SYNTAX  T1LoopbackDiagHexEty
            ACCESS  not-accessible
            STATUS  mandatory
            DESCRIPTION
                "An entry in the T1 alarm status hex table."
            INDEX { t1LoopBkDiagHexUnit }
            ::= { t1LoopbackDiagHexTab 1 }

        T1LoopbackDiagHexEty ::= SEQUENCE  {
            t1LoopBkDiagHexUnit         UnitID,
            t1LoopBkDiagHexData         OCTET STRING
        }

        t1LoopBkDiagHexUnit  OBJECT-TYPE
            SYNTAX  UnitID
            ACCESS  read-only
            STATUS  mandatory
            DESCRIPTION
                "unit index"
            ::= { t1LoopbackDiagHexEty  1 }

        t1LoopBkDiagHexData  OBJECT-TYPE
            SYNTAX  OCTET STRING
            ACCESS  read-only
            STATUS  mandatory
            DESCRIPTION
                "Hex data"
            ::= { t1LoopbackDiagHexEty  2 }

--
--  T1 Alarm Hex Table
--

    t1PerformanceHex      OBJECT IDENTIFIER ::= { t1Consolidation 6 }

--
--  T1 24hour Performance Summary Hex Table
--

        t1PerfSummaryHexTab  OBJECT-TYPE
            SYNTAX  SEQUENCE OF  T1PerfSummaryHexEty
            ACCESS  not-accessible
            STATUS  mandatory
            DESCRIPTION
                "T1 performance summary hex Table "
            ::= { t1PerformanceHex 1 }

        t1PerfSummaryHexEty OBJECT-TYPE
            SYNTAX  T1PerfSummaryHexEty
            ACCESS  not-accessible
            STATUS  mandatory
            DESCRIPTION
                "An entry in the T1 performance summary hex table."
            INDEX { t1PerfSummaryHexUnit ,
                    t1PerfSummaryHexPort }
            ::= { t1PerfSummaryHexTab 1 }

        T1PerfSummaryHexEty ::= SEQUENCE  {
            t1PerfSummaryHexUnit        UnitID,
            t1PerfSummaryHexPort        PortID,
            t1PerfSummaryHexData        OCTET STRING
        }

        t1PerfSummaryHexUnit  OBJECT-TYPE
            SYNTAX  UnitID
            ACCESS  read-only
            STATUS  mandatory
            DESCRIPTION
                "unit index"
            ::= { t1PerfSummaryHexEty  1 }

        t1PerfSummaryHexPort  OBJECT-TYPE
            SYNTAX  PortID
            ACCESS  read-only
            STATUS  mandatory
            DESCRIPTION
                "unit index"
            ::= { t1PerfSummaryHexEty  2 }

        t1PerfSummaryHexData  OBJECT-TYPE
            SYNTAX  OCTET STRING
            ACCESS  read-only
            STATUS  mandatory
            DESCRIPTION
                "Hex data"
            ::= { t1PerfSummaryHexEty  3 }

--
--  T1 15Min Interval Performance Hex Table
--

        t1Perf15MinIntvHexTab  OBJECT-TYPE
            SYNTAX  SEQUENCE OF  T1Perf15MinIntvHexEty
            ACCESS  not-accessible
            STATUS  mandatory
            DESCRIPTION
                "T1 15 min interval performance hex Table "
            ::= { t1PerformanceHex 2 }

        t1Perf15MinIntvHexEty OBJECT-TYPE
            SYNTAX  T1Perf15MinIntvHexEty
            ACCESS  not-accessible
            STATUS  mandatory
            DESCRIPTION
                "An entry in the T1 15 min interval performance hex table."
            INDEX { t1Perf15MIntvHexUnit ,
                    t1Perf15MIntvHexPort ,
                    t1Perf15MIntvHexAnomaly ,
                    t1Perf15MIntvHexIntv }
            ::= { t1Perf15MinIntvHexTab 1 }

        T1Perf15MinIntvHexEty ::= SEQUENCE  {
            t1Perf15MIntvHexUnit        UnitID,
            t1Perf15MIntvHexPort        PortID,
            t1Perf15MIntvHexAnomaly     INTEGER,
            t1Perf15MIntvHexIntv        INTEGER,
            t1Perf15MIntvHexData        OCTET STRING
        }

        t1Perf15MIntvHexUnit  OBJECT-TYPE
            SYNTAX  UnitID
            ACCESS  read-only
            STATUS  mandatory
            DESCRIPTION
                "unit index"
            ::= { t1Perf15MinIntvHexEty  1 }

        t1Perf15MIntvHexPort  OBJECT-TYPE
            SYNTAX  PortID
            ACCESS  read-only
            STATUS  mandatory
            DESCRIPTION
                "unit index"
            ::= { t1Perf15MinIntvHexEty  2 }

        t1Perf15MIntvHexAnomaly  OBJECT-TYPE
            SYNTAX  INTEGER {
                    bip-v5(1),
                    rei-v5(2),
                    t1-line(3)
                }
            ACCESS  read-only
            STATUS  mandatory
            DESCRIPTION
                "anomal type"
            ::= { t1Perf15MinIntvHexEty  3 }

        t1Perf15MIntvHexIntv  OBJECT-TYPE
            SYNTAX  INTEGER (1..96)
            ACCESS  read-only
            STATUS  mandatory
            DESCRIPTION
                "interval value"
            ::= { t1Perf15MinIntvHexEty  4 }

        t1Perf15MIntvHexData  OBJECT-TYPE
            SYNTAX  OCTET STRING
            ACCESS  read-only
            STATUS  mandatory
            DESCRIPTION
                "Hex data"
            ::= { t1Perf15MinIntvHexEty  5 }

--
--  T1 TPSG Protection Switch Hex Table
--

        t1TPSGProtSwitchHexTab  OBJECT-TYPE
            SYNTAX  SEQUENCE OF  T1TPSGProtSwitchHexEty
            ACCESS  not-accessible
            STATUS  mandatory
            DESCRIPTION
                "T1 TPSG protection switch hex Table "
            ::= { t1Consolidation 7 }

        t1TPSGProtSwitchHexEty OBJECT-TYPE
            SYNTAX  T1TPSGProtSwitchHexEty
            ACCESS  not-accessible
            STATUS  mandatory
            DESCRIPTION
                "An entry in the T1 TPSG protection switch hex table."
            INDEX { t1TPSGSwitchHexUnit }
            ::= { t1TPSGProtSwitchHexTab 1 }

        T1TPSGProtSwitchHexEty ::= SEQUENCE  {
            t1TPSGSwitchHexUnit         UnitID,
            t1TPSGSwitchHexData         OCTET STRING
        }

        t1TPSGSwitchHexUnit  OBJECT-TYPE
            SYNTAX  UnitID
            ACCESS  read-only
            STATUS  mandatory
            DESCRIPTION
                "unit index"
            ::= { t1TPSGProtSwitchHexEty  1 }

        t1TPSGSwitchHexData  OBJECT-TYPE
            SYNTAX  OCTET STRING
            ACCESS  read-only
            STATUS  mandatory
            DESCRIPTION
                "Hex data"
            ::= { t1TPSGProtSwitchHexEty  2 }

--2011-3-18 elvis below
--
--  New T1 XC Display Table
--
        new-t1XcDisplayTab  OBJECT-TYPE
            SYNTAX  SEQUENCE OF  NewT1XcDisplayEty
            ACCESS  not-accessible
            STATUS  mandatory
            DESCRIPTION
                "T1 xc display table "
            ::= { hdT1-card 10 }

        new-t1XcDisplayEty  OBJECT-TYPE
            SYNTAX  NewT1XcDisplayEty
            ACCESS  not-accessible
            STATUS  mandatory
            DESCRIPTION
                "T1 xc display entry"
            INDEX { new-t1XcDispMapIndex ,
                    new-t1XcDispUnitIndex ,
                    new-t1XcDispPortIndex }
            ::= { new-t1XcDisplayTab 1 }

        NewT1XcDisplayEty ::= SEQUENCE {
            new-t1XcDispMapIndex        XcMap,
            new-t1XcDispUnitIndex       UnitID,
            new-t1XcDispPortIndex       PortID,
            new-t1XcDispPriSlotType     NewXcModel,
            new-t1XcDispPriSlot         XcSlot,
            new-t1XcDispPriPort         PortID,
            new-t1XcDispPriChannel      ChannelNum,
            new-t1XcDispPriAug1Sts3Path Aug1Sts3Num,
            new-t1XcDispPriVc3Sts1Path  Vc3Sts1Num,
            new-t1XcDispPriVc1xVtxPath  Vc1xVtxNum,
            new-t1XcDispXcGranularity   INTEGER,
            new-t1XcDispXcType          XcType,
            new-t1XcDispSecSlotType     NewXcModel,
            new-t1XcDispSecSlot         XcSlot,
            new-t1XcDispSecPort         PortID,
            new-t1XcDispSecChannel      ChannelNum,
            new-t1XcDispSecAug1Sts3Path Aug1Sts3Num,
            new-t1XcDispSecVc3Sts1Path  Vc3Sts1Num,
            new-t1XcDispSecVc1xVtxPath  Vc1xVtxNum
        }

        new-t1XcDispMapIndex  OBJECT-TYPE
            SYNTAX  XcMap
            ACCESS  read-only
            STATUS  mandatory
            DESCRIPTION
                "xc map index"
            ::= { new-t1XcDisplayEty 1 }

        new-t1XcDispUnitIndex  OBJECT-TYPE
            SYNTAX  UnitID
            ACCESS  read-only
            STATUS  mandatory
            DESCRIPTION
                "unit 1 to 8, total 8 units."
            ::= { new-t1XcDisplayEty 2 }

        new-t1XcDispPortIndex  OBJECT-TYPE
            SYNTAX  PortID
            ACCESS  read-only
            STATUS  mandatory
            DESCRIPTION
                "PORT index"
            ::= { new-t1XcDisplayEty 3 }

        new-t1XcDispPriSlotType  OBJECT-TYPE
            SYNTAX  NewXcModel
            ACCESS  read-only
            STATUS  mandatory
            DESCRIPTION
                " Xc Primary Unit Type"
            ::= { new-t1XcDisplayEty 4 }

        new-t1XcDispPriSlot  OBJECT-TYPE
            SYNTAX  XcSlot
            ACCESS  read-only
            STATUS  mandatory
            DESCRIPTION
                "Xc Primary Unit "
            ::= { new-t1XcDisplayEty 5 }

        new-t1XcDispPriPort  OBJECT-TYPE
            SYNTAX  PortID
            ACCESS  read-only
            STATUS  mandatory
            DESCRIPTION
                "Xc Primary port "
            ::= { new-t1XcDisplayEty 6 }

        new-t1XcDispPriChannel  OBJECT-TYPE
            SYNTAX  ChannelNum
            ACCESS  read-only
            STATUS  mandatory
            DESCRIPTION
                "Xc Primary channel "
            ::= { new-t1XcDisplayEty 7 }

        new-t1XcDispPriAug1Sts3Path  OBJECT-TYPE
            SYNTAX  Aug1Sts3Num
            ACCESS  read-only
            STATUS  mandatory
            DESCRIPTION
                "Xc Primary AUG1/STS3 path"
            ::= { new-t1XcDisplayEty 8 }

        new-t1XcDispPriVc3Sts1Path  OBJECT-TYPE
            SYNTAX  Vc3Sts1Num
            ACCESS  read-only
            STATUS  mandatory
            DESCRIPTION
                "Xc Primary VC3/STS1 path"
            ::= { new-t1XcDisplayEty 9 }

        new-t1XcDispPriVc1xVtxPath  OBJECT-TYPE
            SYNTAX  Vc1xVtxNum
            ACCESS  read-only
            STATUS  mandatory
            DESCRIPTION
                "Xc Primary VC1x/VTx path"
            ::= { new-t1XcDisplayEty 10 }

        new-t1XcDispXcGranularity  OBJECT-TYPE
            SYNTAX  INTEGER {
                    tu3(2),
                    au3-sts1(3),
                    tu11-vt15(4),
                    tu12-vt2(5),
                    vc4-sts3c(6),
                    not-available(100)
                }
            ACCESS  read-only
            STATUS  mandatory
            DESCRIPTION
                "Xc granularity"
            ::= { new-t1XcDisplayEty 11 }

        new-t1XcDispXcType  OBJECT-TYPE
            SYNTAX  XcType
            ACCESS  read-only
            STATUS  mandatory
            DESCRIPTION
                "Xc type"
            ::= { new-t1XcDisplayEty 12 }

        new-t1XcDispSecSlotType  OBJECT-TYPE
            SYNTAX  NewXcModel
            ACCESS  read-only
            STATUS  mandatory
            DESCRIPTION
                " Xc Secondary Unit Type"
            ::= { new-t1XcDisplayEty 13 }

        new-t1XcDispSecSlot  OBJECT-TYPE
            SYNTAX  XcSlot
            ACCESS  read-only
            STATUS  mandatory
            DESCRIPTION
                "Xc Secondary Unit "
            ::= { new-t1XcDisplayEty 14 }

        new-t1XcDispSecPort  OBJECT-TYPE
            SYNTAX  PortID
            ACCESS  read-only
            STATUS  mandatory
            DESCRIPTION
                "Xc Secondary port "
            ::= { new-t1XcDisplayEty 15 }

        new-t1XcDispSecChannel  OBJECT-TYPE
            SYNTAX  ChannelNum
            ACCESS  read-only
            STATUS  mandatory
            DESCRIPTION
                "Xc Secondary channel "
            ::= { new-t1XcDisplayEty 16 }

        new-t1XcDispSecAug1Sts3Path  OBJECT-TYPE
            SYNTAX  Aug1Sts3Num
            ACCESS  read-only
            STATUS  mandatory
            DESCRIPTION
                "Xc Secondary AUG1/STS3 path"
            ::= { new-t1XcDisplayEty 17 }

        new-t1XcDispSecVc3Sts1Path  OBJECT-TYPE
            SYNTAX  Vc3Sts1Num
            ACCESS  read-only
            STATUS  mandatory
            DESCRIPTION
                "Xc Secondary VC3/STS1 path"
            ::= { new-t1XcDisplayEty 18 }

        new-t1XcDispSecVc1xVtxPath  OBJECT-TYPE
            SYNTAX  Vc1xVtxNum
            ACCESS  read-only
            STATUS  mandatory
            DESCRIPTION
                "Xc Secondary VC1x/VTx path"
            ::= { new-t1XcDisplayEty 19 }

--
-- New T1 SNCP/UPSR APS Table
--

        new-t1SncpApsTab  OBJECT-TYPE
            SYNTAX  SEQUENCE OF  NewT1SncpApsEty
            ACCESS  not-accessible
            STATUS  mandatory
            DESCRIPTION
                "T1 SNCP/UPSR APS table "
            ::= { hdT1-card 11 }

        new-t1SncpApsEty  OBJECT-TYPE
            SYNTAX  NewT1SncpApsEty
            ACCESS  not-accessible
            STATUS  mandatory
            DESCRIPTION
                "T1 SNCP/UPSR APS entry"
            INDEX { new-t1SncpUnit , new-t1SncpPort }
            ::= { new-t1SncpApsTab 1 }

        NewT1SncpApsEty ::= SEQUENCE {
            new-t1SncpUnit              UnitID,
            new-t1SncpPort              PortID,
            new-t1SncpCurrSlot          XcSlot,
            new-t1SncpCurrPort          PortID,
            new-t1SncpCurrChannel       ChannelNum,
            new-t1SncpCurrAug1Sts3Path  Aug1Sts3Num,
            new-t1SncpCurrVc3Sts1Path   Vc3Sts1Num,
            new-t1SncpCurrVc1xVtxPath   Vc1xVtxNum,
            new-t1SncpPPType            XcType,
            new-t1SncpCmd               SncpUserCmd,
            new-t1SncpRevertive         INTEGER
        }

        new-t1SncpUnit  OBJECT-TYPE
            SYNTAX  UnitID
            ACCESS  read-only
            STATUS  mandatory
            DESCRIPTION
                "unit 1 to 8, total 8 units."
            ::= { new-t1SncpApsEty 1 }

        new-t1SncpPort  OBJECT-TYPE
            SYNTAX  PortID
            ACCESS  read-only
            STATUS  mandatory
            DESCRIPTION
                "PORT #1~#63"
            ::= { new-t1SncpApsEty 2 }

        new-t1SncpCurrSlot  OBJECT-TYPE
            SYNTAX  XcSlot
            ACCESS  read-only
            STATUS  mandatory
            DESCRIPTION
                "SNCP/UPSR current slot"
            ::= { new-t1SncpApsEty 3 }

        new-t1SncpCurrPort  OBJECT-TYPE
            SYNTAX  PortID
            ACCESS  read-only
            STATUS  mandatory
            DESCRIPTION
                "SNCP/UPSR current port"
            ::= { new-t1SncpApsEty 4 }

        new-t1SncpCurrChannel  OBJECT-TYPE
            SYNTAX  ChannelNum
            ACCESS  read-only
            STATUS  mandatory
            DESCRIPTION
                "SNCP/UPSR current channel"
            ::= { new-t1SncpApsEty 5 }

        new-t1SncpCurrAug1Sts3Path  OBJECT-TYPE
            SYNTAX  Aug1Sts3Num
            ACCESS  read-only
            STATUS  mandatory
            DESCRIPTION
                "SNCP/UPSR current Aug1/Sts3"
            ::= { new-t1SncpApsEty 6 }

        new-t1SncpCurrVc3Sts1Path  OBJECT-TYPE
            SYNTAX  Vc3Sts1Num
            ACCESS  read-only
            STATUS  mandatory
            DESCRIPTION
                "SNCP/UPSR current Vc3/Sts1"
            ::= { new-t1SncpApsEty 7 }

        new-t1SncpCurrVc1xVtxPath  OBJECT-TYPE
            SYNTAX  Vc1xVtxNum
            ACCESS  read-only
            STATUS  mandatory
            DESCRIPTION
                "SNCP/UPSR current Vc1x/Vtx"
            ::= { new-t1SncpApsEty 8 }

        new-t1SncpPPType  OBJECT-TYPE
            SYNTAX  XcType
            ACCESS  read-only
            STATUS  mandatory
            DESCRIPTION
                "SNCP/UPSR path protection type"
            ::= { new-t1SncpApsEty 9 }

        new-t1SncpCmd  OBJECT-TYPE
            SYNTAX  SncpUserCmd
            ACCESS  read-write
            STATUS  mandatory
            DESCRIPTION
                "SNCP/UPSR APS command"
            ::= { new-t1SncpApsEty 10 }

        new-t1SncpRevertive  OBJECT-TYPE
            SYNTAX  INTEGER {
                    non-revertive(1),
                    revertive(2)
                }
            ACCESS  read-write
            STATUS  mandatory
            DESCRIPTION
                "SNCP/UPSR revertive or non-revertive"
            ::= { new-t1SncpApsEty 11 }

        hdT1TotalCard   OBJECT-TYPE
            SYNTAX  INTEGER
            ACCESS  read-only
            STATUS  mandatory
            DESCRIPTION
                "Total cards of hdT1"
            ::= { hdT1-card 100 }

--2011-3-18 elvis above

--======================================================================--
--======================================================================--
--  ethernet-card MIB
--======================================================================--
--======================================================================--

--
-- enetModeTable
--
        enetModeTable  OBJECT-TYPE
            SYNTAX  SEQUENCE OF EnetModeEntry
            ACCESS  not-accessible
            STATUS  mandatory
            DESCRIPTION
                "display ethernet unit mode"
            ::= { enet-card 1 }

        enetModeEntry  OBJECT-TYPE
            SYNTAX  EnetModeEntry
            ACCESS  not-accessible
            STATUS  mandatory
            DESCRIPTION
                "unit model entry"
            INDEX { enetModeUnitIndex }
            ::= { enetModeTable 1 }

        EnetModeEntry ::= SEQUENCE {
            enetModeUnitIndex           UnitID,
            enetModeSetup               INTEGER
        }

        enetModeUnitIndex  OBJECT-TYPE
            SYNTAX  UnitID
            ACCESS  read-only
            STATUS  mandatory
            DESCRIPTION
            "unit 1 to 4."
            ::= { enetModeEntry 1 }

        enetModeSetup   OBJECT-TYPE
            SYNTAX  INTEGER {
                    e-line-8FE(1),
                    e-line-1GE(2),
                    e-lan-8FE(3),
                    e-lan-1GE(4),
                    portmap-8FE(5),
                    portmap-1GE(6)
                }
            ACCESS  read-write
            STATUS  mandatory
            DESCRIPTION
                " ethernet card mode: e-line/e-lan/port-map"
            ::= { enetModeEntry 2 }

--
-- enetWanVcgSetupTable
--
    enetWanVcgSetupTable        OBJECT IDENTIFIER ::= { enet-card 2 }

        enetWanVcgConfigTable  OBJECT-TYPE
            SYNTAX  SEQUENCE OF EnetWanVcgConfigEntry
            ACCESS  not-accessible
            STATUS  mandatory
            DESCRIPTION
                "display vcg configuration"
            ::= { enetWanVcgSetupTable 1 }

        enetWanVcgConfigEntry  OBJECT-TYPE
            SYNTAX  EnetWanVcgConfigEntry
            ACCESS  not-accessible
            STATUS  mandatory
            DESCRIPTION
                "vcg config entry"
            INDEX { vcgUnitIndex , vcgPortIndex }
            ::= { enetWanVcgConfigTable 1 }

        EnetWanVcgConfigEntry ::= SEQUENCE {
            vcgUnitIndex                UnitID,
            vcgPortIndex                VcgPortNum,
            vcgPayloadType              INTEGER,
            vcgLcas                     INTEGER,
            vcgEncapType                INTEGER
        }

        vcgUnitIndex  OBJECT-TYPE
            SYNTAX  UnitID
            ACCESS  read-only
            STATUS  mandatory
            DESCRIPTION
            "unit 1 to 4."
            ::= { enetWanVcgConfigEntry 1 }

        vcgPortIndex  OBJECT-TYPE
            SYNTAX  VcgPortNum
            ACCESS  read-only
            STATUS  mandatory
            DESCRIPTION
                "vcg port index: wan1~wan9 "
            ::= { enetWanVcgConfigEntry 2 }

        vcgPayloadType  OBJECT-TYPE
            SYNTAX  INTEGER {
                    tu3(1),
                    au3-sts1(2),
                    tu11-vt15(3),
                    tu12-vt2(4),
                    au4-sts3c(5)
                }
            ACCESS  read-write
            STATUS  mandatory
            DESCRIPTION
                "vcg payload type"
            ::= { enetWanVcgConfigEntry 3 }

        vcgLcas  OBJECT-TYPE
            SYNTAX  INTEGER {
                    nonlcas(1),
                    lcas(2)
                }
            ACCESS  read-write
            STATUS  mandatory
            DESCRIPTION
                "vcg lcas state"
            ::= { enetWanVcgConfigEntry 4 }


        vcgEncapType  OBJECT-TYPE
            SYNTAX  INTEGER {
                    gfp(1),
                    laps(2),
--                        ppp(3)
                    bcp(4)
                }
            ACCESS  read-write
            STATUS  mandatory
            DESCRIPTION
                "vcg encapturation type"
            ::= { enetWanVcgConfigEntry 5 }

--
-- enetWanVcgAlmSetupTable
--
        enetWanVcgAlmSetupTable  OBJECT-TYPE
            SYNTAX  SEQUENCE OF EnetWanVcgAlmSetupEntry
            ACCESS  not-accessible
            STATUS  mandatory
            DESCRIPTION
                "vcg member alarm setup table"
            ::= { enetWanVcgSetupTable 2 }

        enetWanVcgAlmSetupEntry  OBJECT-TYPE
            SYNTAX  EnetWanVcgAlmSetupEntry
            ACCESS  not-accessible
            STATUS  mandatory
            DESCRIPTION
                "vcg member alarm setup entry"
            INDEX { vcgAlmSetupUnitIndex , vcgAlmSetupPortIndex ,
                    vcgAlmSetupPathIndex , vcgAlmSetupTypeIndex }
            ::= { enetWanVcgAlmSetupTable 1 }

        EnetWanVcgAlmSetupEntry ::= SEQUENCE {
            vcgAlmSetupUnitIndex        UnitID,
            vcgAlmSetupPortIndex        VcgPortNum,
            vcgAlmSetupPathIndex        INTEGER,
            vcgAlmSetupTypeIndex        INTEGER,
            vcgAlmSetupAlarm            INTEGER,
            vcgAlmSetupRelay            INTEGER,
            vcgAlmSetupSeverity         Severity
        }

        vcgAlmSetupUnitIndex  OBJECT-TYPE
            SYNTAX  UnitID
            ACCESS  read-only
            STATUS  mandatory
            DESCRIPTION
            "unit 1 to 4."
            ::= { enetWanVcgAlmSetupEntry 1 }

        vcgAlmSetupPortIndex  OBJECT-TYPE
            SYNTAX  VcgPortNum
            ACCESS  read-only
            STATUS  mandatory
            DESCRIPTION
                "vcg port index: wan1~wan9 "
            ::= { enetWanVcgAlmSetupEntry 2 }

        vcgAlmSetupPathIndex  OBJECT-TYPE
            SYNTAX  INTEGER {
                    low-order(1),
                    hi-order(2)
                }
            ACCESS  read-only
            STATUS  mandatory
            DESCRIPTION
                "vcg path index: low-order path or hi-order path "
            ::= { enetWanVcgAlmSetupEntry 3 }

        vcgAlmSetupTypeIndex  OBJECT-TYPE
            SYNTAX  INTEGER {
                    lop(1),
                    ais(2),
                    sd(3),
                    sf(4),
                    uneq(5),
                    plm(6),
                    tim(7),
                    rdi-p(8),
                    rdi-s(9),
                    rdi-c(10),
                    rei(11),
                    bip(12)
                }
            ACCESS  read-only
            STATUS  mandatory
            DESCRIPTION
                "path alarm type: tu-lop,tu-ais,.... "
            ::= { enetWanVcgAlmSetupEntry 4 }

        vcgAlmSetupAlarm  OBJECT-TYPE
            SYNTAX  INTEGER {
                    disable(1),
                    enable(2)
                }
            ACCESS  read-write
            STATUS  mandatory
            DESCRIPTION
                "vcg member alarm mask enable/disable"
            ::= { enetWanVcgAlmSetupEntry 5 }

        vcgAlmSetupRelay  OBJECT-TYPE
            SYNTAX  INTEGER {
                    disable(1),
                    enable(2)
                }
            ACCESS  read-write
            STATUS  mandatory
            DESCRIPTION
                "vcg member alarm relay enable/disable"
            ::= { enetWanVcgAlmSetupEntry 6 }

        vcgAlmSetupSeverity  OBJECT-TYPE
            SYNTAX  Severity
            ACCESS  read-write
            STATUS  mandatory
            DESCRIPTION
                "vcg member alarm severity"
            ::= { enetWanVcgAlmSetupEntry 7 }

--
-- enetWanVcgGfpParaTable
--
        enetWanVcgGfpParaTable  OBJECT-TYPE
            SYNTAX  SEQUENCE OF EnetWanVcgGfpParaEntry
            ACCESS  not-accessible
            STATUS  mandatory
            DESCRIPTION
                "vcg gfp parameter configuration"
            ::= { enetWanVcgSetupTable 3 }

        enetWanVcgGfpParaEntry  OBJECT-TYPE
            SYNTAX  EnetWanVcgGfpParaEntry
            ACCESS  not-accessible
            STATUS  mandatory
            DESCRIPTION
                "vcg gfp parameter configuration entry"
            INDEX { vcgGfpUnitIndex , vcgGfpPortIndex }
            ::= { enetWanVcgGfpParaTable 1 }

        EnetWanVcgGfpParaEntry ::= SEQUENCE {
            vcgGfpUnitIndex             UnitID,
            vcgGfpPortIndex             VcgPortNum,
            vcgGfpRxPti                 INTEGER,
            vcgGfpTxPti                 INTEGER,
            vcgGfpRxExi                 INTEGER,
            vcgGfpTxExi                 INTEGER,
            vcgGfpRxUpi                 INTEGER,
            vcgGfpTxUpi                 INTEGER,
            vcgGfpDelta                 INTEGER,
            vcgGfpTxPfi                 INTEGER,
            vcgGfpRxDescramble          INTEGER,
            vcgGfpTxScramble            INTEGER,
            vcgGfpRxPayloadFcsCheck     INTEGER,
            vcgGfpTxPayloadFcsInsert    INTEGER,
            vcgGfpRxPtiCheck            INTEGER,
            vcgGfpRxUpiCheck            INTEGER,
            vcgGfpTxRxFcsMode           INTEGER

    }

        vcgGfpUnitIndex  OBJECT-TYPE
            SYNTAX  UnitID
            ACCESS  read-only
            STATUS  mandatory
            DESCRIPTION
            "unit 1 to 4."
            ::= { enetWanVcgGfpParaEntry 1 }

        vcgGfpPortIndex  OBJECT-TYPE
            SYNTAX  VcgPortNum
            ACCESS  read-only
            STATUS  mandatory
            DESCRIPTION
                "vcg port index: wan1~wan9 "
            ::= { enetWanVcgGfpParaEntry 2 }

        vcgGfpRxPti  OBJECT-TYPE
            SYNTAX  INTEGER (0..7)
            ACCESS  read-write
            STATUS  mandatory
            DESCRIPTION
                "vcg Gfp Rx PTI"
            ::= { enetWanVcgGfpParaEntry 3 }

        vcgGfpTxPti  OBJECT-TYPE
            SYNTAX  INTEGER (0..7)
            ACCESS  read-write
            STATUS  mandatory
            DESCRIPTION
                "vcg Gfp Tx PTI"
            ::= { enetWanVcgGfpParaEntry 4 }

        vcgGfpRxExi  OBJECT-TYPE
            SYNTAX  INTEGER (0..15)
            ACCESS  read-write
            STATUS  mandatory
            DESCRIPTION
                "vcg Gfp Rx EXI"
            ::= { enetWanVcgGfpParaEntry 5 }

        vcgGfpTxExi  OBJECT-TYPE
            SYNTAX  INTEGER (0..15)
            ACCESS  read-write
            STATUS  mandatory
            DESCRIPTION
                "vcg Gfp Tx EXI"
            ::= { enetWanVcgGfpParaEntry 6 }

        vcgGfpRxUpi  OBJECT-TYPE
            SYNTAX  INTEGER (0..255)
            ACCESS  read-write
            STATUS  mandatory
            DESCRIPTION
                "vcg Gfp Rx UPI"
            ::= { enetWanVcgGfpParaEntry 7 }

        vcgGfpTxUpi  OBJECT-TYPE
            SYNTAX  INTEGER (0..255)
            ACCESS  read-write
            STATUS  mandatory
            DESCRIPTION
                "vcg Gfp Tx UPI"
            ::= { enetWanVcgGfpParaEntry 8 }

        vcgGfpDelta  OBJECT-TYPE
            SYNTAX  INTEGER (1..4)
            ACCESS  read-write
            STATUS  mandatory
            DESCRIPTION
                "vcg Gfp DELTA"
            ::= { enetWanVcgGfpParaEntry 9 }

        vcgGfpTxPfi  OBJECT-TYPE
            SYNTAX  INTEGER (0..1)
            ACCESS  read-write
            STATUS  mandatory
            DESCRIPTION
                "vcg Gfp Tx PFI"
            ::= { enetWanVcgGfpParaEntry 10 }

        vcgGfpRxDescramble  OBJECT-TYPE
            SYNTAX  INTEGER {
                    disable(1),
                    enable(2)
                }
            ACCESS  read-write
            STATUS  mandatory
            DESCRIPTION
                "vcg Gfp Rx Descramble"
            ::= { enetWanVcgGfpParaEntry 11 }

        vcgGfpTxScramble  OBJECT-TYPE
            SYNTAX  INTEGER {
                    disable(1),
                    enable(2)
                }
            ACCESS  read-write
            STATUS  mandatory
            DESCRIPTION
                "vcg Gfp Tx Scramble"
            ::= { enetWanVcgGfpParaEntry 12 }

        vcgGfpRxPayloadFcsCheck  OBJECT-TYPE
            SYNTAX  INTEGER {
                    disable(1),
                    enable(2)
                }
            ACCESS  read-write
            STATUS  mandatory
            DESCRIPTION
                "vcg Gfp Rx Payload FCS Check"
            ::= { enetWanVcgGfpParaEntry 13 }

        vcgGfpTxPayloadFcsInsert  OBJECT-TYPE
            SYNTAX  INTEGER {
                    disable(1),
                    enable(2)
                }
            ACCESS  read-write
            STATUS  mandatory
            DESCRIPTION
                "vcg Gfp Tx Payload FCS Insert"
            ::= { enetWanVcgGfpParaEntry 14 }

        vcgGfpRxPtiCheck  OBJECT-TYPE
            SYNTAX  INTEGER {
                    disable(1),
                    enable(2)
                }
            ACCESS  read-write
            STATUS  mandatory
            DESCRIPTION
                "vcg Gfp Rx PTI Check"
            ::= { enetWanVcgGfpParaEntry 15 }

        vcgGfpRxUpiCheck  OBJECT-TYPE
            SYNTAX  INTEGER {
                    disable(1),
                    enable(2)
                }
            ACCESS  read-write
            STATUS  mandatory
            DESCRIPTION
                "vcg Gfp Rx UPI Check"
            ::= { enetWanVcgGfpParaEntry 16 }

        vcgGfpTxRxFcsMode  OBJECT-TYPE
            SYNTAX  INTEGER {
                    crc-32(1),
                    crc-16(2)
                }
            ACCESS  read-write
            STATUS  mandatory
            DESCRIPTION
                "vcg Gfp Tx/Rx Payload FCS mode"
            ::= { enetWanVcgGfpParaEntry 17 }

--
-- enetWanVcgLapsParaTable
--
        enetWanVcgLapsParaTable  OBJECT-TYPE
            SYNTAX  SEQUENCE OF EnetWanVcgLapsParaEntry
            ACCESS  not-accessible
            STATUS  mandatory
            DESCRIPTION
                "vcg Laps parameter configuration"
            ::= { enetWanVcgSetupTable 4 }

        enetWanVcgLapsParaEntry  OBJECT-TYPE
            SYNTAX  EnetWanVcgLapsParaEntry
            ACCESS  not-accessible
            STATUS  mandatory
            DESCRIPTION
                "vcg Laps parameter configuration entry"
            INDEX { vcgLapsUnitIndex , vcgLapsPortIndex }
            ::= { enetWanVcgLapsParaTable 1 }

        EnetWanVcgLapsParaEntry ::= SEQUENCE {
            vcgLapsUnitIndex            UnitID,
            vcgLapsPortIndex            VcgPortNum,
            vcgLapsRxAddress            INTEGER,
            vcgLapsTxAddress            INTEGER,
            vcgLapsRxControl            INTEGER,
            vcgLapsTxControl            INTEGER,
            vcgLapsRxSapiMsb            INTEGER,
            vcgLapsTxSapiMsb            INTEGER,
            vcgLapsRxSapiLsb            INTEGER,
            vcgLapsTxSapiLsb            INTEGER,
            vcgLapsRxDescramble         INTEGER,
            vcgLapsTxScramble           INTEGER,
            vcgLapsRxPayloadFcsCheck    INTEGER,
            vcgLapsTxPayloadFcsIns      INTEGER,
            vcgLapsRxAddressCheck       INTEGER,
            vcgLapsRxControlCheck       INTEGER,
            vcgLapsRxSapiCheck          INTEGER,
            vcgLapsTxRxFcsMode          INTEGER
        }

        vcgLapsUnitIndex  OBJECT-TYPE
            SYNTAX  UnitID
            ACCESS  read-only
            STATUS  mandatory
            DESCRIPTION
            "unit 1 to 4."
            ::= { enetWanVcgLapsParaEntry 1 }

        vcgLapsPortIndex  OBJECT-TYPE
            SYNTAX  VcgPortNum
            ACCESS  read-only
            STATUS  mandatory
            DESCRIPTION
                "vcg port index: wan1~wan9 "
            ::= { enetWanVcgLapsParaEntry 2 }

        vcgLapsRxAddress  OBJECT-TYPE
            SYNTAX  INTEGER (0..255)
            ACCESS  read-write
            STATUS  mandatory
            DESCRIPTION
                "vcg Laps Rx Address"
            ::= { enetWanVcgLapsParaEntry 3 }

        vcgLapsTxAddress  OBJECT-TYPE
            SYNTAX  INTEGER (0..255)
            ACCESS  read-write
            STATUS  mandatory
            DESCRIPTION
                "vcg Laps Tx Address"
            ::= { enetWanVcgLapsParaEntry 4 }

        vcgLapsRxControl  OBJECT-TYPE
            SYNTAX  INTEGER (0..255)
            ACCESS  read-write
            STATUS  mandatory
            DESCRIPTION
                "vcg Laps Rx Control"
            ::= { enetWanVcgLapsParaEntry 5 }

        vcgLapsTxControl  OBJECT-TYPE
            SYNTAX  INTEGER (0..255)
            ACCESS  read-write
            STATUS  mandatory
            DESCRIPTION
                "vcg Laps Tx Control"
            ::= { enetWanVcgLapsParaEntry 6 }

        vcgLapsRxSapiMsb  OBJECT-TYPE
            SYNTAX  INTEGER (0..255)
            ACCESS  read-write
            STATUS  mandatory
            DESCRIPTION
                "vcg Laps Rx SAPI MSB"
            ::= { enetWanVcgLapsParaEntry 7 }

        vcgLapsTxSapiMsb  OBJECT-TYPE
            SYNTAX  INTEGER (0..255)
            ACCESS  read-write
            STATUS  mandatory
            DESCRIPTION
                "vcg Laps Tx SAPI MSB"
            ::= { enetWanVcgLapsParaEntry 8 }

        vcgLapsRxSapiLsb  OBJECT-TYPE
            SYNTAX  INTEGER (0..255)
            ACCESS  read-write
            STATUS  mandatory
            DESCRIPTION
                "vcg Laps Rx SAPI LSB"
            ::= { enetWanVcgLapsParaEntry 9 }

        vcgLapsTxSapiLsb  OBJECT-TYPE
            SYNTAX  INTEGER (0..255)
            ACCESS  read-write
            STATUS  mandatory
            DESCRIPTION
                "vcg Laps Tx SAPI LSB"
            ::= { enetWanVcgLapsParaEntry 10 }

        vcgLapsRxDescramble  OBJECT-TYPE
            SYNTAX  INTEGER {
                    disable(1),
                    enable(2)
                }
            ACCESS  read-write
            STATUS  mandatory
            DESCRIPTION
                "vcg Laps Rx Descramble"
            ::= { enetWanVcgLapsParaEntry 11 }

        vcgLapsTxScramble  OBJECT-TYPE
            SYNTAX  INTEGER {
                    disable(1),
                    enable(2)
                }
            ACCESS  read-write
            STATUS  mandatory
            DESCRIPTION
                "vcg Laps Tx Scramble"
            ::= { enetWanVcgLapsParaEntry 12 }

        vcgLapsRxPayloadFcsCheck  OBJECT-TYPE
            SYNTAX  INTEGER {
                    disable(1),
                    enable(2)
                }
            ACCESS  read-write
            STATUS  mandatory
            DESCRIPTION
                "vcg Laps Rx Payload FCS Check"
            ::= { enetWanVcgLapsParaEntry 13 }

        vcgLapsTxPayloadFcsIns  OBJECT-TYPE
            SYNTAX  INTEGER {
                    disable(1),
                    enable(2)
                }
            ACCESS  read-write
            STATUS  mandatory
            DESCRIPTION
                "vcg Laps Tx Payload FCS Insert"
            ::= { enetWanVcgLapsParaEntry 14 }

        vcgLapsRxAddressCheck  OBJECT-TYPE
            SYNTAX  INTEGER {
                    disable(1),
                    enable(2)
                }
            ACCESS  read-write
            STATUS  mandatory
            DESCRIPTION
                "vcg Laps Rx Address Check"
            ::= { enetWanVcgLapsParaEntry 15 }

        vcgLapsRxControlCheck  OBJECT-TYPE
            SYNTAX  INTEGER {
                    disable(1),
                    enable(2)
                }
            ACCESS  read-write
            STATUS  mandatory
            DESCRIPTION
                "vcg Laps Rx Control Check"
            ::= { enetWanVcgLapsParaEntry 16 }

        vcgLapsRxSapiCheck  OBJECT-TYPE
            SYNTAX  INTEGER {
                    disable(1),
                    enable(2)
                }
            ACCESS  read-write
            STATUS  mandatory
            DESCRIPTION
                "vcg Laps Rx SAPI Check"
            ::= { enetWanVcgLapsParaEntry 17 }

        vcgLapsTxRxFcsMode  OBJECT-TYPE
            SYNTAX  INTEGER {
                    crc-32(1),
                    crc-16(2)
                }
            ACCESS  read-write
            STATUS  mandatory
            DESCRIPTION
                "vcg Laps Tx/Rx Payload FCS Mode"
            ::= { enetWanVcgLapsParaEntry 18 }


--
--   enetWanVcgTcaTable
--
        enetWanVcgTcaTable  OBJECT-TYPE
            SYNTAX  SEQUENCE OF EnetWanVcgTcaEntry
            ACCESS  not-accessible
            STATUS  mandatory
            DESCRIPTION
                "vcg threshold cross alarm entry table"
            ::= { enetWanVcgSetupTable 5 }

        enetWanVcgTcaEntry  OBJECT-TYPE
            SYNTAX  EnetWanVcgTcaEntry
            ACCESS  not-accessible
            STATUS  mandatory
            DESCRIPTION
                "vcg threshold cross alarm entry"
            INDEX { vcgTcaUnitIndex , vcgTcaTypeIndex }
            ::= { enetWanVcgTcaTable 1 }

        EnetWanVcgTcaEntry ::= SEQUENCE {
            vcgTcaUnitIndex             UnitID,
            vcgTcaTypeIndex             INTEGER,
            vcgTcaAlmMask               INTEGER,
            vcgTcaSeverity              Severity,
            vcgTcaThreshold             INTEGER
        }

        vcgTcaUnitIndex  OBJECT-TYPE
            SYNTAX  UnitID
            ACCESS  read-only
            STATUS  mandatory
            DESCRIPTION
            "unit 1 to 4."
            ::= { enetWanVcgTcaEntry 1 }

        vcgTcaTypeIndex  OBJECT-TYPE
            SYNTAX  INTEGER {
                    errored-fcs-count(1),
                    fifo-overflow-frame-count(2),
                    dropped-frame-count(3)
                }
            ACCESS  read-only
            STATUS  mandatory
            DESCRIPTION
                "vcg tca type index"
            ::= { enetWanVcgTcaEntry 2 }

        vcgTcaAlmMask  OBJECT-TYPE
            SYNTAX  INTEGER {
                    disable(1),
                    enable(2)
                }
            ACCESS  read-write
            STATUS  mandatory
            DESCRIPTION
                "vcg tca alarm mask enable/disable"
            ::= { enetWanVcgTcaEntry 3 }

        vcgTcaSeverity  OBJECT-TYPE
            SYNTAX  Severity
            ACCESS  read-write
            STATUS  mandatory
            DESCRIPTION
                "vcg tca alarm severity"
            ::= { enetWanVcgTcaEntry 4 }

        vcgTcaThreshold  OBJECT-TYPE
            SYNTAX  INTEGER
            ACCESS  read-write
            STATUS  mandatory
            DESCRIPTION
                "vcg tca threshold"
            ::= { enetWanVcgTcaEntry 5 }

--
-- enetWanVcgPppParaTable
--
--         enetWanVcgPppParaTable  OBJECT-TYPE
--             SYNTAX  SEQUENCE OF EnetWanVcgPppParaEntry
--             ACCESS  not-accessible
--             STATUS  mandatory
--             DESCRIPTION
--                "vcg PPP parameter configuration"
--             ::= { enetWanVcgSetupTable 6 }
--
--         enetWanVcgPppParaEntry  OBJECT-TYPE
--             SYNTAX  EnetWanVcgPppParaEntry
--             ACCESS  not-accessible
--             STATUS  mandatory
--             DESCRIPTION
--                "vcg PPP parameter configuration entry"
--             INDEX  { vcgPppUnitIndex, vcgPppPortIndex }
--             ::= { enetWanVcgPppParaTable 1 }
--
--         EnetWanVcgPppParaEntry ::=
--             SEQUENCE {
--               vcgPppUnitIndex
--                 UnitID,
--               vcgPppPortIndex
--                 VcgPortNum,
--               vcgPppRxAddress
--                 INTEGER,
--               vcgPppTxAddress
--                 INTEGER,
--               vcgPppRxControl
--                 INTEGER,
--               vcgPppTxControl
--                 INTEGER,
--               vcgPppRxProtocolMsb
--                 INTEGER,
--               vcgPppTxProtocolMsb
--                 INTEGER,
--               vcgPppRxProtocolLsb
--                 INTEGER,
--               vcgPppTxProtocolLsb
--                 INTEGER,
--               vcgPppRxDescramble
--                 INTEGER,
--               vcgPppTxScramble
--                 INTEGER,
--               vcgPppRxPayloadFcsCheck
--                 INTEGER,
--               vcgPppTxPayloadFcsIns
--                 INTEGER,
--               vcgPppRxAddressCheck
--                 INTEGER,
--               vcgPppRxControlCheck
--                 INTEGER,
--               vcgPppRxProtocolCheck
--                 INTEGER,
--               vcgPppTxRxFcsMode
--                 INTEGER
--             }
--
--         vcgPppUnitIndex  OBJECT-TYPE
--             SYNTAX  UnitID
--             ACCESS  read-only
--             STATUS  mandatory
--             DESCRIPTION
--                "unit 1 to 4."
--             ::= { enetWanVcgPppParaEntry 1 }
--
--         vcgPppPortIndex  OBJECT-TYPE
--             SYNTAX  VcgPortNum
--             ACCESS  read-only
--             STATUS  mandatory
--             DESCRIPTION
--                "vcg port index: wan1~wan9 "
--             ::= { enetWanVcgPppParaEntry 2 }
--
--         vcgPppRxAddress  OBJECT-TYPE
--             SYNTAX  INTEGER (0..255)
--             ACCESS  read-write
--             STATUS  mandatory
--             DESCRIPTION
--                "vcg PPP Rx Address"
--             ::= { enetWanVcgPppParaEntry 3 }
--
--         vcgPppTxAddress  OBJECT-TYPE
--             SYNTAX  INTEGER (0..255)
--             ACCESS  read-write
--             STATUS  mandatory
--             DESCRIPTION
--                "vcg PPP Tx Address"
--             ::= { enetWanVcgPppParaEntry 4 }
--
--         vcgPppRxControl  OBJECT-TYPE
--             SYNTAX  INTEGER (0..255)
--             ACCESS  read-write
--             STATUS  mandatory
--             DESCRIPTION
--                "vcg PPP Rx Control"
--             ::= { enetWanVcgPppParaEntry 5 }
--
--         vcgPppTxControl  OBJECT-TYPE
--             SYNTAX  INTEGER (0..255)
--             ACCESS  read-write
--             STATUS  mandatory
--             DESCRIPTION
--                "vcg PPP Tx Control"
--             ::= { enetWanVcgPppParaEntry 6 }
--
--         vcgPppRxProtocolMsb  OBJECT-TYPE
--             SYNTAX  INTEGER (0..255)
--             ACCESS  read-write
--             STATUS  mandatory
--             DESCRIPTION
--                "vcg PPP Rx Protocol MSB"
--             ::= { enetWanVcgPppParaEntry 7 }
--
--         vcgPppTxProtocolMsb  OBJECT-TYPE
--             SYNTAX  INTEGER (0..255)
--             ACCESS  read-write
--             STATUS  mandatory
--             DESCRIPTION
--                "vcg PPP Tx Protocol MSB"
--             ::= { enetWanVcgPppParaEntry 8 }
--
--         vcgPppRxProtocolLsb  OBJECT-TYPE
--             SYNTAX  INTEGER (0..255)
--             ACCESS  read-write
--             STATUS  mandatory
--             DESCRIPTION
--                "vcg PPP Rx Protocol LSB"
--             ::= { enetWanVcgPppParaEntry 9 }
--
--         vcgPppTxProtocolLsb  OBJECT-TYPE
--             SYNTAX  INTEGER (0..255)
--             ACCESS  read-write
--             STATUS  mandatory
--             DESCRIPTION
--                "vcg PPP Tx Protocol LSB"
--             ::= { enetWanVcgPppParaEntry 10 }
--
--         vcgPppRxDescramble  OBJECT-TYPE
--             SYNTAX  INTEGER {
--                        disable(1),
--                        enable(2)
--                     }
--             ACCESS  read-write
--             STATUS  mandatory
--             DESCRIPTION
--                "vcg PPP Rx Descramble"
--             ::= { enetWanVcgPppParaEntry 11 }
--
--         vcgPppTxScramble  OBJECT-TYPE
--             SYNTAX  INTEGER {
--                        disable(1),
--                        enable(2)
--                     }
--             ACCESS  read-write
--             STATUS  mandatory
--             DESCRIPTION
--                "vcg PPP Tx Scramble"
--             ::= { enetWanVcgPppParaEntry 12 }
--
--         vcgPppRxPayloadFcsCheck  OBJECT-TYPE
--             SYNTAX  INTEGER {
--                        disable(1),
--                        enable(2)
--                     }
--             ACCESS  read-write
--             STATUS  mandatory
--             DESCRIPTION
--                "vcg PPP Rx Payload FCS Check"
--             ::= { enetWanVcgPppParaEntry 13 }
--
--         vcgPppTxPayloadFcsIns  OBJECT-TYPE
--             SYNTAX  INTEGER {
--                        disable(1),
--                        enable(2)
--                     }
--             ACCESS  read-write
--             STATUS  mandatory
--             DESCRIPTION
--                "vcg PPP Tx Payload FCS Insert"
--             ::= { enetWanVcgPppParaEntry 14 }
--
--         vcgPppRxAddressCheck  OBJECT-TYPE
--             SYNTAX  INTEGER {
--                        disable(1),
--                        enable(2)
--                     }
--             ACCESS  read-write
--             STATUS  mandatory
--             DESCRIPTION
--                "vcg PPP Rx Address Check"
--             ::= { enetWanVcgPppParaEntry 15 }
--
--         vcgPppRxControlCheck  OBJECT-TYPE
--             SYNTAX  INTEGER {
--                        disable(1),
--                        enable(2)
--                     }
--             ACCESS  read-write
--             STATUS  mandatory
--             DESCRIPTION
--                "vcg PPP Rx Control Check"
--             ::= { enetWanVcgPppParaEntry 16 }
--
--         vcgPppRxProtocolCheck  OBJECT-TYPE
--             SYNTAX  INTEGER {
--                        disable(1),
--                        enable(2)
--                     }
--             ACCESS  read-write
--             STATUS  mandatory
--             DESCRIPTION
--                "vcg PPP Rx Protocol Check"
--             ::= { enetWanVcgPppParaEntry 17 }
--
--         vcgPppTxRxFcsMode  OBJECT-TYPE
--             SYNTAX  INTEGER {
--                        crc-32(1),
--                        crc-16(2)
--                     }
--             ACCESS  read-write
--             STATUS  mandatory
--             DESCRIPTION
--                "vcg PPP Tx/Rx Payload FCS Mode"
--             ::= { enetWanVcgPppParaEntry 18 }

--
-- enetWanVcgBcpParaTable
--
        enetWanVcgBcpParaTable  OBJECT-TYPE
            SYNTAX  SEQUENCE OF EnetWanVcgBcpParaEntry
            ACCESS  not-accessible
            STATUS  mandatory
            DESCRIPTION
                "vcg Bcp parameter configuration"
            ::= { enetWanVcgSetupTable 7 }

        enetWanVcgBcpParaEntry  OBJECT-TYPE
            SYNTAX  EnetWanVcgBcpParaEntry
            ACCESS  not-accessible
            STATUS  mandatory
            DESCRIPTION
                "vcg Bcp parameter configuration entry"
            INDEX { vcgBcpUnitIndex , vcgBcpPortIndex }
            ::= { enetWanVcgBcpParaTable 1 }

        EnetWanVcgBcpParaEntry ::= SEQUENCE {
            vcgBcpUnitIndex             UnitID,
            vcgBcpPortIndex             VcgPortNum,
            vcgBcpRxAddress             INTEGER,
            vcgBcpTxAddress             INTEGER,
            vcgBcpRxControl             INTEGER,
            vcgBcpTxControl             INTEGER,
            vcgBcpRxProtocolMsb         INTEGER,
            vcgBcpTxProtocolMsb         INTEGER,
            vcgBcpRxProtocolLsb         INTEGER,
            vcgBcpTxProtocolLsb         INTEGER,
            vcgBcpRxDescramble          INTEGER,
            vcgBcpTxScramble            INTEGER,
            vcgBcpRxPayloadFcsCheck     INTEGER,
            vcgBcpTxPayloadFcsIns       INTEGER,
            vcgBcpRxAddressCheck        INTEGER,
            vcgBcpRxControlCheck        INTEGER,
            vcgBcpRxProtocolCheck       INTEGER,
            vcgBcpTxRxFcsMode           INTEGER,
            vcgBcpRxBitF                INTEGER,
            vcgBcpTxBitF                INTEGER,
            vcgBcpRxBitZ                INTEGER,
            vcgBcpTxBitZ                INTEGER,
            vcgBcpRxPads                INTEGER,
            vcgBcpTxPads                INTEGER,
            vcgBcpRxMacType             INTEGER,
            vcgBcpTxMacType             INTEGER,
            vcgBcpRxBcpFlagCheck        INTEGER,
            vcgBcpRxMacTypeCheck        INTEGER
        }

        vcgBcpUnitIndex  OBJECT-TYPE
            SYNTAX  UnitID
            ACCESS  read-only
            STATUS  mandatory
            DESCRIPTION
            "unit 1 to 4."
            ::= { enetWanVcgBcpParaEntry 1 }

        vcgBcpPortIndex  OBJECT-TYPE
            SYNTAX  VcgPortNum
            ACCESS  read-only
            STATUS  mandatory
            DESCRIPTION
                "vcg port index: wan1~wan9 "
            ::= { enetWanVcgBcpParaEntry 2 }

        vcgBcpRxAddress  OBJECT-TYPE
            SYNTAX  INTEGER (0..255)
            ACCESS  read-write
            STATUS  mandatory
            DESCRIPTION
                "vcg Bcp Rx Address"
            ::= { enetWanVcgBcpParaEntry 3 }

        vcgBcpTxAddress  OBJECT-TYPE
            SYNTAX  INTEGER (0..255)
            ACCESS  read-write
            STATUS  mandatory
            DESCRIPTION
                "vcg Bcp Tx Address"
            ::= { enetWanVcgBcpParaEntry 4 }

        vcgBcpRxControl  OBJECT-TYPE
            SYNTAX  INTEGER (0..255)
            ACCESS  read-write
            STATUS  mandatory
            DESCRIPTION
                "vcg Bcp Rx Control"
            ::= { enetWanVcgBcpParaEntry 5 }

        vcgBcpTxControl  OBJECT-TYPE
            SYNTAX  INTEGER (0..255)
            ACCESS  read-write
            STATUS  mandatory
            DESCRIPTION
                "vcg Bcp Tx Control"
            ::= { enetWanVcgBcpParaEntry 6 }

        vcgBcpRxProtocolMsb  OBJECT-TYPE
            SYNTAX  INTEGER (0..255)
            ACCESS  read-write
            STATUS  mandatory
            DESCRIPTION
                "vcg Bcp Rx Protocol MSB"
            ::= { enetWanVcgBcpParaEntry 7 }

        vcgBcpTxProtocolMsb  OBJECT-TYPE
            SYNTAX  INTEGER (0..255)
            ACCESS  read-write
            STATUS  mandatory
            DESCRIPTION
                "vcg Bcp Tx Protocol MSB"
            ::= { enetWanVcgBcpParaEntry 8 }

        vcgBcpRxProtocolLsb  OBJECT-TYPE
            SYNTAX  INTEGER (0..255)
            ACCESS  read-write
            STATUS  mandatory
            DESCRIPTION
                "vcg Bcp Rx Protocol LSB"
            ::= { enetWanVcgBcpParaEntry 9 }

        vcgBcpTxProtocolLsb  OBJECT-TYPE
            SYNTAX  INTEGER (0..255)
            ACCESS  read-write
            STATUS  mandatory
            DESCRIPTION
                "vcg Bcp Tx Protocol LSB"
            ::= { enetWanVcgBcpParaEntry 10 }

        vcgBcpRxDescramble  OBJECT-TYPE
            SYNTAX  INTEGER {
                    disable(1),
                    enable(2)
                }
            ACCESS  read-write
            STATUS  mandatory
            DESCRIPTION
                "vcg Bcp Rx Descramble"
            ::= { enetWanVcgBcpParaEntry 11 }

        vcgBcpTxScramble  OBJECT-TYPE
            SYNTAX  INTEGER {
                    disable(1),
                    enable(2)
                }
            ACCESS  read-write
            STATUS  mandatory
            DESCRIPTION
                "vcg Bcp Tx Scramble"
            ::= { enetWanVcgBcpParaEntry 12 }

        vcgBcpRxPayloadFcsCheck  OBJECT-TYPE
            SYNTAX  INTEGER {
                    disable(1),
                    enable(2)
                }
            ACCESS  read-write
            STATUS  mandatory
            DESCRIPTION
                "vcg Bcp Rx Payload FCS Check"
            ::= { enetWanVcgBcpParaEntry 13 }

        vcgBcpTxPayloadFcsIns  OBJECT-TYPE
            SYNTAX  INTEGER {
                    disable(1),
                    enable(2)
                }
            ACCESS  read-write
            STATUS  mandatory
            DESCRIPTION
                "vcg Bcp Tx Payload FCS Insert"
            ::= { enetWanVcgBcpParaEntry 14 }

        vcgBcpRxAddressCheck  OBJECT-TYPE
            SYNTAX  INTEGER {
                    disable(1),
                    enable(2)
                }
            ACCESS  read-write
            STATUS  mandatory
            DESCRIPTION
                "vcg Bcp Rx Address Check"
            ::= { enetWanVcgBcpParaEntry 15 }

        vcgBcpRxControlCheck  OBJECT-TYPE
            SYNTAX  INTEGER {
                    disable(1),
                    enable(2)
                }
            ACCESS  read-write
            STATUS  mandatory
            DESCRIPTION
                "vcg Bcp Rx Control Check"
            ::= { enetWanVcgBcpParaEntry 16 }

        vcgBcpRxProtocolCheck  OBJECT-TYPE
            SYNTAX  INTEGER {
                    disable(1),
                    enable(2)
                }
            ACCESS  read-write
            STATUS  mandatory
            DESCRIPTION
                "vcg Bcp Rx Protocol Check"
            ::= { enetWanVcgBcpParaEntry 17 }

        vcgBcpTxRxFcsMode  OBJECT-TYPE
            SYNTAX  INTEGER {
                    crc-32(1),
                    crc-16(2)
                }
            ACCESS  read-write
            STATUS  mandatory
            DESCRIPTION
                "vcg Bcp Tx/Rx Payload FCS Mode"
            ::= { enetWanVcgBcpParaEntry 18 }

        vcgBcpRxBitF  OBJECT-TYPE
            SYNTAX  INTEGER {
                    bit-0(1),
                    bit-1(2)
                }
            ACCESS  read-write
            STATUS  mandatory
            DESCRIPTION
                "vcg Bcp Rx Bit F"
            ::= { enetWanVcgBcpParaEntry 19 }

        vcgBcpTxBitF  OBJECT-TYPE
            SYNTAX  INTEGER {
                    bit-0(1),
                    bit-1(2)
                }
            ACCESS  read-write
            STATUS  mandatory
            DESCRIPTION
                "vcg Bcp Tx Bit F"
            ::= { enetWanVcgBcpParaEntry 20 }

        vcgBcpRxBitZ  OBJECT-TYPE
            SYNTAX  INTEGER {
                    bit-0(1),
                    bit-1(2)
                }
            ACCESS  read-write
            STATUS  mandatory
            DESCRIPTION
                "vcg Bcp Rx Bit Z"
            ::= { enetWanVcgBcpParaEntry 21 }

        vcgBcpTxBitZ  OBJECT-TYPE
            SYNTAX  INTEGER {
                    bit-0(1),
                    bit-1(2)
                }
            ACCESS  read-write
            STATUS  mandatory
            DESCRIPTION
                "vcg Bcp Tx Bit Z"
            ::= { enetWanVcgBcpParaEntry 22 }

        vcgBcpRxPads  OBJECT-TYPE
            SYNTAX  INTEGER (0..15)
            ACCESS  read-write
            STATUS  mandatory
            DESCRIPTION
                "vcg Bcp Rx Pads"
            ::= { enetWanVcgBcpParaEntry 23 }

        vcgBcpTxPads  OBJECT-TYPE
            SYNTAX  INTEGER (0..15)
            ACCESS  read-write
            STATUS  mandatory
            DESCRIPTION
                "vcg Bcp Tx Pads"
            ::= { enetWanVcgBcpParaEntry 24 }

        vcgBcpRxMacType  OBJECT-TYPE
            SYNTAX  INTEGER (0..255)
            ACCESS  read-write
            STATUS  mandatory
            DESCRIPTION
                "vcg Bcp Rx MAC Type"
            ::= { enetWanVcgBcpParaEntry 25 }

        vcgBcpTxMacType  OBJECT-TYPE
            SYNTAX  INTEGER (0..255)
            ACCESS  read-write
            STATUS  mandatory
            DESCRIPTION
                "vcg Bcp Tx MAC Type"
            ::= { enetWanVcgBcpParaEntry 26 }

        vcgBcpRxBcpFlagCheck  OBJECT-TYPE
            SYNTAX  INTEGER {
                    disable(1),
                    enable(2)
                }
            ACCESS  read-write
            STATUS  mandatory
            DESCRIPTION
                "vcg Bcp Rx BCP Flag Check"
            ::= { enetWanVcgBcpParaEntry 27 }

        vcgBcpRxMacTypeCheck  OBJECT-TYPE
            SYNTAX  INTEGER {
                    disable(1),
                    enable(2)
                }
            ACCESS  read-write
            STATUS  mandatory
            DESCRIPTION
                "vcg Bcp Rx MAC Type Check"
            ::= { enetWanVcgBcpParaEntry 28 }

--
-- enetWanVcgPayloadTable
--
        enetWanVcgPayloadTable  OBJECT-TYPE
            SYNTAX  SEQUENCE OF EnetWanVcgPayloadEntry
            ACCESS  not-accessible
            STATUS  mandatory
            DESCRIPTION
                "Card SDH/SONET mode configuration"
            ::= { enetWanVcgSetupTable 8 }

        enetWanVcgPayloadEntry  OBJECT-TYPE
            SYNTAX  EnetWanVcgPayloadEntry
            ACCESS  not-accessible
            STATUS  mandatory
            DESCRIPTION
                "unit payload mode entry"
            INDEX { unitIndex }
            ::= { enetWanVcgPayloadTable 1 }

        EnetWanVcgPayloadEntry ::= SEQUENCE {
            unitIndex                   UnitID,
            unitPayloadMode             INTEGER
        }

        unitIndex  OBJECT-TYPE
            SYNTAX  UnitID
            ACCESS  read-only
            STATUS  mandatory
            DESCRIPTION
            "unit 1 to 4."
            ::= { enetWanVcgPayloadEntry 1 }

        unitPayloadMode  OBJECT-TYPE
            SYNTAX  INTEGER {
                    mode-1(1),
                    mode-2(2)
                }
            ACCESS  read-write
            STATUS  mandatory
            DESCRIPTION
                " In SDH, Mode 1 supports AU4/C4, AU3/C3, TU3, and TU12. Mode 2 supports AU4/C4, AU3/C3, and TU11. In SONET, Mode 1 supports STS3C, STS1, and VT2. Mode 2 supports STS3C, STS1, and VT1.5"
            ::= { enetWanVcgPayloadEntry 2 }

--
--  enetLinkSetupTable
--
    enetLinkSetupTable       OBJECT IDENTIFIER ::= { enet-card 3 }

--
--  enetLinkdownAlmSetupTab
--
        enetLinkdownAlmSetupTab  OBJECT-TYPE
            SYNTAX  SEQUENCE OF  EnetLinkdownAlmSetupEty
            ACCESS  not-accessible
            STATUS  mandatory
            DESCRIPTION
                "The Ethernet Linkdown Alarm Setup Table."
            ::= { enetLinkSetupTable 1 }

        enetLinkdownAlmSetupEty  OBJECT-TYPE
            SYNTAX  EnetLinkdownAlmSetupEty
            ACCESS  not-accessible
            STATUS  mandatory
            DESCRIPTION
                "An entry in The Ethernet Linkdown Alarm Setup Table."
            INDEX { enLinkdownAlmSetupUnit , enLinkdownAlmSetupPort }
            ::= { enetLinkdownAlmSetupTab 1 }

        EnetLinkdownAlmSetupEty ::= SEQUENCE {
            enLinkdownAlmSetupUnit      UnitID,
            enLinkdownAlmSetupPort      LanPortNum,
            enLinkdownAlmSetupAlarm     INTEGER,
            enLinkdownAlmSetupRelay     INTEGER,
            enLinkdownAlmSetupSvrity    Severity
        }

        enLinkdownAlmSetupUnit  OBJECT-TYPE
            SYNTAX  UnitID
            ACCESS  read-only
            STATUS  mandatory
            DESCRIPTION
            "unit 1 to 4."
            ::= { enetLinkdownAlmSetupEty 1 }

        enLinkdownAlmSetupPort  OBJECT-TYPE
            SYNTAX  LanPortNum
            ACCESS  read-only
            STATUS  mandatory
            DESCRIPTION
                "LAN port index: LAN1~LAN9"
            ::= { enetLinkdownAlmSetupEty 2 }

        enLinkdownAlmSetupAlarm  OBJECT-TYPE
            SYNTAX  INTEGER {
                    disable(1),
                    enable(2)
                }
            ACCESS  read-write
            STATUS  mandatory
            DESCRIPTION
                "Linkdown Alarm Mask"
            ::= { enetLinkdownAlmSetupEty 3 }

        enLinkdownAlmSetupRelay  OBJECT-TYPE
            SYNTAX  INTEGER {
                    disable(1),
                    enable(2)
                }
            ACCESS  read-write
            STATUS  mandatory
            DESCRIPTION
                "Linkdown Alarm Relay"
            ::= { enetLinkdownAlmSetupEty 4 }

        enLinkdownAlmSetupSvrity  OBJECT-TYPE
            SYNTAX  Severity
            ACCESS  read-write
            STATUS  mandatory
            DESCRIPTION
                "Linkdown Alarm Severity"
            ::= { enetLinkdownAlmSetupEty 5 }

--
--  enetLinkConfigTable
--
        enetLinkConfigTable  OBJECT-TYPE
            SYNTAX  SEQUENCE OF  EnetLinkConfigEntry
            ACCESS  not-accessible
            STATUS  mandatory
            DESCRIPTION
                "The Ethernet Link Config Table."
            ::= { enetLinkSetupTable 2 }

        enetLinkConfigEntry  OBJECT-TYPE
            SYNTAX  EnetLinkConfigEntry
            ACCESS  not-accessible
            STATUS  mandatory
            DESCRIPTION
                "An entry in The Ethernet Link Config Table."
            INDEX { enLinkCfgUnit , enLinkCfgPort }
            ::= { enetLinkConfigTable 1 }

        EnetLinkConfigEntry ::= SEQUENCE {
            enLinkCfgUnit               UnitID,
            enLinkCfgPort               LanPortNum,
            enLinkCfgConfig             INTEGER
        }

        enLinkCfgUnit  OBJECT-TYPE
            SYNTAX  UnitID
            ACCESS  read-only
            STATUS  mandatory
            DESCRIPTION
            "unit 1 to 4."
            ::= { enetLinkConfigEntry 1 }

        enLinkCfgPort  OBJECT-TYPE
            SYNTAX  LanPortNum
            ACCESS  read-only
            STATUS  mandatory
            DESCRIPTION
                "LAN port index: LAN1~LAN9"
            ::= { enetLinkConfigEntry 2 }

        enLinkCfgConfig  OBJECT-TYPE
            SYNTAX  INTEGER {
                    auto-negotiation(1),
                    full-duplex-100M(2),
                    full-duplex-10M(3),
                    half-duplex-100M(4),
                    half-duplex-10M(5),
                    full-duplex-1000M(6)
                }
            ACCESS  read-write
            STATUS  mandatory
            DESCRIPTION
                "Link Config"
            ::= { enetLinkConfigEntry 3 }

--
--  enetCustomInfoTable
--
        enetCustomInfoTable  OBJECT-TYPE
            SYNTAX  SEQUENCE OF  EnetCustomInfoEntry
            ACCESS  not-accessible
            STATUS  mandatory
            DESCRIPTION
                "The Ethernet Customer Information Table."
            ::= { enetLinkSetupTable 3 }

        enetCustomInfoEntry  OBJECT-TYPE
            SYNTAX  EnetCustomInfoEntry
            ACCESS  not-accessible
            STATUS  mandatory
            DESCRIPTION
                "An entry in The Ethernet Customer Information Table."
            INDEX { enCustomInfoUnit , enCustomInfoPort }
            ::= { enetCustomInfoTable 1 }

        EnetCustomInfoEntry ::= SEQUENCE {
            enCustomInfoUnit            UnitID,
            enCustomInfoPort            LanPortNum,
            enCustomInfoInformation     DisplayString (SIZE (1..20))
        }

        enCustomInfoUnit  OBJECT-TYPE
            SYNTAX  UnitID
            ACCESS  read-only
            STATUS  mandatory
            DESCRIPTION
            "unit 1 to 4."
            ::= { enetCustomInfoEntry 1 }

        enCustomInfoPort  OBJECT-TYPE
            SYNTAX  LanPortNum
            ACCESS  read-only
            STATUS  mandatory
            DESCRIPTION
                "LAN port index: LAN1~LAN9"
            ::= { enetCustomInfoEntry 2 }

        enCustomInfoInformation  OBJECT-TYPE
            SYNTAX  DisplayString (SIZE (1..20))
            ACCESS  read-write
            STATUS  mandatory
            DESCRIPTION
                "Customer Information"
            ::= { enetCustomInfoEntry 3 }

--
--  enetFailPropagationTab
--
        enetFailPropagationTab  OBJECT-TYPE
            SYNTAX  SEQUENCE OF  EnetFailPropagationEty
            ACCESS  not-accessible
            STATUS  mandatory
            DESCRIPTION
                "The Ethernet Link fail propagation Table."
            ::= { enetLinkSetupTable 4 }

        enetFailPropagationEty  OBJECT-TYPE
            SYNTAX  EnetFailPropagationEty
            ACCESS  not-accessible
            STATUS  mandatory
            DESCRIPTION
                "An entry in The Ethernet fail propagation Table."
            INDEX { enFailPropUnit }
            ::= { enetFailPropagationTab 1 }

        EnetFailPropagationEty ::= SEQUENCE {
            enFailPropUnit              UnitID,
            enFailPropWanLost           INTEGER,
            enFailPropRemoteLinkDown    INTEGER,
            enFailPropRemoteGuard       INTEGER
        }

        enFailPropUnit  OBJECT-TYPE
            SYNTAX  UnitID
            ACCESS  read-only
            STATUS  mandatory
            DESCRIPTION
            "unit 1 to 4."
            ::= { enetFailPropagationEty 1 }

        enFailPropWanLost  OBJECT-TYPE
            SYNTAX  INTEGER {
                    disable(1),
                    enable(2)
                }
            ACCESS  read-write
            STATUS  mandatory
            DESCRIPTION
                "WAN(VCG) Lost Propagation"
            ::= { enetFailPropagationEty 2 }

        enFailPropRemoteLinkDown  OBJECT-TYPE
            SYNTAX  INTEGER {
                    disable(1),
                    enable(2)
                }
            ACCESS  read-write
            STATUS  mandatory
            DESCRIPTION
                "Remote Link Down Propagation"
            ::= { enetFailPropagationEty 3 }

        enFailPropRemoteGuard  OBJECT-TYPE
            SYNTAX  INTEGER {
                    second-1(1),
                    second-2(2),
                    second-3(3),
                    second-4(4),
                    second-5(5)
                }
            ACCESS  read-write
            STATUS  mandatory
            DESCRIPTION
                "Remote Link Down Guard Time"
            ::= { enetFailPropagationEty 4 }

--
--  enetLinkIFGTable
--
        enetLinkIFGTable  OBJECT-TYPE
            SYNTAX  SEQUENCE OF  EnetLinkIFGEntry
            ACCESS  not-accessible
            STATUS  mandatory
            DESCRIPTION
                "The Ethernet Link IFG Table."
            ::= { enetLinkSetupTable 5 }

        enetLinkIFGEntry  OBJECT-TYPE
            SYNTAX  EnetLinkIFGEntry
            ACCESS  not-accessible
            STATUS  mandatory
            DESCRIPTION
                "An entry in The Ethernet Link IFG Table."
            INDEX { enLinkIFGUnit , enLinkIFGPort }
            ::= { enetLinkIFGTable 1 }

        EnetLinkIFGEntry ::= SEQUENCE {
            enLinkIFGUnit               UnitID,
            enLinkIFGPort               LanPortNum,
            enLinkIFGSize               INTEGER
        }

        enLinkIFGUnit  OBJECT-TYPE
            SYNTAX  UnitID
            ACCESS  read-only
            STATUS  mandatory
            DESCRIPTION
            "unit 1 to 4."
            ::= { enetLinkIFGEntry 1 }

        enLinkIFGPort  OBJECT-TYPE
            SYNTAX  LanPortNum
            ACCESS  read-only
            STATUS  mandatory
            DESCRIPTION
                "LAN port index: LAN1~LAN9"
            ::= { enetLinkIFGEntry 2 }

        enLinkIFGSize  OBJECT-TYPE
            SYNTAX  INTEGER {
                    bit-times-80(1),
                    bit-times-88(2),
                    bit-times-96(3)
                }
            ACCESS  read-write
            STATUS  mandatory
            DESCRIPTION
                "Link IFG Size"
            ::= { enetLinkIFGEntry 3 }

--
--  enetWanVcgSizeTable
--
        enetWanVcgSizeTable  OBJECT-TYPE
            SYNTAX  SEQUENCE OF  EnetWanVcgSizeEntry
            ACCESS  not-accessible
            STATUS  mandatory
            DESCRIPTION
                "The Ethernet VCG size Table."
            ::= { enet-card 4 }

        enetWanVcgSizeEntry  OBJECT-TYPE
            SYNTAX  EnetWanVcgSizeEntry
            ACCESS  not-accessible
            STATUS  mandatory
            DESCRIPTION
                "An entry in The Ethernet VCG size Table."
            INDEX { enVcgSizeUnit , enVcgSizePort }
            ::= { enetWanVcgSizeTable 1 }

        EnetWanVcgSizeEntry ::= SEQUENCE {
            enVcgSizeUnit               UnitID,
            enVcgSizePort               VcgPortNum,
            enVcgSizeAddChanCount       Counter,
            enVcgSizeDropChanCount      Counter
        }

        enVcgSizeUnit  OBJECT-TYPE
            SYNTAX  UnitID
            ACCESS  read-only
            STATUS  mandatory
            DESCRIPTION
            "unit 1 to 4."
            ::= { enetWanVcgSizeEntry 1 }

        enVcgSizePort  OBJECT-TYPE
            SYNTAX  VcgPortNum
            ACCESS  read-only
            STATUS  mandatory
            DESCRIPTION
                "Port WAN1~9"
            ::= { enetWanVcgSizeEntry 2 }

        enVcgSizeAddChanCount  OBJECT-TYPE
            SYNTAX  Counter
            ACCESS  read-only
            STATUS  mandatory
            DESCRIPTION
                "VCG Add Channel Count"
            ::= { enetWanVcgSizeEntry 3 }

        enVcgSizeDropChanCount  OBJECT-TYPE
            SYNTAX  Counter
            ACCESS  read-only
            STATUS  mandatory
            DESCRIPTION
                "VCG Drop Channel Count"
            ::= { enetWanVcgSizeEntry 4 }

--
--  enetAlarmStatusTable
--
    enetAlarmStatusTable     OBJECT IDENTIFIER ::= { enet-card 5 }

--
--  enetHP-STSAlmStatusTab
--
        enetHP-STSAlmStatusTab  OBJECT-TYPE
            SYNTAX  SEQUENCE OF  EnetHP-STSAlmStatusEty
            ACCESS  not-accessible
            STATUS  mandatory
            DESCRIPTION
                "The Ethernet HO-path/STS-path alm status table."
            ::= { enetAlarmStatusTable 1 }

        enetHP-STSAlmStatusEty  OBJECT-TYPE
            SYNTAX  EnetHP-STSAlmStatusEty
            ACCESS  not-accessible
            STATUS  mandatory
            DESCRIPTION
                "An entry in HO-path/STS-path alm status table."
            INDEX { enHpStsAlmStUnit , enHpStsAlmStPort ,
                    enHpStsAlmStChannel }
            ::= { enetHP-STSAlmStatusTab 1 }

        EnetHP-STSAlmStatusEty ::= SEQUENCE {
            enHpStsAlmStUnit            UnitID,
            enHpStsAlmStPort            VcgPortNum,
            enHpStsAlmStChannel         ChannelNum,
            enHpStsAlmStLOP             AlmStatus,
            enHpStsAlmStAIS             AlmStatus,
            enHpStsAlmStUNEQ            AlmStatus,
            enHpStsAlmStRDI-S           AlmStatus,
            enHpStsAlmStRDI-C           AlmStatus,
            enHpStsAlmStRDI-P           AlmStatus,
            enHpStsAlmStBIP             AlmStatus,
            enHpStsAlmStREI             AlmStatus
        }

        enHpStsAlmStUnit  OBJECT-TYPE
            SYNTAX  UnitID
            ACCESS  read-only
            STATUS  mandatory
            DESCRIPTION
            "unit 1 to 4."
            ::= { enetHP-STSAlmStatusEty 1 }

        enHpStsAlmStPort  OBJECT-TYPE
            SYNTAX  VcgPortNum
            ACCESS  read-only
            STATUS  mandatory
            DESCRIPTION
                "vcg port index: wan1~wan9"
            ::= { enetHP-STSAlmStatusEty 2 }

        enHpStsAlmStChannel  OBJECT-TYPE
            SYNTAX  ChannelNum
            ACCESS  read-only
            STATUS  mandatory
            DESCRIPTION
                "Channel index"
            ::= { enetHP-STSAlmStatusEty 3 }

        enHpStsAlmStLOP  OBJECT-TYPE
            SYNTAX  AlmStatus
            ACCESS  read-only
            STATUS  mandatory
            DESCRIPTION
                "Alarm Status"
            ::= { enetHP-STSAlmStatusEty 4 }

        enHpStsAlmStAIS  OBJECT-TYPE
            SYNTAX  AlmStatus
            ACCESS  read-only
            STATUS  mandatory
            DESCRIPTION
                "Alarm Status"
            ::= { enetHP-STSAlmStatusEty 5 }

        enHpStsAlmStUNEQ  OBJECT-TYPE
            SYNTAX  AlmStatus
            ACCESS  read-only
            STATUS  mandatory
            DESCRIPTION
                "Alarm Status"
            ::= { enetHP-STSAlmStatusEty 6 }

        enHpStsAlmStRDI-S  OBJECT-TYPE
            SYNTAX  AlmStatus
            ACCESS  read-only
            STATUS  mandatory
            DESCRIPTION
                "Alarm Status"
            ::= { enetHP-STSAlmStatusEty 7 }

        enHpStsAlmStRDI-C  OBJECT-TYPE
            SYNTAX  AlmStatus
            ACCESS  read-only
            STATUS  mandatory
            DESCRIPTION
                "Alarm Status"
            ::= { enetHP-STSAlmStatusEty 8 }

        enHpStsAlmStRDI-P  OBJECT-TYPE
            SYNTAX  AlmStatus
            ACCESS  read-only
            STATUS  mandatory
            DESCRIPTION
                "Alarm Status"
            ::= { enetHP-STSAlmStatusEty 9 }

        enHpStsAlmStBIP  OBJECT-TYPE
            SYNTAX  AlmStatus
            ACCESS  read-only
            STATUS  mandatory
            DESCRIPTION
                "Alarm Status"
            ::= { enetHP-STSAlmStatusEty 10 }

        enHpStsAlmStREI  OBJECT-TYPE
            SYNTAX  AlmStatus
            ACCESS  read-only
            STATUS  mandatory
            DESCRIPTION
                "Alarm Status"
            ::= { enetHP-STSAlmStatusEty 11 }

--
--  enetLP-VTAlmStatusTab
--
        enetLP-VTAlmStatusTab  OBJECT-TYPE
            SYNTAX  SEQUENCE OF  EnetLP-VTAlmStatusEty
            ACCESS  not-accessible
            STATUS  mandatory
            DESCRIPTION
                "The Ethernet LO-path/VT-path alm status table."
            ::= { enetAlarmStatusTable 2 }

        enetLP-VTAlmStatusEty  OBJECT-TYPE
            SYNTAX  EnetLP-VTAlmStatusEty
            ACCESS  not-accessible
            STATUS  mandatory
            DESCRIPTION
                "An entry in LO-path/VT-path alm status table."
            INDEX { enLpVtAlmStUnit , enLpVtAlmStPort ,
                    enLpVtAlmStChannel }
            ::= { enetLP-VTAlmStatusTab 1 }

        EnetLP-VTAlmStatusEty ::= SEQUENCE {
            enLpVtAlmStUnit             UnitID,
            enLpVtAlmStPort             VcgPortNum,
            enLpVtAlmStChannel          ChannelNum,
            enLpVtAlmStLOP              AlmStatus,
            enLpVtAlmStAIS              AlmStatus,
            enLpVtAlmStUNEQ             AlmStatus,
            enLpVtAlmStRDI-S            AlmStatus,
            enLpVtAlmStRDI-C            AlmStatus,
            enLpVtAlmStRDI-P            AlmStatus,
            enLpVtAlmStBIP              AlmStatus,
            enLpVtAlmStREI              AlmStatus
        }

        enLpVtAlmStUnit  OBJECT-TYPE
            SYNTAX  UnitID
            ACCESS  read-only
            STATUS  mandatory
            DESCRIPTION
            "unit 1 to 4."
            ::= { enetLP-VTAlmStatusEty 1 }

        enLpVtAlmStPort  OBJECT-TYPE
            SYNTAX  VcgPortNum
            ACCESS  read-only
            STATUS  mandatory
            DESCRIPTION
                "vcg port index: wan1~wan9"
            ::= { enetLP-VTAlmStatusEty 2 }

        enLpVtAlmStChannel  OBJECT-TYPE
            SYNTAX  ChannelNum
            ACCESS  read-only
            STATUS  mandatory
            DESCRIPTION
                "Channel index"
            ::= { enetLP-VTAlmStatusEty 3 }

        enLpVtAlmStLOP  OBJECT-TYPE
            SYNTAX  AlmStatus
            ACCESS  read-only
            STATUS  mandatory
            DESCRIPTION
                "Alarm Status"
            ::= { enetLP-VTAlmStatusEty 4 }

        enLpVtAlmStAIS  OBJECT-TYPE
            SYNTAX  AlmStatus
            ACCESS  read-only
            STATUS  mandatory
            DESCRIPTION
                "Alarm Status"
            ::= { enetLP-VTAlmStatusEty 5 }

        enLpVtAlmStUNEQ  OBJECT-TYPE
            SYNTAX  AlmStatus
            ACCESS  read-only
            STATUS  mandatory
            DESCRIPTION
                "Alarm Status"
            ::= { enetLP-VTAlmStatusEty 6 }

        enLpVtAlmStRDI-S  OBJECT-TYPE
            SYNTAX  AlmStatus
            ACCESS  read-only
            STATUS  mandatory
            DESCRIPTION
                "Alarm Status"
            ::= { enetLP-VTAlmStatusEty 7 }

        enLpVtAlmStRDI-C  OBJECT-TYPE
            SYNTAX  AlmStatus
            ACCESS  read-only
            STATUS  mandatory
            DESCRIPTION
                "Alarm Status"
            ::= { enetLP-VTAlmStatusEty 8 }

        enLpVtAlmStRDI-P  OBJECT-TYPE
            SYNTAX  AlmStatus
            ACCESS  read-only
            STATUS  mandatory
            DESCRIPTION
                "Alarm Status"
            ::= { enetLP-VTAlmStatusEty 9 }

        enLpVtAlmStBIP  OBJECT-TYPE
            SYNTAX  AlmStatus
            ACCESS  read-only
            STATUS  mandatory
            DESCRIPTION
                "Alarm Status"
            ::= { enetLP-VTAlmStatusEty 10 }

        enLpVtAlmStREI  OBJECT-TYPE
            SYNTAX  AlmStatus
            ACCESS  read-only
            STATUS  mandatory
            DESCRIPTION
                "Alarm Status"
            ::= { enetLP-VTAlmStatusEty 11 }

--
--  enetLinkdownAlmStatusTab
--
        enetLinkdownAlmStatusTab  OBJECT-TYPE
            SYNTAX  SEQUENCE OF  EnetLinkdownAlmStatusEty
            ACCESS  not-accessible
            STATUS  mandatory
            DESCRIPTION
                "The Ethernet Linkdown alm status table."
            ::= { enetAlarmStatusTable 3 }

        enetLinkdownAlmStatusEty  OBJECT-TYPE
            SYNTAX  EnetLinkdownAlmStatusEty
            ACCESS  not-accessible
            STATUS  mandatory
            DESCRIPTION
                "An entry in Linkdown alm status table."
            INDEX { enLinkdownAlmStUnit , enLinkdownAlmStPort }
            ::= { enetLinkdownAlmStatusTab 1 }

        EnetLinkdownAlmStatusEty ::= SEQUENCE {
            enLinkdownAlmStUnit         UnitID,
            enLinkdownAlmStPort         LanPortNum,
            enLinkdownAlmStAlarm        AlmStatus
        }

        enLinkdownAlmStUnit  OBJECT-TYPE
            SYNTAX  UnitID
            ACCESS  read-only
            STATUS  mandatory
            DESCRIPTION
            "unit 1 to 4."
            ::= { enetLinkdownAlmStatusEty 1 }

        enLinkdownAlmStPort  OBJECT-TYPE
            SYNTAX  LanPortNum
            ACCESS  read-only
            STATUS  mandatory
            DESCRIPTION
                "LAN port index: LAN1~LAN9"
            ::= { enetLinkdownAlmStatusEty 2 }

        enLinkdownAlmStAlarm  OBJECT-TYPE
            SYNTAX  AlmStatus
            ACCESS  read-only
            STATUS  mandatory
            DESCRIPTION
                "Alarm Status"
            ::= { enetLinkdownAlmStatusEty 3 }


--  2012-07-30 add below by Rukka
--
--  Ethernet Current Active Alarm Summary Table
--
        enetCurrActAlmSummaryTab  OBJECT-TYPE
            SYNTAX  SEQUENCE OF EnetCurrActAlmSummaryEty
            ACCESS  not-accessible
            STATUS  mandatory
            DESCRIPTION
                "Ethernet Current Active Alarm Summary Table."
            ::= { enetAlarmStatusTable 4 }

        enetCurrActAlmSummaryEty  OBJECT-TYPE
            SYNTAX  EnetCurrActAlmSummaryEty
            ACCESS  not-accessible
            STATUS  mandatory
            DESCRIPTION
                "ethernet current active alarm summary entry"
            INDEX { enetAlmSumUnit ,
                    enetAlmSumIndex }
            ::= { enetCurrActAlmSummaryTab 1 }

        EnetCurrActAlmSummaryEty ::= SEQUENCE {
            enetAlmSumUnit               UnitID,
            enetAlmSumIndex              INTEGER,
            enetAlmSumString             DisplayString (SIZE(0..255)),
            enetAlmSumUnitNum            CardID,
            enetAlmSumCardModel          CardModel,
            enetAlmSumPortNum            SwPortNum,
            enetAlmSumChannel            ChannelNum,
            enetAlmSumAlmNum             AlarmNum,
            enetAlmVC43STS31Type         Au4Au3Type,
            enetAlmTU1xVTxType           Tu1xVtxType,
            enetAlmSumStatus             AlmStatus,
            enetAlmSumSeverity           Severity
        }

        enetAlmSumUnit  OBJECT-TYPE
            SYNTAX  UnitID
            ACCESS  read-only
            STATUS  mandatory
            DESCRIPTION
                "Unit 1 to 8"
            ::= { enetCurrActAlmSummaryEty 1 }

        enetAlmSumIndex  OBJECT-TYPE
            SYNTAX  INTEGER
            ACCESS  read-only
            STATUS  mandatory
            DESCRIPTION
                "Select Alarm Summary Index"
            ::= { enetCurrActAlmSummaryEty 2 }

        enetAlmSumString  OBJECT-TYPE
            SYNTAX  DisplayString (SIZE (0..255))
            ACCESS  read-only
            STATUS  mandatory
            DESCRIPTION
                "Alarm Summary String"
            ::= { enetCurrActAlmSummaryEty 3 }

        enetAlmSumUnitNum  OBJECT-TYPE
            SYNTAX  CardID
            ACCESS  read-only
            STATUS  mandatory
            DESCRIPTION
                "Xcu or Unit 1~8"
            ::= { enetCurrActAlmSummaryEty 4 }

        enetAlmSumCardModel  OBJECT-TYPE
            SYNTAX  CardModel
            ACCESS  read-only
            STATUS  mandatory
            DESCRIPTION
                "Card Model"
            ::= { enetCurrActAlmSummaryEty 5 }

        enetAlmSumPortNum  OBJECT-TYPE
            SYNTAX  SwPortNum
            ACCESS  read-only
            STATUS  mandatory
            DESCRIPTION
                "vcg port index: wan1~wan9"
            ::= { enetCurrActAlmSummaryEty 6 }

        enetAlmSumChannel  OBJECT-TYPE
            SYNTAX  ChannelNum
            ACCESS  read-only
            STATUS  mandatory
            DESCRIPTION
                "Channel index"
            ::= { enetCurrActAlmSummaryEty 7 }

        enetAlmSumAlmNum  OBJECT-TYPE
            SYNTAX  AlarmNum
            ACCESS  read-only
            STATUS  mandatory
            DESCRIPTION
                "Alarm Num"
            ::= { enetCurrActAlmSummaryEty 8 }

        enetAlmVC43STS31Type  OBJECT-TYPE
            SYNTAX  Au4Au3Type
            ACCESS  read-only
            STATUS  mandatory
            DESCRIPTION
                "AU4 or AU3 type"
            ::= { enetCurrActAlmSummaryEty 9 }

        enetAlmTU1xVTxType  OBJECT-TYPE
            SYNTAX  Tu1xVtxType
            ACCESS  read-only
            STATUS  mandatory
            DESCRIPTION
                "Tu1x type"
            ::= { enetCurrActAlmSummaryEty 10 }

        enetAlmSumStatus  OBJECT-TYPE
            SYNTAX  AlmStatus
            ACCESS  read-only
            STATUS  mandatory
            DESCRIPTION
                "The Status of Alarm"
            ::= { enetCurrActAlmSummaryEty 11 }

        enetAlmSumSeverity  OBJECT-TYPE
            SYNTAX  Severity
            ACCESS  read-only
            STATUS  mandatory
            DESCRIPTION
                "Alarm Severity"
            ::= { enetCurrActAlmSummaryEty 12 }

-- 2012-07-30 add above by Rukka

--
-- enetPerformanceTable
--
    enetPerformanceTable     OBJECT IDENTIFIER ::= { enet-card 6 }

--
-- enetPerfThreshTable
--
    enetPerfThreshTable      OBJECT IDENTIFIER ::= { enetPerformanceTable 1 }

--
-- enetTcaMaskTable
--
        enetTcaMaskTable  OBJECT-TYPE
            SYNTAX  SEQUENCE OF EnetTcaMaskEntry
            ACCESS  not-accessible
            STATUS  mandatory
            DESCRIPTION
                "ethernet performance TCA mask table"
            ::= { enetPerfThreshTable 1 }

        enetTcaMaskEntry  OBJECT-TYPE
            SYNTAX  EnetTcaMaskEntry
            ACCESS  not-accessible
            STATUS  mandatory
            DESCRIPTION
                "ethernet performance TCA mask entry"
            INDEX { enTcaMaskUnit }
            ::= { enetTcaMaskTable 1 }

        EnetTcaMaskEntry ::= SEQUENCE {
            enTcaMaskUnit               UnitID,
            enTcaMaskHpSts              INTEGER,
            enTcaMaskFarEndHpSts        INTEGER,
            enTcaMaskLpVt-V5            INTEGER,
            enTcaMaskFarEndLpVt-V5      INTEGER,
            enTcaMaskLpVt-B3            INTEGER,
            enTcaMaskFarEndLpVt-B3      INTEGER
        }

        enTcaMaskUnit  OBJECT-TYPE
            SYNTAX  UnitID
            ACCESS  read-only
            STATUS  mandatory
            DESCRIPTION
            "unit 1 to 4."
            ::= { enetTcaMaskEntry 1 }

        enTcaMaskHpSts  OBJECT-TYPE
            SYNTAX  INTEGER {
                    disable(1),
                    enable(2)
                }
            ACCESS  read-write
            STATUS  mandatory
            DESCRIPTION
                "HP/STS TCA Mask"
            ::= { enetTcaMaskEntry 2 }

        enTcaMaskFarEndHpSts  OBJECT-TYPE
            SYNTAX  INTEGER {
                    disable(1),
                    enable(2)
                }
            ACCESS  read-write
            STATUS  mandatory
            DESCRIPTION
                "FarEnd HP/STS TCA Mask"
            ::= { enetTcaMaskEntry 3 }

        enTcaMaskLpVt-V5  OBJECT-TYPE
            SYNTAX  INTEGER {
                    disable(1),
                    enable(2)
                }
            ACCESS  read-write
            STATUS  mandatory
            DESCRIPTION
                "LP/VT V5 TCA Mask"
            ::= { enetTcaMaskEntry 4 }

        enTcaMaskFarEndLpVt-V5  OBJECT-TYPE
            SYNTAX  INTEGER {
                    disable(1),
                    enable(2)
                }
            ACCESS  read-write
            STATUS  mandatory
            DESCRIPTION
                "FarEnd LP/VT V5 TCA Mask"
            ::= { enetTcaMaskEntry 5 }

        enTcaMaskLpVt-B3  OBJECT-TYPE
            SYNTAX  INTEGER {
                    disable(1),
                    enable(2)
                }
            ACCESS  read-write
            STATUS  mandatory
            DESCRIPTION
                "LP/VT B3 TCA Mask"
            ::= { enetTcaMaskEntry 6 }

        enTcaMaskFarEndLpVt-B3  OBJECT-TYPE
            SYNTAX  INTEGER {
                    disable(1),
                    enable(2)
                }
            ACCESS  read-write
            STATUS  mandatory
            DESCRIPTION
                "FarEnd LP/VT B3 TCA Mask"
            ::= { enetTcaMaskEntry 7 }

--
-- enetTcaSvrityTable
--
        enetTcaSvrityTable  OBJECT-TYPE
            SYNTAX  SEQUENCE OF EnetTcaSvrityEntry
            ACCESS  not-accessible
            STATUS  mandatory
            DESCRIPTION
                "ethernet performance TCA severity table"
            ::= { enetPerfThreshTable 2 }

        enetTcaSvrityEntry  OBJECT-TYPE
            SYNTAX  EnetTcaSvrityEntry
            ACCESS  not-accessible
            STATUS  mandatory
            DESCRIPTION
                "ethernet performance TCA severity entry"
            INDEX { enTcaSvrityUnit }
            ::= { enetTcaSvrityTable 1 }

        EnetTcaSvrityEntry ::= SEQUENCE {
            enTcaSvrityUnit             UnitID,
            enTcaSvrityHpSts            Severity,
            enTcaSvrityFarEndHpSts      Severity,
            enTcaSvrityLpVt-V5          Severity,
            enTcaSvrityFarEndLpVt-V5    Severity,
            enTcaSvrityLpVt-B3          Severity,
            enTcaSvrityFarEndLpVt-B3    Severity
        }

        enTcaSvrityUnit  OBJECT-TYPE
            SYNTAX  UnitID
            ACCESS  read-only
            STATUS  mandatory
            DESCRIPTION
            "unit 1 to 4."
            ::= { enetTcaSvrityEntry 1 }

        enTcaSvrityHpSts  OBJECT-TYPE
            SYNTAX  Severity
            ACCESS  read-write
            STATUS  mandatory
            DESCRIPTION
                "HP/STS TCA Severity"
            ::= { enetTcaSvrityEntry 2 }

        enTcaSvrityFarEndHpSts  OBJECT-TYPE
            SYNTAX  Severity
            ACCESS  read-write
            STATUS  mandatory
            DESCRIPTION
                "FarEnd HP/STS TCA Severity"
            ::= { enetTcaSvrityEntry 3 }

        enTcaSvrityLpVt-V5  OBJECT-TYPE
            SYNTAX  Severity
            ACCESS  read-write
            STATUS  mandatory
            DESCRIPTION
                "LP/VT V5 TCA Severity"
            ::= { enetTcaSvrityEntry 4 }

        enTcaSvrityFarEndLpVt-V5  OBJECT-TYPE
            SYNTAX  Severity
            ACCESS  read-write
            STATUS  mandatory
            DESCRIPTION
                "FarEnd LP/VT V5 TCA Severity"
            ::= { enetTcaSvrityEntry 5 }

        enTcaSvrityLpVt-B3  OBJECT-TYPE
            SYNTAX  Severity
            ACCESS  read-write
            STATUS  mandatory
            DESCRIPTION
                "LP/VT B3 TCA Severity"
            ::= { enetTcaSvrityEntry 6 }

        enTcaSvrityFarEndLpVt-B3  OBJECT-TYPE
            SYNTAX  Severity
            ACCESS  read-write
            STATUS  mandatory
            DESCRIPTION
                "FarEnd LP/VT B3 TCA Severity"
            ::= { enetTcaSvrityEntry 7 }

--
-- enetTcaThreshTable
--
        enetTcaThreshTable  OBJECT-TYPE
            SYNTAX  SEQUENCE OF EnetTcaThreshEntry
            ACCESS  not-accessible
            STATUS  mandatory
            DESCRIPTION
                "ethernet performance TCA threshold table"
            ::= { enetPerfThreshTable 3 }

        enetTcaThreshEntry  OBJECT-TYPE
            SYNTAX  EnetTcaThreshEntry
            ACCESS  not-accessible
            STATUS  mandatory
            DESCRIPTION
                "ethernet performance TCA threshold entry"
            INDEX { enTcaThreshUnit }
            ::= { enetTcaThreshTable 1 }

        EnetTcaThreshEntry ::= SEQUENCE {
            enTcaThreshUnit             UnitID,
            enTcaThreshHpSts            INTEGER,
            enTcaThreshFarEndHpSts      INTEGER,
            enTcaThreshLpVt-V5          INTEGER,
            enTcaThreshFarEndLpVt-V5    INTEGER,
            enTcaThreshLpVt-B3          INTEGER,
            enTcaThreshFarEndLpVt-B3    INTEGER
        }

        enTcaThreshUnit  OBJECT-TYPE
            SYNTAX  UnitID
            ACCESS  read-only
            STATUS  mandatory
            DESCRIPTION
            "unit 1 to 4."
            ::= { enetTcaThreshEntry 1 }

        enTcaThreshHpSts  OBJECT-TYPE
            SYNTAX  INTEGER (1..99999)
            ACCESS  read-write
            STATUS  mandatory
            DESCRIPTION
                "HP/STS TCA Thresh"
            ::= { enetTcaThreshEntry 2 }

        enTcaThreshFarEndHpSts  OBJECT-TYPE
            SYNTAX  INTEGER (1..99999)
            ACCESS  read-write
            STATUS  mandatory
            DESCRIPTION
                "FarEnd HP/STS TCA Thresh"
            ::= { enetTcaThreshEntry 3 }

        enTcaThreshLpVt-V5  OBJECT-TYPE
            SYNTAX  INTEGER (1..99999)
            ACCESS  read-write
            STATUS  mandatory
            DESCRIPTION
                "LP/VT V5 TCA Thresh"
            ::= { enetTcaThreshEntry 4 }

        enTcaThreshFarEndLpVt-V5  OBJECT-TYPE
            SYNTAX  INTEGER (1..99999)
            ACCESS  read-write
            STATUS  mandatory
            DESCRIPTION
                "FarEnd LP/VT V5 TCA Thresh"
            ::= { enetTcaThreshEntry 5 }

        enTcaThreshLpVt-B3  OBJECT-TYPE
            SYNTAX  INTEGER (1..99999)
            ACCESS  read-write
            STATUS  mandatory
            DESCRIPTION
                "LP/VT B3 TCA Thresh"
            ::= { enetTcaThreshEntry 6 }

        enTcaThreshFarEndLpVt-B3  OBJECT-TYPE
            SYNTAX  INTEGER (1..99999)
            ACCESS  read-write
            STATUS  mandatory
            DESCRIPTION
                "FarEnd LP/VT B3 TCA Thresh"
            ::= { enetTcaThreshEntry 7 }

--
--  enetPerfControlTable
--
        enetPerfControlTable  OBJECT-TYPE
            SYNTAX  SEQUENCE OF  EnetPerfControlEntry
            ACCESS  not-accessible
            STATUS  mandatory
            DESCRIPTION
                "Ethernet performance control table "
            ::= { enetPerformanceTable 2 }

        enetPerfControlEntry  OBJECT-TYPE
            SYNTAX  EnetPerfControlEntry
            ACCESS  not-accessible
            STATUS  mandatory
            DESCRIPTION
                "Ethernet performance control entry"
            INDEX { enPerfCtrlUnit }
            ::= { enetPerfControlTable 1 }

        EnetPerfControlEntry ::= SEQUENCE {
            enPerfCtrlUnit              UnitID,
            enPerfCtrlPerfClear         INTEGER
        }

        enPerfCtrlUnit  OBJECT-TYPE
            SYNTAX  UnitID
            ACCESS  read-only
            STATUS  mandatory
            DESCRIPTION
            "unit 1 to 4."
            ::= { enetPerfControlEntry 1 }

        enPerfCtrlPerfClear  OBJECT-TYPE
            SYNTAX  INTEGER {
                    no(1),
                    clear(2)
                }
            ACCESS  read-write
            STATUS  mandatory
            DESCRIPTION
                "Clear performance"
            ::= { enetPerfControlEntry 2 }

--
--  enetPerfDisplayTable
--
    enetPerfDisplayTable     OBJECT IDENTIFIER ::= { enetPerformanceTable 3 }

--
--  enHP-STSCurrTab
--
        enHP-STSCurrTab  OBJECT-TYPE
            SYNTAX  SEQUENCE OF  EnHP-STSCurrEty
            ACCESS  not-accessible
            STATUS  mandatory
            DESCRIPTION
                "The Ethernet B3 Current table."
            ::= { enetPerfDisplayTable 1 }

        enHP-STSCurrEty  OBJECT-TYPE
            SYNTAX  EnHP-STSCurrEty
            ACCESS  not-accessible
            STATUS  mandatory
            DESCRIPTION
                "An entry in the Ethernet B3 Current table."
            INDEX { enHpStsCurrUnit , enHpStsCurrPort ,
                    enHpStsCurrChannel }
            ::= { enHP-STSCurrTab 1 }

        EnHP-STSCurrEty ::= SEQUENCE {
            enHpStsCurrUnit             UnitID,
            enHpStsCurrPort             VcgPortNum,
            enHpStsCurrChannel          ChannelNum,
            enHpStsCurrEBs              Counter,
            enHpStsCurrBBEs             Counter,
            enHpStsCurrESs              Counter,
            enHpStsCurrBESs             Counter,
            enHpStsCurrSESs             Counter,
            enHpStsCurrUASs             Counter,
            enHpStsCurr24HValid15M      Counter,
            enHpStsCurr7DayValidDay     Counter,
            enHpStsCurr15MTimeElaps     Counter,
            enHpStsCurrDayValid15M      Counter
        }

        enHpStsCurrUnit  OBJECT-TYPE
            SYNTAX  UnitID
            ACCESS  read-only
            STATUS  mandatory
            DESCRIPTION
            "unit 1 to 4."
            ::= { enHP-STSCurrEty 1 }

        enHpStsCurrPort  OBJECT-TYPE
            SYNTAX  VcgPortNum
            ACCESS  read-only
            STATUS  mandatory
            DESCRIPTION
                "vcg port index: wan1~wan9"
            ::= { enHP-STSCurrEty 2 }

        enHpStsCurrChannel  OBJECT-TYPE
            SYNTAX  ChannelNum
            ACCESS  read-only
            STATUS  mandatory
            DESCRIPTION
                "Channel index"
            ::= { enHP-STSCurrEty 3 }

        enHpStsCurrEBs  OBJECT-TYPE
            SYNTAX  Counter
            ACCESS  read-only
            STATUS  mandatory
            DESCRIPTION
                "B3(BIP-8) Error Block"
            ::= { enHP-STSCurrEty 4 }

        enHpStsCurrBBEs  OBJECT-TYPE
            SYNTAX  Counter
            ACCESS  read-only
            STATUS  mandatory
            DESCRIPTION
                "B3(BIP-8) Background Block Error"
            ::= { enHP-STSCurrEty 5 }

        enHpStsCurrESs  OBJECT-TYPE
            SYNTAX  Counter
            ACCESS  read-only
            STATUS  mandatory
            DESCRIPTION
                "B3(BIP-8) Error Second"
            ::= { enHP-STSCurrEty 6 }

        enHpStsCurrBESs  OBJECT-TYPE
            SYNTAX  Counter
            ACCESS  read-only
            STATUS  mandatory
            DESCRIPTION
                "B3(BIP-8) Background Error Second"
            ::= { enHP-STSCurrEty 7 }

        enHpStsCurrSESs  OBJECT-TYPE
            SYNTAX  Counter
            ACCESS  read-only
            STATUS  mandatory
            DESCRIPTION
                "B3(BIP-8) Severly Error Second"
            ::= { enHP-STSCurrEty 8 }

        enHpStsCurrUASs  OBJECT-TYPE
            SYNTAX  Counter
            ACCESS  read-only
            STATUS  mandatory
            DESCRIPTION
                "B3(BIP-8) Unavailable Second"
            ::= { enHP-STSCurrEty 9 }

        enHpStsCurr24HValid15M  OBJECT-TYPE
            SYNTAX  Counter
            ACCESS  read-only
            STATUS  mandatory
            DESCRIPTION
                "B3(BIP-8) Valid 15-Min Interval"
            ::= { enHP-STSCurrEty 10 }

        enHpStsCurr7DayValidDay  OBJECT-TYPE
            SYNTAX  Counter
            ACCESS  read-only
            STATUS  mandatory
            DESCRIPTION
                "B3(BIP-8) Valid 1-Day Interval"
            ::= { enHP-STSCurrEty 11 }

        enHpStsCurr15MTimeElaps  OBJECT-TYPE
            SYNTAX  Counter
            ACCESS  read-only
            STATUS  mandatory
            DESCRIPTION
                "B3(BIP-8) Current 15-MIN Time Elapsed"
            ::= { enHP-STSCurrEty 12 }

        enHpStsCurrDayValid15M  OBJECT-TYPE
            SYNTAX  Counter
            ACCESS  read-only
            STATUS  mandatory
            DESCRIPTION
                "B3(BIP-8) Current Day Time Elapsed"
            ::= { enHP-STSCurrEty 13 }

--
--  enHP-STSIntervTab
--
        enHP-STSIntervTab  OBJECT-TYPE
            SYNTAX  SEQUENCE OF  EnHP-STSIntervEty
            ACCESS  not-accessible
            STATUS  mandatory
            DESCRIPTION
                "The Ethernet B3 Interval table."
            ::= { enetPerfDisplayTable 2 }

        enHP-STSIntervEty  OBJECT-TYPE
            SYNTAX  EnHP-STSIntervEty
            ACCESS  not-accessible
            STATUS  mandatory
            DESCRIPTION
                "An entry in the Ethernet B3 Interval table."
            INDEX { enHpStsIntervUnit , enHpStsIntervPort ,
                    enHpStsIntervChannel , enHpStsIntervNumber }
            ::= { enHP-STSIntervTab 1 }

        EnHP-STSIntervEty ::= SEQUENCE {
            enHpStsIntervUnit           UnitID,
            enHpStsIntervPort           VcgPortNum,
            enHpStsIntervChannel        ChannelNum,
            enHpStsIntervNumber         INTEGER (1..96),
            enHpStsIntervEBs            Counter,
            enHpStsIntervBBEs           Counter,
            enHpStsIntervESs            Counter,
            enHpStsIntervBESs           Counter,
            enHpStsIntervSESs           Counter,
            enHpStsIntervUASs           Counter
        }

        enHpStsIntervUnit  OBJECT-TYPE
            SYNTAX  UnitID
            ACCESS  read-only
            STATUS  mandatory
            DESCRIPTION
            "unit 1 to 4."
            ::= { enHP-STSIntervEty 1 }

        enHpStsIntervPort  OBJECT-TYPE
            SYNTAX  VcgPortNum
            ACCESS  read-only
            STATUS  mandatory
            DESCRIPTION
                "vcg port index: wan1~wan9"
            ::= { enHP-STSIntervEty 2 }

        enHpStsIntervChannel  OBJECT-TYPE
            SYNTAX  ChannelNum
            ACCESS  read-only
            STATUS  mandatory
            DESCRIPTION
                "Channel index"
            ::= { enHP-STSIntervEty 3 }

        enHpStsIntervNumber  OBJECT-TYPE
            SYNTAX  INTEGER (1..96)
            ACCESS  read-only
            STATUS  mandatory
            DESCRIPTION
                "A number between 1 and 96"
            ::= { enHP-STSIntervEty 4 }

        enHpStsIntervEBs  OBJECT-TYPE
            SYNTAX  Counter
            ACCESS  read-only
            STATUS  mandatory
            DESCRIPTION
                "B3(BIP-8) Error Block"
            ::= { enHP-STSIntervEty 5 }

        enHpStsIntervBBEs  OBJECT-TYPE
            SYNTAX  Counter
            ACCESS  read-only
            STATUS  mandatory
            DESCRIPTION
                "B3(BIP-8) Background Block Error"
            ::= { enHP-STSIntervEty 6 }

        enHpStsIntervESs  OBJECT-TYPE
            SYNTAX  Counter
            ACCESS  read-only
            STATUS  mandatory
            DESCRIPTION
                "B3(BIP-8) Error Second"
            ::= { enHP-STSIntervEty 7 }

        enHpStsIntervBESs  OBJECT-TYPE
            SYNTAX  Counter
            ACCESS  read-only
            STATUS  mandatory
            DESCRIPTION
                "B3(BIP-8) Background Error Second"
            ::= { enHP-STSIntervEty 8 }

        enHpStsIntervSESs  OBJECT-TYPE
            SYNTAX  Counter
            ACCESS  read-only
            STATUS  mandatory
            DESCRIPTION
                "B3(BIP-8) Severly Error Second"
            ::= { enHP-STSIntervEty 9 }

        enHpStsIntervUASs  OBJECT-TYPE
            SYNTAX  Counter
            ACCESS  read-only
            STATUS  mandatory
            DESCRIPTION
                "B3(BIP-8) Unavailable Second"
            ::= { enHP-STSIntervEty 10 }

--
--  enHP-STS7DaysTab
--
        enHP-STS7DaysTab  OBJECT-TYPE
            SYNTAX  SEQUENCE OF  EnHP-STS7DaysEty
            ACCESS  not-accessible
            STATUS  mandatory
            DESCRIPTION
                "The Ethernet B3 7 days table."
            ::= { enetPerfDisplayTable 3 }

        enHP-STS7DaysEty  OBJECT-TYPE
            SYNTAX  EnHP-STS7DaysEty
            ACCESS  not-accessible
            STATUS  mandatory
            DESCRIPTION
                "An entry in the Ethernet B3 7 days table."
            INDEX { enHpSts7DaysUnit , enHpSts7DaysPort ,
                    enHpSts7DaysChannel , enHpSts7DaysNumber }
            ::= { enHP-STS7DaysTab 1 }

        EnHP-STS7DaysEty ::= SEQUENCE {
            enHpSts7DaysUnit            UnitID,
            enHpSts7DaysPort            VcgPortNum,
            enHpSts7DaysChannel         ChannelNum,
            enHpSts7DaysNumber          INTEGER (1..7),
            enHpSts7DaysDate            DisplayString (SIZE (0..255)),
            enHpSts7DaysEBs             Counter,
            enHpSts7DaysBBEs            Counter,
            enHpSts7DaysESs             Counter,
            enHpSts7DaysBESs            Counter,
            enHpSts7DaysSESs            Counter,
            enHpSts7DaysUASs            Counter
        }

        enHpSts7DaysUnit  OBJECT-TYPE
            SYNTAX  UnitID
            ACCESS  read-only
            STATUS  mandatory
            DESCRIPTION
            "unit 1 to 4."
            ::= { enHP-STS7DaysEty 1 }

        enHpSts7DaysPort  OBJECT-TYPE
            SYNTAX  VcgPortNum
            ACCESS  read-only
            STATUS  mandatory
            DESCRIPTION
                "vcg port index: wan1~wan9"
            ::= { enHP-STS7DaysEty 2 }

        enHpSts7DaysChannel  OBJECT-TYPE
            SYNTAX  ChannelNum
            ACCESS  read-only
            STATUS  mandatory
            DESCRIPTION
                "Channel index"
            ::= { enHP-STS7DaysEty 3 }

        enHpSts7DaysNumber  OBJECT-TYPE
            SYNTAX  INTEGER (1..7)
            ACCESS  read-only
            STATUS  mandatory
            DESCRIPTION
                "A number between 1 and 7"
            ::= { enHP-STS7DaysEty 4 }

        enHpSts7DaysDate  OBJECT-TYPE
            SYNTAX  DisplayString (SIZE (0..255))
            ACCESS  read-only
            STATUS  mandatory
            DESCRIPTION
                "Date"
            ::= { enHP-STS7DaysEty 5 }

        enHpSts7DaysEBs  OBJECT-TYPE
            SYNTAX  Counter
            ACCESS  read-only
            STATUS  mandatory
            DESCRIPTION
                "B3(BIP-8) Error Block"
            ::= { enHP-STS7DaysEty 6 }

        enHpSts7DaysBBEs  OBJECT-TYPE
            SYNTAX  Counter
            ACCESS  read-only
            STATUS  mandatory
            DESCRIPTION
                "B3(BIP-8) Background Block Error"
            ::= { enHP-STS7DaysEty 7 }

        enHpSts7DaysESs  OBJECT-TYPE
            SYNTAX  Counter
            ACCESS  read-only
            STATUS  mandatory
            DESCRIPTION
                "B3(BIP-8) Error Second"
            ::= { enHP-STS7DaysEty 8 }

        enHpSts7DaysBESs  OBJECT-TYPE
            SYNTAX  Counter
            ACCESS  read-only
            STATUS  mandatory
            DESCRIPTION
                "B3(BIP-8) Background Error Second"
            ::= { enHP-STS7DaysEty 9 }

        enHpSts7DaysSESs  OBJECT-TYPE
            SYNTAX  Counter
            ACCESS  read-only
            STATUS  mandatory
            DESCRIPTION
                "B3(BIP-8) Severly Error Second"
            ::= { enHP-STS7DaysEty 10 }

        enHpSts7DaysUASs  OBJECT-TYPE
            SYNTAX  Counter
            ACCESS  read-only
            STATUS  mandatory
            DESCRIPTION
                "B3(BIP-8) Unavailable Second"
            ::= { enHP-STS7DaysEty 11 }

--
--  enHP-STSTotalTab
--
        enHP-STSTotalTab  OBJECT-TYPE
            SYNTAX  SEQUENCE OF  EnHP-STSTotalEty
            ACCESS  not-accessible
            STATUS  mandatory
            DESCRIPTION
                "The Ethernet B3 Total table."
            ::= { enetPerfDisplayTable 4 }

        enHP-STSTotalEty  OBJECT-TYPE
            SYNTAX  EnHP-STSTotalEty
            ACCESS  not-accessible
            STATUS  mandatory
            DESCRIPTION
                "An entry in the Ethernet B3 Total table."
            INDEX { enHpStsTotalUnit , enHpStsTotalPort ,
                    enHpStsTotalChannel }
            ::= { enHP-STSTotalTab 1 }

        EnHP-STSTotalEty ::= SEQUENCE {
            enHpStsTotalUnit            UnitID,
            enHpStsTotalPort            VcgPortNum,
            enHpStsTotalChannel         ChannelNum,
            enHpStsTotalEBs             Counter,
            enHpStsTotalBBEs            Counter,
            enHpStsTotalESs             Counter,
            enHpStsTotalBESs            Counter,
            enHpStsTotalSESs            Counter,
            enHpStsTotalUASs            Counter
        }

        enHpStsTotalUnit  OBJECT-TYPE
            SYNTAX  UnitID
            ACCESS  read-only
            STATUS  mandatory
            DESCRIPTION
            "unit 1 to 4."
            ::= { enHP-STSTotalEty 1 }

        enHpStsTotalPort  OBJECT-TYPE
            SYNTAX  VcgPortNum
            ACCESS  read-only
            STATUS  mandatory
            DESCRIPTION
                "vcg port index: wan1~wan9"
            ::= { enHP-STSTotalEty 2 }

        enHpStsTotalChannel  OBJECT-TYPE
            SYNTAX  ChannelNum
            ACCESS  read-only
            STATUS  mandatory
            DESCRIPTION
                "Channel index"
            ::= { enHP-STSTotalEty 3 }

        enHpStsTotalEBs  OBJECT-TYPE
            SYNTAX  Counter
            ACCESS  read-only
            STATUS  mandatory
            DESCRIPTION
                "B3(BIP-8) Error Block"
            ::= { enHP-STSTotalEty 4 }

        enHpStsTotalBBEs  OBJECT-TYPE
            SYNTAX  Counter
            ACCESS  read-only
            STATUS  mandatory
            DESCRIPTION
                "B3(BIP-8) Background Block Error"
            ::= { enHP-STSTotalEty 5 }

        enHpStsTotalESs  OBJECT-TYPE
            SYNTAX  Counter
            ACCESS  read-only
            STATUS  mandatory
            DESCRIPTION
                "B3(BIP-8) Error Second"
            ::= { enHP-STSTotalEty 6 }

        enHpStsTotalBESs  OBJECT-TYPE
            SYNTAX  Counter
            ACCESS  read-only
            STATUS  mandatory
            DESCRIPTION
                "B3(BIP-8) Background Error Second"
            ::= { enHP-STSTotalEty 7 }

        enHpStsTotalSESs  OBJECT-TYPE
            SYNTAX  Counter
            ACCESS  read-only
            STATUS  mandatory
            DESCRIPTION
                "B3(BIP-8) Severly Error Second"
            ::= { enHP-STSTotalEty 8 }

        enHpStsTotalUASs  OBJECT-TYPE
            SYNTAX  Counter
            ACCESS  read-only
            STATUS  mandatory
            DESCRIPTION
                "B3(BIP-8) Unavailable Second"
            ::= { enHP-STSTotalEty 9 }

--
--  enFarEndHP-STSCurrTab
--
        enFarEndHP-STSCurrTab  OBJECT-TYPE
            SYNTAX  SEQUENCE OF  EnFarEndHP-STSCurrEty
            ACCESS  not-accessible
            STATUS  mandatory
            DESCRIPTION
                "The Ethernet HP-REI/REI-P Current table."
            ::= { enetPerfDisplayTable 5 }

        enFarEndHP-STSCurrEty  OBJECT-TYPE
            SYNTAX  EnFarEndHP-STSCurrEty
            ACCESS  not-accessible
            STATUS  mandatory
            DESCRIPTION
                "An entry in the Ethernet HP-REI/REI-P Current table."
            INDEX { enFrHpStsCurrUnit , enFrHpStsCurrPort ,
                    enFrHpStsCurrChannel }
            ::= { enFarEndHP-STSCurrTab 1 }

        EnFarEndHP-STSCurrEty ::= SEQUENCE {
            enFrHpStsCurrUnit           UnitID,
            enFrHpStsCurrPort           VcgPortNum,
            enFrHpStsCurrChannel        ChannelNum,
            enFrHpStsCurrEBs            Counter,
            enFrHpStsCurrBBEs           Counter,
            enFrHpStsCurrESs            Counter,
            enFrHpStsCurrBESs           Counter,
            enFrHpStsCurrSESs           Counter,
            enFrHpStsCurrUASs           Counter,
            enFrHpStsCurr24HValid15M    Counter,
            enFrHpStsCurr7DayValidDay   Counter,
            enFrHpStsCurr15MTimeElaps   Counter,
            enFrHpStsCurrDayValid15M    Counter
        }

        enFrHpStsCurrUnit  OBJECT-TYPE
            SYNTAX  UnitID
            ACCESS  read-only
            STATUS  mandatory
            DESCRIPTION
            "unit 1 to 4."
            ::= { enFarEndHP-STSCurrEty 1 }

        enFrHpStsCurrPort  OBJECT-TYPE
            SYNTAX  VcgPortNum
            ACCESS  read-only
            STATUS  mandatory
            DESCRIPTION
                "vcg port index: wan1~wan9"
            ::= { enFarEndHP-STSCurrEty 2 }

        enFrHpStsCurrChannel  OBJECT-TYPE
            SYNTAX  ChannelNum
            ACCESS  read-only
            STATUS  mandatory
            DESCRIPTION
                "Channel index"
            ::= { enFarEndHP-STSCurrEty 3 }

        enFrHpStsCurrEBs  OBJECT-TYPE
            SYNTAX  Counter
            ACCESS  read-only
            STATUS  mandatory
            DESCRIPTION
                "HP-REI/REI-P(BIP-8) Error Block"
            ::= { enFarEndHP-STSCurrEty 4 }

        enFrHpStsCurrBBEs  OBJECT-TYPE
            SYNTAX  Counter
            ACCESS  read-only
            STATUS  mandatory
            DESCRIPTION
                "HP-REI/REI-P(BIP-8) Background Block Error"
            ::= { enFarEndHP-STSCurrEty 5 }

        enFrHpStsCurrESs  OBJECT-TYPE
            SYNTAX  Counter
            ACCESS  read-only
            STATUS  mandatory
            DESCRIPTION
                "HP-REI/REI-P(BIP-8) Error Second"
            ::= { enFarEndHP-STSCurrEty 6 }

        enFrHpStsCurrBESs  OBJECT-TYPE
            SYNTAX  Counter
            ACCESS  read-only
            STATUS  mandatory
            DESCRIPTION
                "HP-REI/REI-P(BIP-8) Background Error Second"
            ::= { enFarEndHP-STSCurrEty 7 }

        enFrHpStsCurrSESs  OBJECT-TYPE
            SYNTAX  Counter
            ACCESS  read-only
            STATUS  mandatory
            DESCRIPTION
                "HP-REI/REI-P(BIP-8) Severly Error Second"
            ::= { enFarEndHP-STSCurrEty 8 }

        enFrHpStsCurrUASs  OBJECT-TYPE
            SYNTAX  Counter
            ACCESS  read-only
            STATUS  mandatory
            DESCRIPTION
                "HP-REI/REI-P(BIP-8) Unavailable Second"
            ::= { enFarEndHP-STSCurrEty 9 }

        enFrHpStsCurr24HValid15M  OBJECT-TYPE
            SYNTAX  Counter
            ACCESS  read-only
            STATUS  mandatory
            DESCRIPTION
                "HP-REI/REI-P(BIP-8) Valid 15-Min Interval"
            ::= { enFarEndHP-STSCurrEty 10 }

        enFrHpStsCurr7DayValidDay  OBJECT-TYPE
            SYNTAX  Counter
            ACCESS  read-only
            STATUS  mandatory
            DESCRIPTION
                "HP-REI/REI-P(BIP-8) Valid 1-Day Interval"
            ::= { enFarEndHP-STSCurrEty 11 }

        enFrHpStsCurr15MTimeElaps  OBJECT-TYPE
            SYNTAX  Counter
            ACCESS  read-only
            STATUS  mandatory
            DESCRIPTION
                "HP-REI/REI-P(BIP-8) Current 15-MIN Time Elapsed"
            ::= { enFarEndHP-STSCurrEty 12 }

        enFrHpStsCurrDayValid15M  OBJECT-TYPE
            SYNTAX  Counter
            ACCESS  read-only
            STATUS  mandatory
            DESCRIPTION
                "HP-REI/REI-P(BIP-8) Current Day Time Elapsed"
            ::= { enFarEndHP-STSCurrEty 13 }

--
--  enFarEndHP-STSIntervTab Interval Table
--
        enFarEndHP-STSIntervTab  OBJECT-TYPE
            SYNTAX  SEQUENCE OF  EnFarEndHP-STSIntervEty
            ACCESS  not-accessible
            STATUS  mandatory
            DESCRIPTION
                "The Ethernet HP-REI/REI-P Interval table."
            ::= { enetPerfDisplayTable 6 }

        enFarEndHP-STSIntervEty  OBJECT-TYPE
            SYNTAX  EnFarEndHP-STSIntervEty
            ACCESS  not-accessible
            STATUS  mandatory
            DESCRIPTION
                "An entry in the Ethernet HP-REI/REI-P Interval table."
            INDEX { enFrHpStsIntervUnit , enFrHpStsIntervPort ,
                    enFrHpStsIntervChannel , enFrHpStsIntervNumber }
            ::= { enFarEndHP-STSIntervTab 1 }

        EnFarEndHP-STSIntervEty ::= SEQUENCE {
            enFrHpStsIntervUnit         UnitID,
            enFrHpStsIntervPort         VcgPortNum,
            enFrHpStsIntervChannel      ChannelNum,
            enFrHpStsIntervNumber       INTEGER (1..96),
            enFrHpStsIntervEBs          Counter,
            enFrHpStsIntervBBEs         Counter,
            enFrHpStsIntervESs          Counter,
            enFrHpStsIntervBESs         Counter,
            enFrHpStsIntervSESs         Counter,
            enFrHpStsIntervUASs         Counter
        }

        enFrHpStsIntervUnit  OBJECT-TYPE
            SYNTAX  UnitID
            ACCESS  read-only
            STATUS  mandatory
            DESCRIPTION
            "unit 1 to 4."
            ::= { enFarEndHP-STSIntervEty 1 }

        enFrHpStsIntervPort  OBJECT-TYPE
            SYNTAX  VcgPortNum
            ACCESS  read-only
            STATUS  mandatory
            DESCRIPTION
                "vcg port index: wan1~wan9"
            ::= { enFarEndHP-STSIntervEty 2 }

        enFrHpStsIntervChannel  OBJECT-TYPE
            SYNTAX  ChannelNum
            ACCESS  read-only
            STATUS  mandatory
            DESCRIPTION
                "Channel index"
            ::= { enFarEndHP-STSIntervEty 3 }

        enFrHpStsIntervNumber  OBJECT-TYPE
            SYNTAX  INTEGER (1..96)
            ACCESS  read-only
            STATUS  mandatory
            DESCRIPTION
                "A number between 1 and 96"
            ::= { enFarEndHP-STSIntervEty 4 }

        enFrHpStsIntervEBs  OBJECT-TYPE
            SYNTAX  Counter
            ACCESS  read-only
            STATUS  mandatory
            DESCRIPTION
                "HP-REI/REI-P(BIP-8) Error Block"
            ::= { enFarEndHP-STSIntervEty 5 }

        enFrHpStsIntervBBEs  OBJECT-TYPE
            SYNTAX  Counter
            ACCESS  read-only
            STATUS  mandatory
            DESCRIPTION
                "HP-REI/REI-P(BIP-8) Background Block Error"
            ::= { enFarEndHP-STSIntervEty 6 }

        enFrHpStsIntervESs  OBJECT-TYPE
            SYNTAX  Counter
            ACCESS  read-only
            STATUS  mandatory
            DESCRIPTION
                "HP-REI/REI-P(BIP-8) Error Second"
            ::= { enFarEndHP-STSIntervEty 7 }

        enFrHpStsIntervBESs  OBJECT-TYPE
            SYNTAX  Counter
            ACCESS  read-only
            STATUS  mandatory
            DESCRIPTION
                "HP-REI/REI-P(BIP-8) Background Error Second"
            ::= { enFarEndHP-STSIntervEty 8 }

        enFrHpStsIntervSESs  OBJECT-TYPE
            SYNTAX  Counter
            ACCESS  read-only
            STATUS  mandatory
            DESCRIPTION
                "HP-REI/REI-P(BIP-8) Severly Error Second"
            ::= { enFarEndHP-STSIntervEty 9 }

        enFrHpStsIntervUASs  OBJECT-TYPE
            SYNTAX  Counter
            ACCESS  read-only
            STATUS  mandatory
            DESCRIPTION
                "HP-REI/REI-P(BIP-8) Unavailable Second"
            ::= { enFarEndHP-STSIntervEty 10 }

--
--  enFarEndHP-STS7DaysTab
--
        enFarEndHP-STS7DaysTab  OBJECT-TYPE
            SYNTAX  SEQUENCE OF  EnFarEndHP-STS7DaysEty
            ACCESS  not-accessible
            STATUS  mandatory
            DESCRIPTION
                "The Ethernet HP-REI/REI-P 7 days table."
            ::= { enetPerfDisplayTable 7 }

        enFarEndHP-STS7DaysEty  OBJECT-TYPE
            SYNTAX  EnFarEndHP-STS7DaysEty
            ACCESS  not-accessible
            STATUS  mandatory
            DESCRIPTION
                "An entry in the Ethernet HP-REI/REI-P 7 days table."
            INDEX { enFrHpSts7DaysUnit , enFrHpSts7DaysPort ,
                    enFrHpSts7DaysChannel , enFrHpSts7DaysNumber }
            ::= { enFarEndHP-STS7DaysTab 1 }

        EnFarEndHP-STS7DaysEty ::= SEQUENCE {
            enFrHpSts7DaysUnit          UnitID,
            enFrHpSts7DaysPort          VcgPortNum,
            enFrHpSts7DaysChannel       ChannelNum,
            enFrHpSts7DaysNumber        INTEGER (1..7),
            enFrHpSts7DaysDate          DisplayString (SIZE (0..255)),
            enFrHpSts7DaysEBs           Counter,
            enFrHpSts7DaysBBEs          Counter,
            enFrHpSts7DaysESs           Counter,
            enFrHpSts7DaysBESs          Counter,
            enFrHpSts7DaysSESs          Counter,
            enFrHpSts7DaysUASs          Counter
        }

        enFrHpSts7DaysUnit  OBJECT-TYPE
            SYNTAX  UnitID
            ACCESS  read-only
            STATUS  mandatory
            DESCRIPTION
            "unit 1 to 4."
            ::= { enFarEndHP-STS7DaysEty 1 }

        enFrHpSts7DaysPort  OBJECT-TYPE
            SYNTAX  VcgPortNum
            ACCESS  read-only
            STATUS  mandatory
            DESCRIPTION
                "vcg port index: wan1~wan9"
            ::= { enFarEndHP-STS7DaysEty 2 }

        enFrHpSts7DaysChannel  OBJECT-TYPE
            SYNTAX  ChannelNum
            ACCESS  read-only
            STATUS  mandatory
            DESCRIPTION
                "Channel index"
            ::= { enFarEndHP-STS7DaysEty 3 }

        enFrHpSts7DaysNumber  OBJECT-TYPE
            SYNTAX  INTEGER (1..7)
            ACCESS  read-only
            STATUS  mandatory
            DESCRIPTION
                "A number between 1 and 7"
            ::= { enFarEndHP-STS7DaysEty 4 }

        enFrHpSts7DaysDate  OBJECT-TYPE
            SYNTAX  DisplayString (SIZE (0..255))
            ACCESS  read-only
            STATUS  mandatory
            DESCRIPTION
                "Date"
            ::= { enFarEndHP-STS7DaysEty 5 }

        enFrHpSts7DaysEBs  OBJECT-TYPE
            SYNTAX  Counter
            ACCESS  read-only
            STATUS  mandatory
            DESCRIPTION
                "HP-REI/REI-P(BIP-8) Error Block"
            ::= { enFarEndHP-STS7DaysEty 6 }

        enFrHpSts7DaysBBEs  OBJECT-TYPE
            SYNTAX  Counter
            ACCESS  read-only
            STATUS  mandatory
            DESCRIPTION
                "HP-REI/REI-P(BIP-8) Background Block Error"
            ::= { enFarEndHP-STS7DaysEty 7 }

        enFrHpSts7DaysESs  OBJECT-TYPE
            SYNTAX  Counter
            ACCESS  read-only
            STATUS  mandatory
            DESCRIPTION
                "HP-REI/REI-P(BIP-8) Error Second"
            ::= { enFarEndHP-STS7DaysEty 8 }

        enFrHpSts7DaysBESs  OBJECT-TYPE
            SYNTAX  Counter
            ACCESS  read-only
            STATUS  mandatory
            DESCRIPTION
                "HP-REI/REI-P(BIP-8) Background Error Second"
            ::= { enFarEndHP-STS7DaysEty 9 }

        enFrHpSts7DaysSESs  OBJECT-TYPE
            SYNTAX  Counter
            ACCESS  read-only
            STATUS  mandatory
            DESCRIPTION
                "HP-REI/REI-P(BIP-8) Severly Error Second"
            ::= { enFarEndHP-STS7DaysEty 10 }

        enFrHpSts7DaysUASs  OBJECT-TYPE
            SYNTAX  Counter
            ACCESS  read-only
            STATUS  mandatory
            DESCRIPTION
                "HP-REI/REI-P(BIP-8) Unavailable Second"
            ::= { enFarEndHP-STS7DaysEty 11 }

--
--  enFarEndHP-STSTotalTab
--
        enFarEndHP-STSTotalTab  OBJECT-TYPE
            SYNTAX  SEQUENCE OF  EnFarEndHP-STSTotalEty
            ACCESS  not-accessible
            STATUS  mandatory
            DESCRIPTION
                "The Ethernet HP-REI/REI-P Total table."
            ::= { enetPerfDisplayTable 8 }

        enFarEndHP-STSTotalEty  OBJECT-TYPE
            SYNTAX  EnFarEndHP-STSTotalEty
            ACCESS  not-accessible
            STATUS  mandatory
            DESCRIPTION
                "An entry in the Ethernet HP-REI/REI-P Total table."
            INDEX { enFrHpStsTotalUnit , enFrHpStsTotalPort ,
                    enFrHpStsTotalChannel }
            ::= { enFarEndHP-STSTotalTab 1 }

        EnFarEndHP-STSTotalEty ::= SEQUENCE {
            enFrHpStsTotalUnit          UnitID,
            enFrHpStsTotalPort          VcgPortNum,
            enFrHpStsTotalChannel       ChannelNum,
            enFrHpStsTotalEBs           Counter,
            enFrHpStsTotalBBEs          Counter,
            enFrHpStsTotalESs           Counter,
            enFrHpStsTotalBESs          Counter,
            enFrHpStsTotalSESs          Counter,
            enFrHpStsTotalUASs          Counter
        }

        enFrHpStsTotalUnit  OBJECT-TYPE
            SYNTAX  UnitID
            ACCESS  read-only
            STATUS  mandatory
            DESCRIPTION
            "unit 1 to 4."
            ::= { enFarEndHP-STSTotalEty 1 }

        enFrHpStsTotalPort  OBJECT-TYPE
            SYNTAX  VcgPortNum
            ACCESS  read-only
            STATUS  mandatory
            DESCRIPTION
                "vcg port index: wan1~wan9"
            ::= { enFarEndHP-STSTotalEty 2 }

        enFrHpStsTotalChannel  OBJECT-TYPE
            SYNTAX  ChannelNum
            ACCESS  read-only
            STATUS  mandatory
            DESCRIPTION
                "Channel index"
            ::= { enFarEndHP-STSTotalEty 3 }

        enFrHpStsTotalEBs  OBJECT-TYPE
            SYNTAX  Counter
            ACCESS  read-only
            STATUS  mandatory
            DESCRIPTION
                "HP-REI/REI-P(BIP-8) Error Block"
            ::= { enFarEndHP-STSTotalEty 4 }

        enFrHpStsTotalBBEs  OBJECT-TYPE
            SYNTAX  Counter
            ACCESS  read-only
            STATUS  mandatory
            DESCRIPTION
                "HP-REI/REI-P(BIP-8) Background Block Error"
            ::= { enFarEndHP-STSTotalEty 5 }

        enFrHpStsTotalESs  OBJECT-TYPE
            SYNTAX  Counter
            ACCESS  read-only
            STATUS  mandatory
            DESCRIPTION
                "HP-REI/REI-P(BIP-8) Error Second"
            ::= { enFarEndHP-STSTotalEty 6 }

        enFrHpStsTotalBESs  OBJECT-TYPE
            SYNTAX  Counter
            ACCESS  read-only
            STATUS  mandatory
            DESCRIPTION
                "HP-REI/REI-P(BIP-8) Background Error Second"
            ::= { enFarEndHP-STSTotalEty 7 }

        enFrHpStsTotalSESs  OBJECT-TYPE
            SYNTAX  Counter
            ACCESS  read-only
            STATUS  mandatory
            DESCRIPTION
                "HP-REI/REI-P(BIP-8) Severly Error Second"
            ::= { enFarEndHP-STSTotalEty 8 }

        enFrHpStsTotalUASs  OBJECT-TYPE
            SYNTAX  Counter
            ACCESS  read-only
            STATUS  mandatory
            DESCRIPTION
                "HP-REI/REI-P(BIP-8) Unavailable Second"
            ::= { enFarEndHP-STSTotalEty 9 }

--
--  enLP-VTCurrTab
--
        enLP-VTCurrTab  OBJECT-TYPE
            SYNTAX  SEQUENCE OF  EnLP-VTCurrEty
            ACCESS  not-accessible
            STATUS  mandatory
            DESCRIPTION
                "The Ethernet LP-BIP Current table."
            ::= { enetPerfDisplayTable 9 }

        enLP-VTCurrEty  OBJECT-TYPE
            SYNTAX  EnLP-VTCurrEty
            ACCESS  not-accessible
            STATUS  mandatory
            DESCRIPTION
                "An entry in the Ethernet LP-BIP Current table."
            INDEX { enLpVtCurrUnit , enLpVtCurrPort ,
                    enLpVtCurrChannel }
            ::= { enLP-VTCurrTab 1 }

        EnLP-VTCurrEty ::= SEQUENCE {
            enLpVtCurrUnit              UnitID,
            enLpVtCurrPort              VcgPortNum,
            enLpVtCurrChannel           ChannelNum,
            enLpVtCurrEBs               Counter,
            enLpVtCurrBBEs              Counter,
            enLpVtCurrESs               Counter,
            enLpVtCurrBESs              Counter,
            enLpVtCurrSESs              Counter,
            enLpVtCurrUASs              Counter,
            enLpVtCurr24HValid15M       Counter,
            enLpVtCurr7DayValidDay      Counter,
            enLpVtCurr15MTimeElaps      Counter,
            enLpVtCurrDayValid15M       Counter
        }

        enLpVtCurrUnit  OBJECT-TYPE
            SYNTAX  UnitID
            ACCESS  read-only
            STATUS  mandatory
            DESCRIPTION
            "unit 1 to 4."
            ::= { enLP-VTCurrEty 1 }

        enLpVtCurrPort  OBJECT-TYPE
            SYNTAX  VcgPortNum
            ACCESS  read-only
            STATUS  mandatory
            DESCRIPTION
                "vcg port index: wan1~wan9"
            ::= { enLP-VTCurrEty 2 }

        enLpVtCurrChannel  OBJECT-TYPE
            SYNTAX  ChannelNum
            ACCESS  read-only
            STATUS  mandatory
            DESCRIPTION
                "Channel index"
            ::= { enLP-VTCurrEty 3 }

        enLpVtCurrEBs  OBJECT-TYPE
            SYNTAX  Counter
            ACCESS  read-only
            STATUS  mandatory
            DESCRIPTION
                "LP-BIP Error Block"
            ::= { enLP-VTCurrEty 4 }

        enLpVtCurrBBEs  OBJECT-TYPE
            SYNTAX  Counter
            ACCESS  read-only
            STATUS  mandatory
            DESCRIPTION
                "LP-BIP Background Block Error"
            ::= { enLP-VTCurrEty 5 }

        enLpVtCurrESs  OBJECT-TYPE
            SYNTAX  Counter
            ACCESS  read-only
            STATUS  mandatory
            DESCRIPTION
                "LP-BIP Error Second"
            ::= { enLP-VTCurrEty 6 }

        enLpVtCurrBESs  OBJECT-TYPE
            SYNTAX  Counter
            ACCESS  read-only
            STATUS  mandatory
            DESCRIPTION
                "LP-BIP Background Error Second"
            ::= { enLP-VTCurrEty 7 }

        enLpVtCurrSESs  OBJECT-TYPE
            SYNTAX  Counter
            ACCESS  read-only
            STATUS  mandatory
            DESCRIPTION
                "LP-BIP Severly Error Second"
            ::= { enLP-VTCurrEty 8 }

        enLpVtCurrUASs  OBJECT-TYPE
            SYNTAX  Counter
            ACCESS  read-only
            STATUS  mandatory
            DESCRIPTION
                "LP-BIP Unavailable Second"
            ::= { enLP-VTCurrEty 9 }

        enLpVtCurr24HValid15M  OBJECT-TYPE
            SYNTAX  Counter
            ACCESS  read-only
            STATUS  mandatory
            DESCRIPTION
                "LP-BIP Valid 15-Min Interval"
            ::= { enLP-VTCurrEty 10 }

        enLpVtCurr7DayValidDay  OBJECT-TYPE
            SYNTAX  Counter
            ACCESS  read-only
            STATUS  mandatory
            DESCRIPTION
                "LP-BIP Valid 1-Day Interval"
            ::= { enLP-VTCurrEty 11 }

        enLpVtCurr15MTimeElaps  OBJECT-TYPE
            SYNTAX  Counter
            ACCESS  read-only
            STATUS  mandatory
            DESCRIPTION
                "LP-BIP Current 15-MIN Time Elapsed"
            ::= { enLP-VTCurrEty 12 }

        enLpVtCurrDayValid15M  OBJECT-TYPE
            SYNTAX  Counter
            ACCESS  read-only
            STATUS  mandatory
            DESCRIPTION
                "LP-BIP Current Day Time Elapsed"
            ::= { enLP-VTCurrEty 13 }

--
--  enLP-VTIntervTab
--
        enLP-VTIntervTab  OBJECT-TYPE
            SYNTAX  SEQUENCE OF  EnLP-VTIntervEty
            ACCESS  not-accessible
            STATUS  mandatory
            DESCRIPTION
                "The Ethernet LP-BIP Interval table."
            ::= { enetPerfDisplayTable 10 }

        enLP-VTIntervEty  OBJECT-TYPE
            SYNTAX  EnLP-VTIntervEty
            ACCESS  not-accessible
            STATUS  mandatory
            DESCRIPTION
                "An entry in the Ethernet LP-BIP Interval table."
            INDEX { enLpVtIntervUnit , enLpVtIntervPort ,
                    enLpVtIntervChannel , enLpVtIntervNumber }
            ::= { enLP-VTIntervTab 1 }

        EnLP-VTIntervEty ::= SEQUENCE {
            enLpVtIntervUnit            UnitID,
            enLpVtIntervPort            VcgPortNum,
            enLpVtIntervChannel         ChannelNum,
            enLpVtIntervNumber          INTEGER (1..96),
            enLpVtIntervEBs             Counter,
            enLpVtIntervBBEs            Counter,
            enLpVtIntervESs             Counter,
            enLpVtIntervBESs            Counter,
            enLpVtIntervSESs            Counter,
            enLpVtIntervUASs            Counter
        }

        enLpVtIntervUnit  OBJECT-TYPE
            SYNTAX  UnitID
            ACCESS  read-only
            STATUS  mandatory
            DESCRIPTION
            "unit 1 to 4."
            ::= { enLP-VTIntervEty 1 }

        enLpVtIntervPort  OBJECT-TYPE
            SYNTAX  VcgPortNum
            ACCESS  read-only
            STATUS  mandatory
            DESCRIPTION
                "vcg port index: wan1~wan9"
            ::= { enLP-VTIntervEty 2 }

        enLpVtIntervChannel  OBJECT-TYPE
            SYNTAX  ChannelNum
            ACCESS  read-only
            STATUS  mandatory
            DESCRIPTION
                "Channel index"
            ::= { enLP-VTIntervEty 3 }

        enLpVtIntervNumber  OBJECT-TYPE
            SYNTAX  INTEGER (1..96)
            ACCESS  read-only
            STATUS  mandatory
            DESCRIPTION
                "A number between 1 and 96"
            ::= { enLP-VTIntervEty 4 }

        enLpVtIntervEBs  OBJECT-TYPE
            SYNTAX  Counter
            ACCESS  read-only
            STATUS  mandatory
            DESCRIPTION
                "LP-BIP Error Block"
            ::= { enLP-VTIntervEty 5 }

        enLpVtIntervBBEs  OBJECT-TYPE
            SYNTAX  Counter
            ACCESS  read-only
            STATUS  mandatory
            DESCRIPTION
                "LP-BIP Background Block Error"
            ::= { enLP-VTIntervEty 6 }

        enLpVtIntervESs  OBJECT-TYPE
            SYNTAX  Counter
            ACCESS  read-only
            STATUS  mandatory
            DESCRIPTION
                "LP-BIP Error Second"
            ::= { enLP-VTIntervEty 7 }

        enLpVtIntervBESs  OBJECT-TYPE
            SYNTAX  Counter
            ACCESS  read-only
            STATUS  mandatory
            DESCRIPTION
                "LP-BIP Background Error Second"
            ::= { enLP-VTIntervEty 8 }

        enLpVtIntervSESs  OBJECT-TYPE
            SYNTAX  Counter
            ACCESS  read-only
            STATUS  mandatory
            DESCRIPTION
                "LP-BIP Severly Error Second"
            ::= { enLP-VTIntervEty 9 }

        enLpVtIntervUASs  OBJECT-TYPE
            SYNTAX  Counter
            ACCESS  read-only
            STATUS  mandatory
            DESCRIPTION
                "LP-BIP Unavailable Second"
            ::= { enLP-VTIntervEty 10 }

--
--  enLP-VT7DaysTab
--
        enLP-VT7DaysTab  OBJECT-TYPE
            SYNTAX  SEQUENCE OF  EnLP-VT7DaysEty
            ACCESS  not-accessible
            STATUS  mandatory
            DESCRIPTION
                "The Ethernet LP-BIP 7 days table."
            ::= { enetPerfDisplayTable 11 }

        enLP-VT7DaysEty  OBJECT-TYPE
            SYNTAX  EnLP-VT7DaysEty
            ACCESS  not-accessible
            STATUS  mandatory
            DESCRIPTION
                "An entry in the Ethernet LP-BIP 7 days table."
            INDEX { enLpVt7DaysUnit , enLpVt7DaysPort ,
                    enLpVt7DaysChannel , enLpVt7DaysNumber }
            ::= { enLP-VT7DaysTab 1 }

        EnLP-VT7DaysEty ::= SEQUENCE {
            enLpVt7DaysUnit             UnitID,
            enLpVt7DaysPort             VcgPortNum,
            enLpVt7DaysChannel          ChannelNum,
            enLpVt7DaysNumber           INTEGER (1..7),
            enLpVt7DaysDate             DisplayString (SIZE (0..255)),
            enLpVt7DaysEBs              Counter,
            enLpVt7DaysBBEs             Counter,
            enLpVt7DaysESs              Counter,
            enLpVt7DaysBESs             Counter,
            enLpVt7DaysSESs             Counter,
            enLpVt7DaysUASs             Counter
        }

        enLpVt7DaysUnit  OBJECT-TYPE
            SYNTAX  UnitID
            ACCESS  read-only
            STATUS  mandatory
            DESCRIPTION
            "unit 1 to 4."
            ::= { enLP-VT7DaysEty 1 }

        enLpVt7DaysPort  OBJECT-TYPE
            SYNTAX  VcgPortNum
            ACCESS  read-only
            STATUS  mandatory
            DESCRIPTION
                "vcg port index: wan1~wan9"
            ::= { enLP-VT7DaysEty 2 }

        enLpVt7DaysChannel  OBJECT-TYPE
            SYNTAX  ChannelNum
            ACCESS  read-only
            STATUS  mandatory
            DESCRIPTION
                "Channel index"
            ::= { enLP-VT7DaysEty 3 }

        enLpVt7DaysNumber  OBJECT-TYPE
            SYNTAX  INTEGER (1..7)
            ACCESS  read-only
            STATUS  mandatory
            DESCRIPTION
                "A number between 1 and 7"
            ::= { enLP-VT7DaysEty 4 }

        enLpVt7DaysDate  OBJECT-TYPE
            SYNTAX  DisplayString (SIZE (0..255))
            ACCESS  read-only
            STATUS  mandatory
            DESCRIPTION
                "Date"
            ::= { enLP-VT7DaysEty 5 }

        enLpVt7DaysEBs  OBJECT-TYPE
            SYNTAX  Counter
            ACCESS  read-only
            STATUS  mandatory
            DESCRIPTION
                "LP-BIP Error Block"
            ::= { enLP-VT7DaysEty 6 }

        enLpVt7DaysBBEs  OBJECT-TYPE
            SYNTAX  Counter
            ACCESS  read-only
            STATUS  mandatory
            DESCRIPTION
                "LP-BIP Background Block Error"
            ::= { enLP-VT7DaysEty 7 }

        enLpVt7DaysESs  OBJECT-TYPE
            SYNTAX  Counter
            ACCESS  read-only
            STATUS  mandatory
            DESCRIPTION
                "LP-BIP Error Second"
            ::= { enLP-VT7DaysEty 8 }

        enLpVt7DaysBESs  OBJECT-TYPE
            SYNTAX  Counter
            ACCESS  read-only
            STATUS  mandatory
            DESCRIPTION
                "LP-BIP Background Error Second"
            ::= { enLP-VT7DaysEty 9 }

        enLpVt7DaysSESs  OBJECT-TYPE
            SYNTAX  Counter
            ACCESS  read-only
            STATUS  mandatory
            DESCRIPTION
                "LP-BIP Severly Error Second"
            ::= { enLP-VT7DaysEty 10 }

        enLpVt7DaysUASs  OBJECT-TYPE
            SYNTAX  Counter
            ACCESS  read-only
            STATUS  mandatory
            DESCRIPTION
                "LP-BIP Unavailable Second"
            ::= { enLP-VT7DaysEty 11 }

--
--  enLP-VTTotalTab
--
        enLP-VTTotalTab  OBJECT-TYPE
            SYNTAX  SEQUENCE OF  EnLP-VTTotalEty
            ACCESS  not-accessible
            STATUS  mandatory
            DESCRIPTION
                "The Ethernet LP-BIP Total table."
            ::= { enetPerfDisplayTable 12 }

        enLP-VTTotalEty  OBJECT-TYPE
            SYNTAX  EnLP-VTTotalEty
            ACCESS  not-accessible
            STATUS  mandatory
            DESCRIPTION
                "An entry in the Ethernet LP-BIP Total table."
            INDEX { enLpVtTotalUnit , enLpVtTotalPort ,
                    enLpVtTotalChannel }
            ::= { enLP-VTTotalTab 1 }

        EnLP-VTTotalEty ::= SEQUENCE {
            enLpVtTotalUnit             UnitID,
            enLpVtTotalPort             VcgPortNum,
            enLpVtTotalChannel          ChannelNum,
            enLpVtTotalEBs              Counter,
            enLpVtTotalBBEs             Counter,
            enLpVtTotalESs              Counter,
            enLpVtTotalBESs             Counter,
            enLpVtTotalSESs             Counter,
            enLpVtTotalUASs             Counter
        }

        enLpVtTotalUnit  OBJECT-TYPE
            SYNTAX  UnitID
            ACCESS  read-only
            STATUS  mandatory
            DESCRIPTION
            "unit 1 to 4."
            ::= { enLP-VTTotalEty 1 }

        enLpVtTotalPort  OBJECT-TYPE
            SYNTAX  VcgPortNum
            ACCESS  read-only
            STATUS  mandatory
            DESCRIPTION
                "vcg port index: wan1~wan9"
            ::= { enLP-VTTotalEty 2 }

        enLpVtTotalChannel  OBJECT-TYPE
            SYNTAX  ChannelNum
            ACCESS  read-only
            STATUS  mandatory
            DESCRIPTION
                "Channel index"
            ::= { enLP-VTTotalEty 3 }

        enLpVtTotalEBs  OBJECT-TYPE
            SYNTAX  Counter
            ACCESS  read-only
            STATUS  mandatory
            DESCRIPTION
                "LP-BIP Error Block"
            ::= { enLP-VTTotalEty 4 }

        enLpVtTotalBBEs  OBJECT-TYPE
            SYNTAX  Counter
            ACCESS  read-only
            STATUS  mandatory
            DESCRIPTION
                "LP-BIP Background Block Error"
            ::= { enLP-VTTotalEty 5 }

        enLpVtTotalESs  OBJECT-TYPE
            SYNTAX  Counter
            ACCESS  read-only
            STATUS  mandatory
            DESCRIPTION
                "LP-BIP Error Second"
            ::= { enLP-VTTotalEty 6 }

        enLpVtTotalBESs  OBJECT-TYPE
            SYNTAX  Counter
            ACCESS  read-only
            STATUS  mandatory
            DESCRIPTION
                "LP-BIP Background Error Second"
            ::= { enLP-VTTotalEty 7 }

        enLpVtTotalSESs  OBJECT-TYPE
            SYNTAX  Counter
            ACCESS  read-only
            STATUS  mandatory
            DESCRIPTION
                "LP-BIP Severly Error Second"
            ::= { enLP-VTTotalEty 8 }

        enLpVtTotalUASs  OBJECT-TYPE
            SYNTAX  Counter
            ACCESS  read-only
            STATUS  mandatory
            DESCRIPTION
                "LP-BIP Unavailable Second"
            ::= { enLP-VTTotalEty 9 }

--
--  enFarEndLP-VTCurrTab
--
        enFarEndLP-VTCurrTab  OBJECT-TYPE
            SYNTAX  SEQUENCE OF  EnFarEndLP-VTCurrEty
            ACCESS  not-accessible
            STATUS  mandatory
            DESCRIPTION
                "The Ethernet LP-REI/REI-V Current table."
            ::= { enetPerfDisplayTable 13 }

        enFarEndLP-VTCurrEty  OBJECT-TYPE
            SYNTAX  EnFarEndLP-VTCurrEty
            ACCESS  not-accessible
            STATUS  mandatory
            DESCRIPTION
                "An entry in the Ethernet LP-REI/REI-V Current table."
            INDEX { enFrLpVtCurrUnit , enFrLpVtCurrPort ,
                    enFrLpVtCurrChannel }
            ::= { enFarEndLP-VTCurrTab 1 }

        EnFarEndLP-VTCurrEty ::= SEQUENCE {
            enFrLpVtCurrUnit            UnitID,
            enFrLpVtCurrPort            VcgPortNum,
            enFrLpVtCurrChannel         ChannelNum,
            enFrLpVtCurrEBs             Counter,
            enFrLpVtCurrBBEs            Counter,
            enFrLpVtCurrESs             Counter,
            enFrLpVtCurrBESs            Counter,
            enFrLpVtCurrSESs            Counter,
            enFrLpVtCurrUASs            Counter,
            enFrLpVtCurr24HValid15M     Counter,
            enFrLpVtCurr7DayValidDay    Counter,
            enFrLpVtCurr15MTimeElaps    Counter,
            enFrLpVtCurrDayValid15M     Counter
        }

        enFrLpVtCurrUnit  OBJECT-TYPE
            SYNTAX  UnitID
            ACCESS  read-only
            STATUS  mandatory
            DESCRIPTION
            "unit 1 to 4."
            ::= { enFarEndLP-VTCurrEty 1 }

        enFrLpVtCurrPort  OBJECT-TYPE
            SYNTAX  VcgPortNum
            ACCESS  read-only
            STATUS  mandatory
            DESCRIPTION
                "vcg port index: wan1~wan9"
            ::= { enFarEndLP-VTCurrEty 2 }

        enFrLpVtCurrChannel  OBJECT-TYPE
            SYNTAX  ChannelNum
            ACCESS  read-only
            STATUS  mandatory
            DESCRIPTION
                "Channel index"
            ::= { enFarEndLP-VTCurrEty 3 }

        enFrLpVtCurrEBs  OBJECT-TYPE
            SYNTAX  Counter
            ACCESS  read-only
            STATUS  mandatory
            DESCRIPTION
                "LP-REI/REI-V Error Block"
            ::= { enFarEndLP-VTCurrEty 4 }

        enFrLpVtCurrBBEs  OBJECT-TYPE
            SYNTAX  Counter
            ACCESS  read-only
            STATUS  mandatory
            DESCRIPTION
                "LP-REI/REI-V Background Block Error"
            ::= { enFarEndLP-VTCurrEty 5 }

        enFrLpVtCurrESs  OBJECT-TYPE
            SYNTAX  Counter
            ACCESS  read-only
            STATUS  mandatory
            DESCRIPTION
                "LP-REI/REI-V Error Second"
            ::= { enFarEndLP-VTCurrEty 6 }

        enFrLpVtCurrBESs  OBJECT-TYPE
            SYNTAX  Counter
            ACCESS  read-only
            STATUS  mandatory
            DESCRIPTION
                "LP-REI/REI-V Background Error Second"
            ::= { enFarEndLP-VTCurrEty 7 }

        enFrLpVtCurrSESs  OBJECT-TYPE
            SYNTAX  Counter
            ACCESS  read-only
            STATUS  mandatory
            DESCRIPTION
                "LP-REI/REI-V Severly Error Second"
            ::= { enFarEndLP-VTCurrEty 8 }

        enFrLpVtCurrUASs  OBJECT-TYPE
            SYNTAX  Counter
            ACCESS  read-only
            STATUS  mandatory
            DESCRIPTION
                "LP-REI/REI-V Unavailable Second"
            ::= { enFarEndLP-VTCurrEty 9 }

        enFrLpVtCurr24HValid15M  OBJECT-TYPE
            SYNTAX  Counter
            ACCESS  read-only
            STATUS  mandatory
            DESCRIPTION
                "LP-REI/REI-V Valid 15-Min Interval"
            ::= { enFarEndLP-VTCurrEty 10 }

        enFrLpVtCurr7DayValidDay  OBJECT-TYPE
            SYNTAX  Counter
            ACCESS  read-only
            STATUS  mandatory
            DESCRIPTION
                "LP-REI/REI-V Valid 1-Day Interval"
            ::= { enFarEndLP-VTCurrEty 11 }

        enFrLpVtCurr15MTimeElaps  OBJECT-TYPE
            SYNTAX  Counter
            ACCESS  read-only
            STATUS  mandatory
            DESCRIPTION
                "LP-REI/REI-V Current 15-MIN Time Elapsed"
            ::= { enFarEndLP-VTCurrEty 12 }

        enFrLpVtCurrDayValid15M  OBJECT-TYPE
            SYNTAX  Counter
            ACCESS  read-only
            STATUS  mandatory
            DESCRIPTION
                "LP-REI/REI-V Current Day Time Elapsed"
            ::= { enFarEndLP-VTCurrEty 13 }

--
--  enFarEndLP-VTIntervTab
--
        enFarEndLP-VTIntervTab  OBJECT-TYPE
            SYNTAX  SEQUENCE OF  EnFarEndLP-VTIntervEty
            ACCESS  not-accessible
            STATUS  mandatory
            DESCRIPTION
                "The Ethernet LP-REI/REI-V Interval table."
            ::= { enetPerfDisplayTable 14 }

        enFarEndLP-VTIntervEty  OBJECT-TYPE
            SYNTAX  EnFarEndLP-VTIntervEty
            ACCESS  not-accessible
            STATUS  mandatory
            DESCRIPTION
                "An entry in the Ethernet LP-REI/REI-V Interval table."
            INDEX { enFrLpVtIntervUnit , enFrLpVtIntervPort ,
                    enFrLpVtIntervChannel , enFrLpVtIntervNumber }
            ::= { enFarEndLP-VTIntervTab 1 }

        EnFarEndLP-VTIntervEty ::= SEQUENCE {
            enFrLpVtIntervUnit          UnitID,
            enFrLpVtIntervPort          VcgPortNum,
            enFrLpVtIntervChannel       ChannelNum,
            enFrLpVtIntervNumber        INTEGER (1..96),
            enFrLpVtIntervEBs           Counter,
            enFrLpVtIntervBBEs          Counter,
            enFrLpVtIntervESs           Counter,
            enFrLpVtIntervBESs          Counter,
            enFrLpVtIntervSESs          Counter,
            enFrLpVtIntervUASs          Counter
        }

        enFrLpVtIntervUnit  OBJECT-TYPE
            SYNTAX  UnitID
            ACCESS  read-only
            STATUS  mandatory
            DESCRIPTION
            "unit 1 to 4."
            ::= { enFarEndLP-VTIntervEty 1 }

        enFrLpVtIntervPort  OBJECT-TYPE
            SYNTAX  VcgPortNum
            ACCESS  read-only
            STATUS  mandatory
            DESCRIPTION
                "vcg port index: wan1~wan9"
            ::= { enFarEndLP-VTIntervEty 2 }

        enFrLpVtIntervChannel  OBJECT-TYPE
            SYNTAX  ChannelNum
            ACCESS  read-only
            STATUS  mandatory
            DESCRIPTION
                "Channel index"
            ::= { enFarEndLP-VTIntervEty 3 }

        enFrLpVtIntervNumber  OBJECT-TYPE
            SYNTAX  INTEGER (1..96)
            ACCESS  read-only
            STATUS  mandatory
            DESCRIPTION
                "A number between 1 and 96"
            ::= { enFarEndLP-VTIntervEty 4 }

        enFrLpVtIntervEBs  OBJECT-TYPE
            SYNTAX  Counter
            ACCESS  read-only
            STATUS  mandatory
            DESCRIPTION
                "LP-REI/REI-V Error Block"
            ::= { enFarEndLP-VTIntervEty 5 }

        enFrLpVtIntervBBEs  OBJECT-TYPE
            SYNTAX  Counter
            ACCESS  read-only
            STATUS  mandatory
            DESCRIPTION
                "LP-REI/REI-V Background Block Error"
            ::= { enFarEndLP-VTIntervEty 6 }

        enFrLpVtIntervESs  OBJECT-TYPE
            SYNTAX  Counter
            ACCESS  read-only
            STATUS  mandatory
            DESCRIPTION
                "LP-REI/REI-V Error Second"
            ::= { enFarEndLP-VTIntervEty 7 }

        enFrLpVtIntervBESs  OBJECT-TYPE
            SYNTAX  Counter
            ACCESS  read-only
            STATUS  mandatory
            DESCRIPTION
                "LP-REI/REI-V Background Error Second"
            ::= { enFarEndLP-VTIntervEty 8 }

        enFrLpVtIntervSESs  OBJECT-TYPE
            SYNTAX  Counter
            ACCESS  read-only
            STATUS  mandatory
            DESCRIPTION
                "LP-REI/REI-V Severly Error Second"
            ::= { enFarEndLP-VTIntervEty 9 }

        enFrLpVtIntervUASs  OBJECT-TYPE
            SYNTAX  Counter
            ACCESS  read-only
            STATUS  mandatory
            DESCRIPTION
                "LP-REI/REI-V Unavailable Second"
            ::= { enFarEndLP-VTIntervEty 10 }

--
--  enFarEndLP-VT7DaysTab
--
        enFarEndLP-VT7DaysTab  OBJECT-TYPE
            SYNTAX  SEQUENCE OF  EnFarEndLP-VT7DaysEty
            ACCESS  not-accessible
            STATUS  mandatory
            DESCRIPTION
                "The Ethernet LP-REI/REI-V 7 days table."
            ::= { enetPerfDisplayTable 15 }

        enFarEndLP-VT7DaysEty  OBJECT-TYPE
            SYNTAX  EnFarEndLP-VT7DaysEty
            ACCESS  not-accessible
            STATUS  mandatory
            DESCRIPTION
                "An entry in the Ethernet LP-REI/REI-V 7 days table."
            INDEX { enFrLpVt7DaysUnit , enFrLpVt7DaysPort ,
                    enFrLpVt7DaysChannel , enFrLpVt7DaysNumber }
            ::= { enFarEndLP-VT7DaysTab 1 }

        EnFarEndLP-VT7DaysEty ::= SEQUENCE {
            enFrLpVt7DaysUnit           UnitID,
            enFrLpVt7DaysPort           VcgPortNum,
            enFrLpVt7DaysChannel        ChannelNum,
            enFrLpVt7DaysNumber         INTEGER (1..7),
            enFrLpVt7DaysDate           DisplayString (SIZE (0..255)),
            enFrLpVt7DaysEBs            Counter,
            enFrLpVt7DaysBBEs           Counter,
            enFrLpVt7DaysESs            Counter,
            enFrLpVt7DaysBESs           Counter,
            enFrLpVt7DaysSESs           Counter,
            enFrLpVt7DaysUASs           Counter
        }

        enFrLpVt7DaysUnit  OBJECT-TYPE
            SYNTAX  UnitID
            ACCESS  read-only
            STATUS  mandatory
            DESCRIPTION
            "unit 1 to 4."
            ::= { enFarEndLP-VT7DaysEty 1 }

        enFrLpVt7DaysPort  OBJECT-TYPE
            SYNTAX  VcgPortNum
            ACCESS  read-only
            STATUS  mandatory
            DESCRIPTION
                "vcg port index: wan1~wan9"
            ::= { enFarEndLP-VT7DaysEty 2 }

        enFrLpVt7DaysChannel  OBJECT-TYPE
            SYNTAX  ChannelNum
            ACCESS  read-only
            STATUS  mandatory
            DESCRIPTION
                "Channel index"
            ::= { enFarEndLP-VT7DaysEty 3 }

        enFrLpVt7DaysNumber  OBJECT-TYPE
            SYNTAX  INTEGER (1..7)
            ACCESS  read-only
            STATUS  mandatory
            DESCRIPTION
                "A number between 1 and 7"
            ::= { enFarEndLP-VT7DaysEty 4 }

        enFrLpVt7DaysDate  OBJECT-TYPE
            SYNTAX  DisplayString (SIZE (0..255))
            ACCESS  read-only
            STATUS  mandatory
            DESCRIPTION
                "Date"
            ::= { enFarEndLP-VT7DaysEty 5 }

        enFrLpVt7DaysEBs  OBJECT-TYPE
            SYNTAX  Counter
            ACCESS  read-only
            STATUS  mandatory
            DESCRIPTION
                "LP-REI/REI-V Error Block"
            ::= { enFarEndLP-VT7DaysEty 6 }

        enFrLpVt7DaysBBEs  OBJECT-TYPE
            SYNTAX  Counter
            ACCESS  read-only
            STATUS  mandatory
            DESCRIPTION
                "LP-REI/REI-V Background Block Error"
            ::= { enFarEndLP-VT7DaysEty 7 }

        enFrLpVt7DaysESs  OBJECT-TYPE
            SYNTAX  Counter
            ACCESS  read-only
            STATUS  mandatory
            DESCRIPTION
                "LP-REI/REI-V Error Second"
            ::= { enFarEndLP-VT7DaysEty 8 }

        enFrLpVt7DaysBESs  OBJECT-TYPE
            SYNTAX  Counter
            ACCESS  read-only
            STATUS  mandatory
            DESCRIPTION
                "LP-REI/REI-V Background Error Second"
            ::= { enFarEndLP-VT7DaysEty 9 }

        enFrLpVt7DaysSESs  OBJECT-TYPE
            SYNTAX  Counter
            ACCESS  read-only
            STATUS  mandatory
            DESCRIPTION
                "LP-REI/REI-V Severly Error Second"
            ::= { enFarEndLP-VT7DaysEty 10 }

        enFrLpVt7DaysUASs  OBJECT-TYPE
            SYNTAX  Counter
            ACCESS  read-only
            STATUS  mandatory
            DESCRIPTION
                "LP-REI/REI-V Unavailable Second"
            ::= { enFarEndLP-VT7DaysEty 11 }

--
--  enFarEndLP-VTTotalTab
--
        enFarEndLP-VTTotalTab  OBJECT-TYPE
            SYNTAX  SEQUENCE OF  EnFarEndLP-VTTotalEty
            ACCESS  not-accessible
            STATUS  mandatory
            DESCRIPTION
                "The Ethernet LP-REI/REI-V Total table."
            ::= { enetPerfDisplayTable 16 }

        enFarEndLP-VTTotalEty  OBJECT-TYPE
            SYNTAX  EnFarEndLP-VTTotalEty
            ACCESS  not-accessible
            STATUS  mandatory
            DESCRIPTION
                "An entry in the Ethernet LP-REI/REI-V Total table."
            INDEX { enFrLpVtTotalUnit , enFrLpVtTotalPort ,
                    enFrLpVtTotalChannel }
            ::= { enFarEndLP-VTTotalTab 1 }

        EnFarEndLP-VTTotalEty ::= SEQUENCE {
            enFrLpVtTotalUnit           UnitID,
            enFrLpVtTotalPort           VcgPortNum,
            enFrLpVtTotalChannel        ChannelNum,
            enFrLpVtTotalEBs            Counter,
            enFrLpVtTotalBBEs           Counter,
            enFrLpVtTotalESs            Counter,
            enFrLpVtTotalBESs           Counter,
            enFrLpVtTotalSESs           Counter,
            enFrLpVtTotalUASs           Counter
        }

        enFrLpVtTotalUnit  OBJECT-TYPE
            SYNTAX  UnitID
            ACCESS  read-only
            STATUS  mandatory
            DESCRIPTION
            "unit 1 to 4."
            ::= { enFarEndLP-VTTotalEty 1 }

        enFrLpVtTotalPort  OBJECT-TYPE
            SYNTAX  VcgPortNum
            ACCESS  read-only
            STATUS  mandatory
            DESCRIPTION
                "vcg port index: wan1~wan9"
            ::= { enFarEndLP-VTTotalEty 2 }

        enFrLpVtTotalChannel  OBJECT-TYPE
            SYNTAX  ChannelNum
            ACCESS  read-only
            STATUS  mandatory
            DESCRIPTION
                "Channel index"
            ::= { enFarEndLP-VTTotalEty 3 }

        enFrLpVtTotalEBs  OBJECT-TYPE
            SYNTAX  Counter
            ACCESS  read-only
            STATUS  mandatory
            DESCRIPTION
                "LP-REI/REI-V Error Block"
            ::= { enFarEndLP-VTTotalEty 4 }

        enFrLpVtTotalBBEs  OBJECT-TYPE
            SYNTAX  Counter
            ACCESS  read-only
            STATUS  mandatory
            DESCRIPTION
                "LP-REI/REI-V Background Block Error"
            ::= { enFarEndLP-VTTotalEty 5 }

        enFrLpVtTotalESs  OBJECT-TYPE
            SYNTAX  Counter
            ACCESS  read-only
            STATUS  mandatory
            DESCRIPTION
                "LP-REI/REI-V Error Second"
            ::= { enFarEndLP-VTTotalEty 6 }

        enFrLpVtTotalBESs  OBJECT-TYPE
            SYNTAX  Counter
            ACCESS  read-only
            STATUS  mandatory
            DESCRIPTION
                "LP-REI/REI-V Background Error Second"
            ::= { enFarEndLP-VTTotalEty 7 }

        enFrLpVtTotalSESs  OBJECT-TYPE
            SYNTAX  Counter
            ACCESS  read-only
            STATUS  mandatory
            DESCRIPTION
                "LP-REI/REI-V Severly Error Second"
            ::= { enFarEndLP-VTTotalEty 8 }

        enFrLpVtTotalUASs  OBJECT-TYPE
            SYNTAX  Counter
            ACCESS  read-only
            STATUS  mandatory
            DESCRIPTION
                "LP-REI/REI-V Unavailable Second"
            ::= { enFarEndLP-VTTotalEty 9 }

--
--  enetWanVcgStatisticTable
--
    enetWanVcgStatisticTable    OBJECT IDENTIFIER ::= { enet-card 7 }

--
--  enetGfpStatisticTable
--
        enetGfpStatisticTable  OBJECT-TYPE
            SYNTAX  SEQUENCE OF  EnetGfpStatisticEntry
            ACCESS  not-accessible
            STATUS  mandatory
            DESCRIPTION
                "The Ethernet wan(vcg) GFP statistic table."
            ::= { enetWanVcgStatisticTable 1 }

        enetGfpStatisticEntry  OBJECT-TYPE
            SYNTAX  EnetGfpStatisticEntry
            ACCESS  not-accessible
            STATUS  mandatory
            DESCRIPTION
                "An entry in the Ethernet wan(vcg) GFP statistic table."
            INDEX { enGfpStUnit , enGfpStPort }
            ::= { enetGfpStatisticTable 1 }

        EnetGfpStatisticEntry ::= SEQUENCE {
            enGfpStUnit                 UnitID,
            enGfpStPort                 VcgPortNum,
            enGfpStRxFrames             Counter,
            enGfpStRxBytes              Counter,
            enGfpStRxControlFrames      Counter,
            enGfpStRxIdleFrames         Counter,
            enGfpStRxCSFFrames          Counter,
            enGfpStRxDroppedFrames      Counter,
            enGfpStRxErrCHECFrames      Counter,
            enGfpStRxErrTHECFrames      Counter,
            enGfpStRxErrEHECFrames      Counter,
            enGfpStRxErrFCSFrames       Counter,
            enGfpStRxFifoOvfFrames      Counter,
            enGfpStTxFrames             Counter,
            enGfpStTxBytes              Counter,
            enGfpStTxCmfCtrlFrames      Counter,
            enGfpStTxIdleFrames         Counter
        }

        enGfpStUnit  OBJECT-TYPE
            SYNTAX  UnitID
            ACCESS  read-only
            STATUS  mandatory
            DESCRIPTION
            "unit 1 to 4."
            ::= { enetGfpStatisticEntry 1 }

        enGfpStPort  OBJECT-TYPE
            SYNTAX  VcgPortNum
            ACCESS  read-only
            STATUS  mandatory
            DESCRIPTION
                "vcg port index: wan1~wan9"
            ::= { enetGfpStatisticEntry 2 }

        enGfpStRxFrames  OBJECT-TYPE
            SYNTAX  Counter
            ACCESS  read-only
            STATUS  mandatory
            DESCRIPTION
                "WAN(VCG) Rx Frames Counter"
            ::= { enetGfpStatisticEntry 3 }

        enGfpStRxBytes  OBJECT-TYPE
            SYNTAX  Counter
            ACCESS  read-only
            STATUS  mandatory
            DESCRIPTION
                "WAN(VCG) Rx Bytes Counter"
            ::= { enetGfpStatisticEntry 4 }

        enGfpStRxControlFrames  OBJECT-TYPE
            SYNTAX  Counter
            ACCESS  read-only
            STATUS  mandatory
            DESCRIPTION
                "WAN(VCG) Rx Control Frames Counter"
            ::= { enetGfpStatisticEntry 5 }

        enGfpStRxIdleFrames  OBJECT-TYPE
            SYNTAX  Counter
            ACCESS  read-only
            STATUS  mandatory
            DESCRIPTION
                "WAN(VCG) Rx Idle Frames Counter"
            ::= { enetGfpStatisticEntry 6 }

        enGfpStRxCSFFrames  OBJECT-TYPE
            SYNTAX  Counter
            ACCESS  read-only
            STATUS  mandatory
            DESCRIPTION
                "WAN(VCG) Rx CSF Frames Counter"
            ::= { enetGfpStatisticEntry 7 }

        enGfpStRxDroppedFrames  OBJECT-TYPE
            SYNTAX  Counter
            ACCESS  read-only
            STATUS  mandatory
            DESCRIPTION
                "WAN(VCG) Rx Dropped Frames Counter"
            ::= { enetGfpStatisticEntry 8 }

        enGfpStRxErrCHECFrames  OBJECT-TYPE
            SYNTAX  Counter
            ACCESS  read-only
            STATUS  mandatory
            DESCRIPTION
                "WAN(VCG) Rx Error cHEC Frames Counter"
            ::= { enetGfpStatisticEntry 9 }

        enGfpStRxErrTHECFrames  OBJECT-TYPE
            SYNTAX  Counter
            ACCESS  read-only
            STATUS  mandatory
            DESCRIPTION
                "WAN(VCG) Rx Error tHEC Frames Counter"
            ::= { enetGfpStatisticEntry 10 }

        enGfpStRxErrEHECFrames  OBJECT-TYPE
            SYNTAX  Counter
            ACCESS  read-only
            STATUS  mandatory
            DESCRIPTION
                "WAN(VCG) Rx Error eHEC Frames Counter"
            ::= { enetGfpStatisticEntry 11 }

        enGfpStRxErrFCSFrames  OBJECT-TYPE
            SYNTAX  Counter
            ACCESS  read-only
            STATUS  mandatory
            DESCRIPTION
                "WAN(VCG) Rx error FCS Frames Counter"
            ::= { enetGfpStatisticEntry 12 }

        enGfpStRxFifoOvfFrames  OBJECT-TYPE
            SYNTAX  Counter
            ACCESS  read-only
            STATUS  mandatory
            DESCRIPTION
                "WAN(VCG) Rx FIFO Overflow Frames Counter"
            ::= { enetGfpStatisticEntry 13 }

        enGfpStTxFrames  OBJECT-TYPE
            SYNTAX  Counter
            ACCESS  read-only
            STATUS  mandatory
            DESCRIPTION
                "WAN(VCG) Tx Frames Counter"
            ::= { enetGfpStatisticEntry 14 }

        enGfpStTxBytes  OBJECT-TYPE
            SYNTAX  Counter
            ACCESS  read-only
            STATUS  mandatory
            DESCRIPTION
                "WAN(VCG) Tx Bytes Counter"
            ::= { enetGfpStatisticEntry 15 }

        enGfpStTxCmfCtrlFrames  OBJECT-TYPE
            SYNTAX  Counter
            ACCESS  read-only
            STATUS  mandatory
            DESCRIPTION
                "WAN(VCG) Tx CMF/Control Frames Counter"
            ::= { enetGfpStatisticEntry 16 }

        enGfpStTxIdleFrames  OBJECT-TYPE
            SYNTAX  Counter
            ACCESS  read-only
            STATUS  mandatory
            DESCRIPTION
                "WAN(VCG) Tx Idle Frames Counter"
            ::= { enetGfpStatisticEntry 17 }

--
--  enetLapsStatisticTable
--
        enetLapsStatisticTable  OBJECT-TYPE
            SYNTAX  SEQUENCE OF  EnetLapsStatisticEntry
            ACCESS  not-accessible
            STATUS  mandatory
            DESCRIPTION
                "The Ethernet wan(vcg) LAPS statistic table."
            ::= { enetWanVcgStatisticTable 2 }

        enetLapsStatisticEntry  OBJECT-TYPE
            SYNTAX  EnetLapsStatisticEntry
            ACCESS  not-accessible
            STATUS  mandatory
            DESCRIPTION
                "An entry in the Ethernet wan(vcg) LAPS statistic table."
            INDEX { enLapsStUnit , enLapsStPort }
            ::= { enetLapsStatisticTable 1 }

        EnetLapsStatisticEntry ::= SEQUENCE {
            enLapsStUnit                UnitID,
            enLapsStPort                VcgPortNum,
            enLapsStRxFrames            Counter,
            enLapsStRxBytes             Counter,
            enLapsStRxAbortedFrames     Counter,
            enLapsStRxDroppedFrames     Counter,
            enLapsStRxErrFCSFrames      Counter,
            enLapsStRxTransErrFrames    Counter,
            enLapsStRxMaxLenVioFrm      Counter,
            enLapsStRxMinLenVioFrm      Counter,
            enLapsStRxFifoOvfFrames     Counter,
            enLapsStTxFrames            Counter,
            enLapsStTxBytes             Counter
        }

        enLapsStUnit  OBJECT-TYPE
            SYNTAX  UnitID
            ACCESS  read-only
            STATUS  mandatory
            DESCRIPTION
            "unit 1 to 4."
            ::= { enetLapsStatisticEntry 1 }

        enLapsStPort  OBJECT-TYPE
            SYNTAX  VcgPortNum
            ACCESS  read-only
            STATUS  mandatory
            DESCRIPTION
                "vcg port index: wan1~wan9"
            ::= { enetLapsStatisticEntry 2 }

        enLapsStRxFrames  OBJECT-TYPE
            SYNTAX  Counter
            ACCESS  read-only
            STATUS  mandatory
            DESCRIPTION
                "WAN(VCG) Rx Frames Counter"
            ::= { enetLapsStatisticEntry 3 }

        enLapsStRxBytes  OBJECT-TYPE
            SYNTAX  Counter
            ACCESS  read-only
            STATUS  mandatory
            DESCRIPTION
                "WAN(VCG) Rx Bytes Counter"
            ::= { enetLapsStatisticEntry 4 }

        enLapsStRxAbortedFrames  OBJECT-TYPE
            SYNTAX  Counter
            ACCESS  read-only
            STATUS  mandatory
            DESCRIPTION
                "WAN(VCG) Rx Aborted Frames Counter"
            ::= { enetLapsStatisticEntry 5 }

        enLapsStRxDroppedFrames  OBJECT-TYPE
            SYNTAX  Counter
            ACCESS  read-only
            STATUS  mandatory
            DESCRIPTION
                "WAN(VCG) Rx Dropped Frames Counter"
            ::= { enetLapsStatisticEntry 6 }

        enLapsStRxErrFCSFrames  OBJECT-TYPE
            SYNTAX  Counter
            ACCESS  read-only
            STATUS  mandatory
            DESCRIPTION
                "WAN(VCG) Rx Erred FCS Frames Counter"
            ::= { enetLapsStatisticEntry 7 }

        enLapsStRxTransErrFrames  OBJECT-TYPE
            SYNTAX  Counter
            ACCESS  read-only
            STATUS  mandatory
            DESCRIPTION
                "WAN(VCG) Rx Transparency Erred Frames Counter"
            ::= { enetLapsStatisticEntry 8 }

        enLapsStRxMaxLenVioFrm  OBJECT-TYPE
            SYNTAX  Counter
            ACCESS  read-only
            STATUS  mandatory
            DESCRIPTION
                "WAN(VCG) Rx Max Length Violation Frames Counter"
            ::= { enetLapsStatisticEntry 9 }

        enLapsStRxMinLenVioFrm  OBJECT-TYPE
            SYNTAX  Counter
            ACCESS  read-only
            STATUS  mandatory
            DESCRIPTION
                "WAN(VCG) Min Length Violation Frames Counter"
            ::= { enetLapsStatisticEntry 10 }

        enLapsStRxFifoOvfFrames  OBJECT-TYPE
            SYNTAX  Counter
            ACCESS  read-only
            STATUS  mandatory
            DESCRIPTION
                "WAN(VCG) Rx FIFO Overflow Frames Counter"
            ::= { enetLapsStatisticEntry 11 }

        enLapsStTxFrames  OBJECT-TYPE
            SYNTAX  Counter
            ACCESS  read-only
            STATUS  mandatory
            DESCRIPTION
                "WAN(VCG) Tx Frames Counter"
            ::= { enetLapsStatisticEntry 12 }

        enLapsStTxBytes  OBJECT-TYPE
            SYNTAX  Counter
            ACCESS  read-only
            STATUS  mandatory
            DESCRIPTION
                "WAN(VCG) Tx Bytes Counter"
            ::= { enetLapsStatisticEntry 13 }

--
--  enetMacStatisticTable
--
        enetMacStatisticTable  OBJECT-TYPE
            SYNTAX  SEQUENCE OF  EnetMacStatisticEntry
            ACCESS  not-accessible
            STATUS  mandatory
            DESCRIPTION
                "The Ethernet wan(vcg) MAC statistic table."
            ::= { enetWanVcgStatisticTable 3 }

        enetMacStatisticEntry  OBJECT-TYPE
            SYNTAX  EnetMacStatisticEntry
            ACCESS  not-accessible
            STATUS  mandatory
            DESCRIPTION
                "An entry in the Ethernet wan(vcg) MAC statistic table."
            INDEX { enMacStUnit , enMacStPort }
            ::= { enetMacStatisticTable 1 }

        EnetMacStatisticEntry ::= SEQUENCE {
            enMacStUnit                 UnitID,
            enMacStPort                 VcgPortNum,
            enMacStRxFrames             Counter,
            enMacStRxOctets             Counter,
            enMacStRxTaggedFramesOK     Counter,
            enMacStRxFCSErrors          Counter,
            enMacStRxLayer1Errors       Counter,
            enMacStRxLayer2Errors       Counter,
            enMacStRxFramesTooLong      Counter,
            enMacStRxFramesTooShort     Counter,
            enMacStRxJabbers            Counter,
            enMacStRxPauseCtrlFrmOK     Counter,
            enMacStTxFrames             Counter,
            enMacStTxOctets             Counter,
            enMacStTxTaggedFramesOK     Counter,
            enMacStTxFcsErrors          Counter,
            enMacStFilterMacCtrlFrms    Counter,
            enMacStIngFifoOvfPkts       Counter,
            enMacStIngFifoOvfBytes      Counter
        }

        enMacStUnit  OBJECT-TYPE
            SYNTAX  UnitID
            ACCESS  read-only
            STATUS  mandatory
            DESCRIPTION
            "unit 1 to 4."
            ::= { enetMacStatisticEntry 1 }

        enMacStPort  OBJECT-TYPE
            SYNTAX  VcgPortNum
            ACCESS  read-only
            STATUS  mandatory
            DESCRIPTION
                "vcg port index: wan1~wan9"
            ::= { enetMacStatisticEntry 2 }

        enMacStRxFrames  OBJECT-TYPE
            SYNTAX  Counter
            ACCESS  read-only
            STATUS  mandatory
            DESCRIPTION
                "WAN(VCG) MAC Rx Frames Counter"
            ::= { enetMacStatisticEntry 3 }

        enMacStRxOctets  OBJECT-TYPE
            SYNTAX  Counter
            ACCESS  read-only
            STATUS  mandatory
            DESCRIPTION
                "WAN(VCG) MAC Rx Octets Counter"
            ::= { enetMacStatisticEntry 4 }

        enMacStRxTaggedFramesOK  OBJECT-TYPE
            SYNTAX  Counter
            ACCESS  read-only
            STATUS  mandatory
            DESCRIPTION
                "WAN(VCG) MAC Rx Tagged Frames OK Counter"
            ::= { enetMacStatisticEntry 5 }

        enMacStRxFCSErrors  OBJECT-TYPE
            SYNTAX  Counter
            ACCESS  read-only
            STATUS  mandatory
            DESCRIPTION
                "WAN(VCG) MAC Rx FXS Errors Counter"
            ::= { enetMacStatisticEntry 6 }

        enMacStRxLayer1Errors  OBJECT-TYPE
            SYNTAX  Counter
            ACCESS  read-only
            STATUS  mandatory
            DESCRIPTION
                "WAN(VCG) MAC Rx Layer1 Errors Counter"
            ::= { enetMacStatisticEntry 7 }

        enMacStRxLayer2Errors  OBJECT-TYPE
            SYNTAX  Counter
            ACCESS  read-only
            STATUS  mandatory
            DESCRIPTION
                "WAN(VCG) MAC Rx Layer2 Errors Counter"
            ::= { enetMacStatisticEntry 8 }

        enMacStRxFramesTooLong  OBJECT-TYPE
            SYNTAX  Counter
            ACCESS  read-only
            STATUS  mandatory
            DESCRIPTION
                "WAN(VCG) MAC Rx Frames Too Long Counter"
            ::= { enetMacStatisticEntry 9 }

        enMacStRxFramesTooShort  OBJECT-TYPE
            SYNTAX  Counter
            ACCESS  read-only
            STATUS  mandatory
            DESCRIPTION
                "WAN(VCG) MAC Rx Frames Too Short Counter"
            ::= { enetMacStatisticEntry 10 }

        enMacStRxJabbers  OBJECT-TYPE
            SYNTAX  Counter
            ACCESS  read-only
            STATUS  mandatory
            DESCRIPTION
                "WAN(VCG) MAC Rx Jabbers Counter"
            ::= { enetMacStatisticEntry 11 }

        enMacStRxPauseCtrlFrmOK  OBJECT-TYPE
            SYNTAX  Counter
            ACCESS  read-only
            STATUS  mandatory
            DESCRIPTION
                "WAN(VCG) MAC Rx Pause Control Frames OK Counter"
            ::= { enetMacStatisticEntry 12 }

        enMacStTxFrames  OBJECT-TYPE
            SYNTAX  Counter
            ACCESS  read-only
            STATUS  mandatory
            DESCRIPTION
                "WAN(VCG) MAC Tx Frames Counter"
            ::= { enetMacStatisticEntry 13 }

        enMacStTxOctets  OBJECT-TYPE
            SYNTAX  Counter
            ACCESS  read-only
            STATUS  mandatory
            DESCRIPTION
                "WAN(VCG) MAC Tx Octets Counter"
            ::= { enetMacStatisticEntry 14 }

        enMacStTxTaggedFramesOK  OBJECT-TYPE
            SYNTAX  Counter
            ACCESS  read-only
            STATUS  mandatory
            DESCRIPTION
                "WAN(VCG) MAC Tx Tagged Frames OK Counter"
            ::= { enetMacStatisticEntry 15 }

        enMacStTxFcsErrors  OBJECT-TYPE
            SYNTAX  Counter
            ACCESS  read-only
            STATUS  mandatory
            DESCRIPTION
                "WAN(VCG) MAC Tx FCS Errors Counter"
            ::= { enetMacStatisticEntry 16 }

        enMacStFilterMacCtrlFrms  OBJECT-TYPE
            SYNTAX  Counter
            ACCESS  read-only
            STATUS  mandatory
            DESCRIPTION
                "WAN(VCG) MAC Filtered MAC Control Frames Counter"
            ::= { enetMacStatisticEntry 17 }

        enMacStIngFifoOvfPkts  OBJECT-TYPE
            SYNTAX  Counter
            ACCESS  read-only
            STATUS  mandatory
            DESCRIPTION
                "WAN(VCG) MAC Ingress FIFO Overflow Packets Counter"
            ::= { enetMacStatisticEntry 18 }

        enMacStIngFifoOvfBytes  OBJECT-TYPE
            SYNTAX  Counter
            ACCESS  read-only
            STATUS  mandatory
            DESCRIPTION
                "WAN(VCG) MAC Ingress FIFO Overflow Bytes Counter"
            ::= { enetMacStatisticEntry 19 }


--
--  enetBcpStatisticTable
--
        enetBcpStatisticTable  OBJECT-TYPE
            SYNTAX  SEQUENCE OF  EnetBcpStatisticEntry
            ACCESS  not-accessible
            STATUS  mandatory
            DESCRIPTION
                "The Ethernet wan(vcg) BCP statistic table."
            ::= { enetWanVcgStatisticTable 4 }

        enetBcpStatisticEntry  OBJECT-TYPE
            SYNTAX  EnetBcpStatisticEntry
            ACCESS  not-accessible
            STATUS  mandatory
            DESCRIPTION
                "An entry in the Ethernet wan(vcg) BCP statistic table."
            INDEX { enBcpStUnit , enBcpStPort }
            ::= { enetBcpStatisticTable 1 }

        EnetBcpStatisticEntry ::= SEQUENCE {
            enBcpStUnit                 UnitID,
            enBcpStPort                 VcgPortNum,
            enBcpStRxFrames             Counter,
            enBcpStRxBytes              Counter,
            enBcpStRxAbortedFrames      Counter,
            enBcpStRxDroppedFrames      Counter,
            enBcpStRxErrFCSFrames       Counter,
            enBcpStRxTransErrFrames     Counter,
            enBcpStRxMaxLenVioFrm       Counter,
            enBcpStRxMinLenVioFrm       Counter,
            enBcpStRxFifoOvfFrames      Counter,
            enBcpStTxFrames             Counter,
            enBcpStTxBytes              Counter
        }

        enBcpStUnit  OBJECT-TYPE
            SYNTAX  UnitID
            ACCESS  read-only
            STATUS  mandatory
            DESCRIPTION
            "unit 1 to 4."
            ::= { enetBcpStatisticEntry 1 }

        enBcpStPort  OBJECT-TYPE
            SYNTAX  VcgPortNum
            ACCESS  read-only
            STATUS  mandatory
            DESCRIPTION
                "vcg port index: wan1~wan9"
            ::= { enetBcpStatisticEntry 2 }

        enBcpStRxFrames  OBJECT-TYPE
            SYNTAX  Counter
            ACCESS  read-only
            STATUS  mandatory
            DESCRIPTION
                "WAN(VCG) Rx Frames Counter"
            ::= { enetBcpStatisticEntry 3 }

        enBcpStRxBytes  OBJECT-TYPE
            SYNTAX  Counter
            ACCESS  read-only
            STATUS  mandatory
            DESCRIPTION
                "WAN(VCG) Rx Bytes Counter"
            ::= { enetBcpStatisticEntry 4 }

        enBcpStRxAbortedFrames  OBJECT-TYPE
            SYNTAX  Counter
            ACCESS  read-only
            STATUS  mandatory
            DESCRIPTION
                "WAN(VCG) Rx Aborted Frames Counter"
            ::= { enetBcpStatisticEntry 5 }

        enBcpStRxDroppedFrames  OBJECT-TYPE
            SYNTAX  Counter
            ACCESS  read-only
            STATUS  mandatory
            DESCRIPTION
                "WAN(VCG) Rx Dropped Frames Counter"
            ::= { enetBcpStatisticEntry 6 }

        enBcpStRxErrFCSFrames  OBJECT-TYPE
            SYNTAX  Counter
            ACCESS  read-only
            STATUS  mandatory
            DESCRIPTION
                "WAN(VCG) Rx Erred FCS Frames Counter"
            ::= { enetBcpStatisticEntry 7 }

        enBcpStRxTransErrFrames  OBJECT-TYPE
            SYNTAX  Counter
            ACCESS  read-only
            STATUS  mandatory
            DESCRIPTION
                "WAN(VCG) Rx Transparency Erred Frames Counter"
            ::= { enetBcpStatisticEntry 8 }

        enBcpStRxMaxLenVioFrm  OBJECT-TYPE
            SYNTAX  Counter
            ACCESS  read-only
            STATUS  mandatory
            DESCRIPTION
                "WAN(VCG) Rx Max Length Violation Frames Counter"
            ::= { enetBcpStatisticEntry 9 }

        enBcpStRxMinLenVioFrm  OBJECT-TYPE
            SYNTAX  Counter
            ACCESS  read-only
            STATUS  mandatory
            DESCRIPTION
                "WAN(VCG) Min Length Violation Frames Counter"
            ::= { enetBcpStatisticEntry 10 }

        enBcpStRxFifoOvfFrames  OBJECT-TYPE
            SYNTAX  Counter
            ACCESS  read-only
            STATUS  mandatory
            DESCRIPTION
                "WAN(VCG) Rx FIFO Overflow Frames Counter"
            ::= { enetBcpStatisticEntry 11 }

        enBcpStTxFrames  OBJECT-TYPE
            SYNTAX  Counter
            ACCESS  read-only
            STATUS  mandatory
            DESCRIPTION
                "WAN(VCG) Tx Frames Counter"
            ::= { enetBcpStatisticEntry 12 }

        enBcpStTxBytes  OBJECT-TYPE
            SYNTAX  Counter
            ACCESS  read-only
            STATUS  mandatory
            DESCRIPTION
                "WAN(VCG) Tx Bytes Counter"
            ::= { enetBcpStatisticEntry 13 }

--
--   enetLedStatusTable
--
        enetLedStatusTable  OBJECT-TYPE
            SYNTAX  SEQUENCE OF  EnetLedStatusEntry
            ACCESS  not-accessible
            STATUS  mandatory
            DESCRIPTION
                "The Ethernet LED Status Table."
            ::= { enet-card 8 }

        enetLedStatusEntry  OBJECT-TYPE
            SYNTAX  EnetLedStatusEntry
            ACCESS  not-accessible
            STATUS  mandatory
            DESCRIPTION
                "An entry in the Ethernet LED Status Table."
            INDEX { enLedStaUnit }
            ::= { enetLedStatusTable 1 }

        EnetLedStatusEntry ::= SEQUENCE {
            enLedStaUnit                UnitID,
            enLedStaActiveLED           LedStatusType,
            enLedStaTestLED             LedStatusType,
            enLedStaAlarmLED            LedStatusType
        }

        enLedStaUnit  OBJECT-TYPE
            SYNTAX  UnitID
            ACCESS  read-only
            STATUS  mandatory
            DESCRIPTION
            "unit 1 to 4."
            ::= { enetLedStatusEntry 1 }

        enLedStaActiveLED  OBJECT-TYPE
            SYNTAX  LedStatusType
            ACCESS  read-only
            STATUS  mandatory
            DESCRIPTION
                "Active LED status"
            ::= { enetLedStatusEntry 2 }

        enLedStaTestLED  OBJECT-TYPE
            SYNTAX  LedStatusType
            ACCESS  read-only
            STATUS  mandatory
            DESCRIPTION
                "Test LED status"
            ::= { enetLedStatusEntry 3 }

        enLedStaAlarmLED  OBJECT-TYPE
            SYNTAX  LedStatusType
            ACCESS  read-only
            STATUS  mandatory
            DESCRIPTION
                "Alarm LED status"
            ::= { enetLedStatusEntry 4 }

--
--  ethernet card switch table
--
    enetSwitchTable          OBJECT IDENTIFIER ::= { enet-card 10 }

--
--  enetSwStatisticTable
--
        enetSwStatisticTable  OBJECT-TYPE
            SYNTAX  SEQUENCE OF  EnetSwStatisticEntry
            ACCESS  not-accessible
            STATUS  mandatory
            DESCRIPTION
                "The Ethernet Switch Statistic Table."
            ::= { enetSwitchTable 1 }

        enetSwStatisticEntry  OBJECT-TYPE
            SYNTAX  EnetSwStatisticEntry
            ACCESS  not-accessible
            STATUS  mandatory
            DESCRIPTION
                "An entry in the Ethernet Switch Statistic Table."
            INDEX { enSwStUnit , enSwStPort }
            ::= { enetSwStatisticTable 1 }

        EnetSwStatisticEntry ::= SEQUENCE {
            enSwStUnit                  UnitID,
            enSwStPort                  SwPortNum,
            enSwStDropEvent             Counter,
            enSwStOctets                Counter,
            enSwStPkts                  Counter,
            enSwStBroadcastPkts         Counter,
            enSwStMulticastPkts         Counter,
            enSwStCRCAlignErrors        Counter,
            enSwStUndersizePkts         Counter,
            enSwStOversize-Jabbers      Counter,
            enSwStFragments             Counter,
            enSwStCollisions            Counter,
            enSwSt64Octets              Counter,
            enSwSt65to127Octets         Counter,
            enSwSt128to255Octets        Counter,
            enSwSt256to511Octets        Counter,
            enSwSt512to1023Octets       Counter,
            enSwSt1024to1522Octets      Counter,
            enSwStOctetsSend            Counter,
            enSwStUnicastPktsSend       Counter,
            enSwStNonUnicastPktsSend    Counter,
            enSwStFlowCtrlPktsSend      Counter
        }

        enSwStUnit  OBJECT-TYPE
            SYNTAX  UnitID
            ACCESS  read-only
            STATUS  mandatory
            DESCRIPTION
            "unit 1 to 4."
            ::= { enetSwStatisticEntry 1 }

        enSwStPort  OBJECT-TYPE
            SYNTAX  SwPortNum
            ACCESS  read-only
            STATUS  mandatory
            DESCRIPTION
                "Port WAN1~9, LAN1~9."
            ::= { enetSwStatisticEntry 2 }

        enSwStDropEvent  OBJECT-TYPE
            SYNTAX  Counter
            ACCESS  read-only
            STATUS  mandatory
            DESCRIPTION
                "DropEvent Statistics"
            ::= { enetSwStatisticEntry 3 }

        enSwStOctets  OBJECT-TYPE
            SYNTAX  Counter
            ACCESS  read-only
            STATUS  mandatory
            DESCRIPTION
                "Octets Statistics"
            ::= { enetSwStatisticEntry 4 }

        enSwStPkts  OBJECT-TYPE
            SYNTAX  Counter
            ACCESS  read-only
            STATUS  mandatory
            DESCRIPTION
                "Pkts Statistics"
            ::= { enetSwStatisticEntry 5 }

        enSwStBroadcastPkts  OBJECT-TYPE
            SYNTAX  Counter
            ACCESS  read-only
            STATUS  mandatory
            DESCRIPTION
                "Broadcast Pkts Statistics"
            ::= { enetSwStatisticEntry 6 }

        enSwStMulticastPkts  OBJECT-TYPE
            SYNTAX  Counter
            ACCESS  read-only
            STATUS  mandatory
            DESCRIPTION
                "Multicast Pkts Statistics"
            ::= { enetSwStatisticEntry 7 }

        enSwStCRCAlignErrors  OBJECT-TYPE
            SYNTAX  Counter
            ACCESS  read-only
            STATUS  mandatory
            DESCRIPTION
                "CRC Align Errors Statistics"
            ::= { enetSwStatisticEntry 8 }

        enSwStUndersizePkts  OBJECT-TYPE
            SYNTAX  Counter
            ACCESS  read-only
            STATUS  mandatory
            DESCRIPTION
                "Undersize Pkts Statistics"
            ::= { enetSwStatisticEntry 9 }

        enSwStOversize-Jabbers  OBJECT-TYPE
            SYNTAX  Counter
            ACCESS  read-only
            STATUS  mandatory
            DESCRIPTION
                "Oversize Pkts/Jabbers Statistics"
            ::= { enetSwStatisticEntry 10 }

        enSwStFragments  OBJECT-TYPE
            SYNTAX  Counter
            ACCESS  read-only
            STATUS  mandatory
            DESCRIPTION
                "Fragments Statistics"
            ::= { enetSwStatisticEntry 11 }

        enSwStCollisions  OBJECT-TYPE
            SYNTAX  Counter
            ACCESS  read-only
            STATUS  mandatory
            DESCRIPTION
                "Collisions Statistics"
            ::= { enetSwStatisticEntry 12 }

        enSwSt64Octets  OBJECT-TYPE
            SYNTAX  Counter
            ACCESS  read-only
            STATUS  mandatory
            DESCRIPTION
                "Pkts 64 Octets Statistics"
            ::= { enetSwStatisticEntry 13 }

        enSwSt65to127Octets  OBJECT-TYPE
            SYNTAX  Counter
            ACCESS  read-only
            STATUS  mandatory
            DESCRIPTION
                "Pkts 65 to 127 Octets Statistics"
            ::= { enetSwStatisticEntry 14 }

        enSwSt128to255Octets  OBJECT-TYPE
            SYNTAX  Counter
            ACCESS  read-only
            STATUS  mandatory
            DESCRIPTION
                "Pkts 128 to 255 Octets Statistics"
            ::= { enetSwStatisticEntry 15 }

        enSwSt256to511Octets  OBJECT-TYPE
            SYNTAX  Counter
            ACCESS  read-only
            STATUS  mandatory
            DESCRIPTION
                "Pkts 256 to 511 Octets Statistics"
            ::= { enetSwStatisticEntry 16 }

        enSwSt512to1023Octets  OBJECT-TYPE
            SYNTAX  Counter
            ACCESS  read-only
            STATUS  mandatory
            DESCRIPTION
                "Pkts 512 to 1023 Octets Statistics"
            ::= { enetSwStatisticEntry 17 }

        enSwSt1024to1522Octets  OBJECT-TYPE
            SYNTAX  Counter
            ACCESS  read-only
            STATUS  mandatory
            DESCRIPTION
                "Pkts 1024 to 1522 Octets Statistics"
            ::= { enetSwStatisticEntry 18 }

        enSwStOctetsSend  OBJECT-TYPE
            SYNTAX  Counter
            ACCESS  read-only
            STATUS  mandatory
            DESCRIPTION
                "Octets Send Statistics"
            ::= { enetSwStatisticEntry 19 }

        enSwStUnicastPktsSend  OBJECT-TYPE
            SYNTAX  Counter
            ACCESS  read-only
            STATUS  mandatory
            DESCRIPTION
                "Unicast Pkts Send Statistics"
            ::= { enetSwStatisticEntry 20 }

        enSwStNonUnicastPktsSend  OBJECT-TYPE
            SYNTAX  Counter
            ACCESS  read-only
            STATUS  mandatory
            DESCRIPTION
                "Non-Unicast Pkts Send Statistics"
            ::= { enetSwStatisticEntry 21 }

        enSwStFlowCtrlPktsSend  OBJECT-TYPE
            SYNTAX  Counter
            ACCESS  read-only
            STATUS  mandatory
            DESCRIPTION
                "Flow Control Pkts Send Statistics"
            ::= { enetSwStatisticEntry 22 }

--
--  ethernet card vlan table
--
    enetVlanTable           OBJECT IDENTIFIER ::= { enetSwitchTable 2 }

    vlanSetupTable    OBJECT IDENTIFIER ::= { enetVlanTable 1 }

        enetVlanTableUnit   OBJECT-TYPE
            SYNTAX  UnitID
            ACCESS  read-write
            STATUS  mandatory
            DESCRIPTION
                " unit"
            ::= { vlanSetupTable 1 }

        enetVlanTableVlanID   OBJECT-TYPE
            SYNTAX  INTEGER (1..4094)
            ACCESS  read-write
            STATUS  mandatory
            DESCRIPTION
                " Vlan ID"
            ::= { vlanSetupTable 2 }

        enetVlanTableValid   OBJECT-TYPE
            SYNTAX  INTEGER {
                    no-action(0),
                    invalid(1),
                    valid(2)
                }
            ACCESS  read-write
            STATUS  mandatory
            DESCRIPTION
                "Vlan entry valid/inalid"
            ::= { vlanSetupTable 3 }

        enetVlanWan1Port   OBJECT-TYPE
            SYNTAX  INTEGER {
                    no-action(0),
                    off(1),
                    on(2)
                }
            ACCESS  read-write
            STATUS  mandatory
            DESCRIPTION
                " Vlan wan1 entry"
            ::= { vlanSetupTable 4 }

        enetVlanWan2Port   OBJECT-TYPE
            SYNTAX  INTEGER {
                    no-action(0),
                    off(1),
                    on(2)
                }
            ACCESS  read-write
            STATUS  mandatory
            DESCRIPTION
                " Vlan wan2 entry"
            ::= { vlanSetupTable 5 }

        enetVlanWan3Port   OBJECT-TYPE
            SYNTAX  INTEGER {
                    no-action(0),
                    off(1),
                    on(2)
                }
            ACCESS  read-write
            STATUS  mandatory
            DESCRIPTION
                " Vlan wan3 entry"
            ::= { vlanSetupTable 6 }

        enetVlanWan4Port   OBJECT-TYPE
            SYNTAX  INTEGER {
                    no-action(0),
                    off(1),
                    on(2)
                }
            ACCESS  read-write
            STATUS  mandatory
            DESCRIPTION
                " Vlan wan4 entry"
            ::= { vlanSetupTable 7 }

        enetVlanWan5Port   OBJECT-TYPE
            SYNTAX  INTEGER {
                    no-action(0),
                    off(1),
                    on(2)
                }
            ACCESS  read-write
            STATUS  mandatory
            DESCRIPTION
                " Vlan wan5 entry"
            ::= { vlanSetupTable 8 }

        enetVlanWan6Port   OBJECT-TYPE
            SYNTAX  INTEGER {
                    no-action(0),
                    off(1),
                    on(2)
                }
            ACCESS  read-write
            STATUS  mandatory
            DESCRIPTION
                " Vlan wan6 entry"
            ::= { vlanSetupTable 9 }

        enetVlanWan7Port   OBJECT-TYPE
            SYNTAX  INTEGER {
                    no-action(0),
                    off(1),
                    on(2)
                }
            ACCESS  read-write
            STATUS  mandatory
            DESCRIPTION
                " Vlan wan7 entry"
            ::= { vlanSetupTable 10 }

        enetVlanWan8Port   OBJECT-TYPE
            SYNTAX  INTEGER {
                    no-action(0),
                    off(1),
                    on(2)
                }
            ACCESS  read-write
            STATUS  mandatory
            DESCRIPTION
                " Vlan wan8 entry"
            ::= { vlanSetupTable 11 }

        enetVlanWan9Port   OBJECT-TYPE
            SYNTAX  INTEGER {
                    no-action(0),
                    off(1),
                    on(2)
                }
            ACCESS  read-write
            STATUS  mandatory
            DESCRIPTION
                " Vlan wan9 entry"
            ::= { vlanSetupTable 12 }

        enetVlanLan1Port   OBJECT-TYPE
            SYNTAX  INTEGER {
                    no-action(0),
                    off(1),
                    on(2)
                }
            ACCESS  read-write
            STATUS  mandatory
            DESCRIPTION
                " Vlan lan1 entry"
            ::= { vlanSetupTable 13 }

        enetVlanLan2Port   OBJECT-TYPE
            SYNTAX  INTEGER {
                    no-action(0),
                    off(1),
                    on(2)
                }
            ACCESS  read-write
            STATUS  mandatory
            DESCRIPTION
                " Vlan lan2 entry"
            ::= { vlanSetupTable 14 }

        enetVlanLan3Port   OBJECT-TYPE
            SYNTAX  INTEGER {
                    no-action(0),
                    off(1),
                    on(2)
                }
            ACCESS  read-write
            STATUS  mandatory
            DESCRIPTION
                " Vlan lan3 entry"
            ::= { vlanSetupTable 15 }

        enetVlanLan4Port   OBJECT-TYPE
            SYNTAX  INTEGER {
                    no-action(0),
                    off(1),
                    on(2)
                }
            ACCESS  read-write
            STATUS  mandatory
            DESCRIPTION
                " Vlan lan4 entry"
            ::= { vlanSetupTable 16 }

        enetVlanLan5Port   OBJECT-TYPE
            SYNTAX  INTEGER {
                    no-action(0),
                    off(1),
                    on(2)
                }
            ACCESS  read-write
            STATUS  mandatory
            DESCRIPTION
                " Vlan lan5 entry"
            ::= { vlanSetupTable 17 }

        enetVlanLan6Port   OBJECT-TYPE
            SYNTAX  INTEGER {
                    no-action(0),
                    off(1),
                    on(2)
                }
            ACCESS  read-write
            STATUS  mandatory
            DESCRIPTION
                " Vlan lan6 entry"
            ::= { vlanSetupTable 18 }

        enetVlanLan7Port   OBJECT-TYPE
            SYNTAX  INTEGER {
                    no-action(0),
                    off(1),
                    on(2)
                }
            ACCESS  read-write
            STATUS  mandatory
            DESCRIPTION
                " Vlan lan7 entry"
            ::= { vlanSetupTable 19 }

        enetVlanLan8Port   OBJECT-TYPE
            SYNTAX  INTEGER {
                    no-action(0),
                    off(1),
                    on(2)
                }
            ACCESS  read-write
            STATUS  mandatory
            DESCRIPTION
                " Vlan lan8 entry"
            ::= { vlanSetupTable 20 }

        enetVlanLan9Port   OBJECT-TYPE
            SYNTAX  INTEGER {
                    no-action(0),
                    off(1),
                    on(2)
                }
            ACCESS  read-write
            STATUS  mandatory
            DESCRIPTION
                " Vlan lan9 entry"
            ::= { vlanSetupTable 21 }

        enetVlanFilterBroadcast   OBJECT-TYPE
            SYNTAX  INTEGER {
                    no-action(0),
                    off(1),
                    on(2)
                }
            ACCESS  read-write
            STATUS  mandatory
            DESCRIPTION
                " Vlan filter broadcast"
            ::= { vlanSetupTable 22 }


        enetVlanEntryCmd   OBJECT-TYPE
            SYNTAX  INTEGER {
                    get(1),
                    set(2),
                    result-fail(3),
                    result-ok(4)
                }
            ACCESS  read-write
            STATUS  mandatory
            DESCRIPTION
                " command and result for this vlan entry"
            ::= { vlanSetupTable 23 }


--
--  VLAN port association table
--
        vlanPortAssociateTbl  OBJECT-TYPE
            SYNTAX  SEQUENCE OF VlanPortAssociateEntry
            ACCESS  not-accessible
            STATUS  mandatory
            DESCRIPTION
                "VLAN port association table"
            ::= { enetVlanTable 2  }

        vlanPortAssociateEntry  OBJECT-TYPE
            SYNTAX  VlanPortAssociateEntry
            ACCESS  not-accessible
            STATUS  mandatory
            DESCRIPTION
                "An entry in the VLAN port association table."
            INDEX { vlanPatUnit , vlanPatVlanId }
            ::= { vlanPortAssociateTbl 1 }

        VlanPortAssociateEntry ::= SEQUENCE {
            vlanPatUnit                 UnitID,
            vlanPatVlanId               INTEGER,
            vlanPatWan1Port             INTEGER,
            vlanPatWan2Port             INTEGER,
            vlanPatWan3Port             INTEGER,
            vlanPatWan4Port             INTEGER,
            vlanPatWan5Port             INTEGER,
            vlanPatWan6Port             INTEGER,
            vlanPatWan7Port             INTEGER,
            vlanPatWan8Port             INTEGER,
            vlanPatWan9Port             INTEGER,
            vlanPatLan1Port             INTEGER,
            vlanPatLan2Port             INTEGER,
            vlanPatLan3Port             INTEGER,
            vlanPatLan4Port             INTEGER,
            vlanPatLan5Port             INTEGER,
            vlanPatLan6Port             INTEGER,
            vlanPatLan7Port             INTEGER,
            vlanPatLan8Port             INTEGER,
            vlanPatLan9Port             INTEGER,
            vlanPatFilterBroadcast      INTEGER
        }

        vlanPatUnit OBJECT-TYPE
            SYNTAX  UnitID
            ACCESS  read-only
            STATUS  mandatory
            DESCRIPTION
                "Unit"
            ::= {  vlanPortAssociateEntry 1 }

        vlanPatVlanId OBJECT-TYPE
            SYNTAX  INTEGER (1..4094)
            ACCESS  read-only
            STATUS  mandatory
            DESCRIPTION
                "vlan ID 1~4094"
            ::= { vlanPortAssociateEntry 2 }

        vlanPatWan1Port  OBJECT-TYPE
            SYNTAX  INTEGER {
                    off(1),
                    on(2),
                    not-available(100)
                }
            ACCESS  read-only
            STATUS  mandatory
            DESCRIPTION
                "vlan port wan1"
            ::= { vlanPortAssociateEntry  3 }

        vlanPatWan2Port  OBJECT-TYPE
            SYNTAX  INTEGER {
                    off(1),
                    on(2),
                    not-available(100)
                }
            ACCESS  read-only
            STATUS  mandatory
            DESCRIPTION
                "vlan port wan2"
            ::= { vlanPortAssociateEntry  4 }

        vlanPatWan3Port  OBJECT-TYPE
            SYNTAX  INTEGER {
                    off(1),
                    on(2),
                    not-available(100)
                }
            ACCESS  read-only
            STATUS  mandatory
            DESCRIPTION
                "vlan port wan3"
            ::= { vlanPortAssociateEntry  5 }

        vlanPatWan4Port  OBJECT-TYPE
            SYNTAX  INTEGER {
                    off(1),
                    on(2),
                    not-available(100)
                }
            ACCESS  read-only
            STATUS  mandatory
            DESCRIPTION
                "vlan port wan4"
            ::= { vlanPortAssociateEntry  6 }

        vlanPatWan5Port  OBJECT-TYPE
            SYNTAX  INTEGER {
                    off(1),
                    on(2),
                    not-available(100)
                }
            ACCESS  read-only
            STATUS  mandatory
            DESCRIPTION
                "vlan port wan5"
            ::= { vlanPortAssociateEntry  7 }

        vlanPatWan6Port  OBJECT-TYPE
            SYNTAX  INTEGER {
                    off(1),
                    on(2),
                    not-available(100)
                }
            ACCESS  read-only
            STATUS  mandatory
            DESCRIPTION
                "vlan port wan6"
            ::= { vlanPortAssociateEntry  8 }

        vlanPatWan7Port  OBJECT-TYPE
            SYNTAX  INTEGER {
                    off(1),
                    on(2),
                    not-available(100)
                }
            ACCESS  read-only
            STATUS  mandatory
            DESCRIPTION
                "vlan port wan7"
            ::= { vlanPortAssociateEntry  9 }

        vlanPatWan8Port  OBJECT-TYPE
            SYNTAX  INTEGER {
                    off(1),
                    on(2),
                    not-available(100)
                }
            ACCESS  read-only
            STATUS  mandatory
            DESCRIPTION
                "vlan port wan8"
            ::= { vlanPortAssociateEntry  10 }

        vlanPatWan9Port  OBJECT-TYPE
            SYNTAX  INTEGER {
                    off(1),
                    on(2),
                    not-available(100)
                }
            ACCESS  read-only
            STATUS  mandatory
            DESCRIPTION
                "vlan port wan9"
            ::= { vlanPortAssociateEntry  11 }

        vlanPatLan1Port  OBJECT-TYPE
            SYNTAX  INTEGER {
                    off(1),
                    on(2),
                    not-available(100)
                }
            ACCESS  read-only
            STATUS  mandatory
            DESCRIPTION
                "vlan port lan1"
            ::= { vlanPortAssociateEntry  12 }

        vlanPatLan2Port  OBJECT-TYPE
            SYNTAX  INTEGER {
                    off(1),
                    on(2),
                    not-available(100)
                }
            ACCESS  read-only
            STATUS  mandatory
            DESCRIPTION
                "vlan port lan2"
            ::= { vlanPortAssociateEntry  13 }

        vlanPatLan3Port  OBJECT-TYPE
            SYNTAX  INTEGER {
                    off(1),
                    on(2),
                    not-available(100)
                }
            ACCESS  read-only
            STATUS  mandatory
            DESCRIPTION
                "vlan port lan3"
            ::= { vlanPortAssociateEntry  14 }

        vlanPatLan4Port  OBJECT-TYPE
            SYNTAX  INTEGER {
                    off(1),
                    on(2),
                    not-available(100)
                }
            ACCESS  read-only
            STATUS  mandatory
            DESCRIPTION
                "vlan port lan4"
            ::= { vlanPortAssociateEntry  15 }

        vlanPatLan5Port  OBJECT-TYPE
            SYNTAX  INTEGER {
                    off(1),
                    on(2),
                    not-available(100)
                }
            ACCESS  read-only
            STATUS  mandatory
            DESCRIPTION
                "vlan port lan5"
            ::= { vlanPortAssociateEntry  16 }

        vlanPatLan6Port  OBJECT-TYPE
            SYNTAX  INTEGER {
                    off(1),
                    on(2),
                    not-available(100)
                }
            ACCESS  read-only
            STATUS  mandatory
            DESCRIPTION
                "vlan port lan6"
            ::= { vlanPortAssociateEntry  17 }

        vlanPatLan7Port  OBJECT-TYPE
            SYNTAX  INTEGER {
                    off(1),
                    on(2),
                    not-available(100)
                }
            ACCESS  read-only
            STATUS  mandatory
            DESCRIPTION
                "vlan port lan7"
            ::= { vlanPortAssociateEntry  18 }

        vlanPatLan8Port  OBJECT-TYPE
            SYNTAX  INTEGER {
                    off(1),
                    on(2),
                    not-available(100)
                }
            ACCESS  read-only
            STATUS  mandatory
            DESCRIPTION
                "vlan port lan8"
            ::= { vlanPortAssociateEntry  19 }

        vlanPatLan9Port  OBJECT-TYPE
            SYNTAX  INTEGER {
                    off(1),
                    on(2),
                    not-available(100)
                }
            ACCESS  read-only
            STATUS  mandatory
            DESCRIPTION
                "vlan port lan9"
            ::= { vlanPortAssociateEntry  20 }

        vlanPatFilterBroadcast  OBJECT-TYPE
            SYNTAX  INTEGER {
                    off(1),
                    on(2),
                    not-available(100)
                }
            ACCESS  read-only
            STATUS  mandatory
            DESCRIPTION
                "filter broadcast"
            ::= { vlanPortAssociateEntry  21 }

--
--  VLAN port configuration
--
        vlanPortCfgTable  OBJECT-TYPE
            SYNTAX  SEQUENCE OF VlanPortCfgEntry
            ACCESS  not-accessible
            STATUS  mandatory
            DESCRIPTION
                "vlan port configuration table"
            ::= { enetVlanTable  3  }

        vlanPortCfgEntry  OBJECT-TYPE
            SYNTAX  VlanPortCfgEntry
            ACCESS  not-accessible
            STATUS  mandatory
            DESCRIPTION
                "vlan port configuration entry"
            INDEX { vlanPortCfgUnit , vlanPortCfgPort }
            ::= { vlanPortCfgTable 1 }

        VlanPortCfgEntry ::= SEQUENCE {
            vlanPortCfgUnit             UnitID,
            vlanPortCfgPort             INTEGER,
            vlanPortCfgVlanID           INTEGER,
            vlanPortCfgUntagOut         INTEGER
        }

        vlanPortCfgUnit OBJECT-TYPE
            SYNTAX  UnitID
            ACCESS  read-only
            STATUS  mandatory
            DESCRIPTION
                "Unit"
            ::= {  vlanPortCfgEntry 1 }

        vlanPortCfgPort OBJECT-TYPE
            SYNTAX  INTEGER{
                    wan1(1),
                    wan2(2),
                    wan3(3),
                    wan4(4),
                    wan5(5),
                    wan6(6),
                    wan7(7),
                    wan8(8),
                    wan9(9),
                    lan1(10),
                    lan2(11),
                    lan3(12),
                    lan4(13),
                    lan5(14),
                    lan6(15),
                    lan7(16),
                    lan8(17),
                    lan9(18)
                }
            ACCESS  read-only
            STATUS  mandatory
            DESCRIPTION
                "Port WAN1~9, LAN1~9 "
            ::= {  vlanPortCfgEntry 2 }

        vlanPortCfgVlanID OBJECT-TYPE
            SYNTAX  INTEGER (1..4094)
            ACCESS  read-write
            STATUS  mandatory
            DESCRIPTION
                "default vlan ID of the port"
            ::= { vlanPortCfgEntry  3 }

        vlanPortCfgUntagOut  OBJECT-TYPE
            SYNTAX  INTEGER {
                    disable(1),
                    enable(2)
                }
            ACCESS  read-write
            STATUS  mandatory
            DESCRIPTION
                "vlan port tag-out or untag-out"
            ::= { vlanPortCfgEntry  4 }

--
--  vlanTPIDTable     OBJECT IDENTIFIER ::= { enetVlanTable 4 }
--
        vlanTPIDTable  OBJECT-TYPE
            SYNTAX  SEQUENCE OF  VlanTPIDEntry
            ACCESS  not-accessible
            STATUS  mandatory
            DESCRIPTION
                "The Ethernet VLAN Tag Protocol ID Table."
            ::= { enetVlanTable 4 }

        vlanTPIDEntry  OBJECT-TYPE
            SYNTAX  VlanTPIDEntry
            ACCESS  not-accessible
            STATUS  mandatory
            DESCRIPTION
                "An entry in The Ethernet VLAN Tag Protocol ID Table."
            INDEX { vlanTPIDUnit }
            ::= { vlanTPIDTable 1 }

        VlanTPIDEntry ::= SEQUENCE {
            vlanTPIDUnit                UnitID,
            vlanTPIDTPID                OCTET STRING
        }

        vlanTPIDUnit  OBJECT-TYPE
            SYNTAX  UnitID
            ACCESS  read-only
            STATUS  mandatory
            DESCRIPTION
            "unit 1 to 4."
            ::= { vlanTPIDEntry 1 }

        vlanTPIDTPID  OBJECT-TYPE
            SYNTAX  OCTET STRING(SIZE(2))
            ACCESS  read-write
            STATUS  mandatory
            DESCRIPTION
                "VLAN Tag Protocol ID"
            ::= { vlanTPIDEntry 2 }

--
--  enetPortmapTable
--
        enetPortmapTable  OBJECT-TYPE
            SYNTAX  SEQUENCE OF  EnetPortmapEntry
            ACCESS  not-accessible
            STATUS  mandatory
            DESCRIPTION
                "The Ethernet Port Map Table."
            ::= { enetSwitchTable 3 }

        enetPortmapEntry  OBJECT-TYPE
            SYNTAX  EnetPortmapEntry
            ACCESS  not-accessible
            STATUS  mandatory
            DESCRIPTION
                "An entry in The Ethernet Port Map Table."
            INDEX { enPortMapUnit , enPortMapPort }
            ::= { enetPortmapTable 1 }

        EnetPortmapEntry ::= SEQUENCE {
            enPortMapUnit               UnitID,
            enPortMapPort               SwPortNum,
            enPortMapDesWan1            INTEGER,
            enPortMapDesWan2            INTEGER,
            enPortMapDesWan3            INTEGER,
            enPortMapDesWan4            INTEGER,
            enPortMapDesWan5            INTEGER,
            enPortMapDesWan6            INTEGER,
            enPortMapDesWan7            INTEGER,
            enPortMapDesWan8            INTEGER,
            enPortMapDesWan9            INTEGER,
            enPortMapDesLan1            INTEGER,
            enPortMapDesLan2            INTEGER,
            enPortMapDesLan3            INTEGER,
            enPortMapDesLan4            INTEGER,
            enPortMapDesLan5            INTEGER,
            enPortMapDesLan6            INTEGER,
            enPortMapDesLan7            INTEGER,
            enPortMapDesLan8            INTEGER,
            enPortMapDesLan9            INTEGER
        }

        enPortMapUnit  OBJECT-TYPE
            SYNTAX  UnitID
            ACCESS  read-only
            STATUS  mandatory
            DESCRIPTION
            "unit 1 to 4."
            ::= { enetPortmapEntry 1 }

        enPortMapPort  OBJECT-TYPE
            SYNTAX  SwPortNum
            ACCESS  read-only
            STATUS  mandatory
            DESCRIPTION
                "LAN port index: LAN1~LAN9"
            ::= { enetPortmapEntry 2 }

        enPortMapDesWan1  OBJECT-TYPE
            SYNTAX  INTEGER {
                    off(1),
                    on(2)
                }
            ACCESS  read-write
            STATUS  mandatory
            DESCRIPTION
                "Port Map to WAN1 ON/OFF"
            ::= { enetPortmapEntry 3 }

        enPortMapDesWan2  OBJECT-TYPE
            SYNTAX  INTEGER {
                    off(1),
                    on(2)
                }
            ACCESS  read-write
            STATUS  mandatory
            DESCRIPTION
                "Port Map to WAN2 ON/OFF"
            ::= { enetPortmapEntry 4 }

        enPortMapDesWan3  OBJECT-TYPE
            SYNTAX  INTEGER {
                    off(1),
                    on(2)
                }
            ACCESS  read-write
            STATUS  mandatory
            DESCRIPTION
                "Port Map to WAN3 ON/OFF"
            ::= { enetPortmapEntry 5 }

        enPortMapDesWan4  OBJECT-TYPE
            SYNTAX  INTEGER {
                    off(1),
                    on(2)
                }
            ACCESS  read-write
            STATUS  mandatory
            DESCRIPTION
                "Port Map to WAN4 ON/OFF"
            ::= { enetPortmapEntry 6 }

        enPortMapDesWan5  OBJECT-TYPE
            SYNTAX  INTEGER {
                    off(1),
                    on(2)
                }
            ACCESS  read-write
            STATUS  mandatory
            DESCRIPTION
                "Port Map to WAN5 ON/OFF"
            ::= { enetPortmapEntry 7 }

        enPortMapDesWan6  OBJECT-TYPE
            SYNTAX  INTEGER {
                    off(1),
                    on(2)
                }
            ACCESS  read-write
            STATUS  mandatory
            DESCRIPTION
                "Port Map to WAN6 ON/OFF"
            ::= { enetPortmapEntry 8 }

        enPortMapDesWan7  OBJECT-TYPE
            SYNTAX  INTEGER {
                    off(1),
                    on(2)
                }
            ACCESS  read-write
            STATUS  mandatory
            DESCRIPTION
                "Port Map to WAN7 ON/OFF"
            ::= { enetPortmapEntry 9 }

        enPortMapDesWan8  OBJECT-TYPE
            SYNTAX  INTEGER {
                    off(1),
                    on(2)
                }
            ACCESS  read-write
            STATUS  mandatory
            DESCRIPTION
                "Port Map to WAN8 ON/OFF"
            ::= { enetPortmapEntry 10 }

        enPortMapDesWan9  OBJECT-TYPE
            SYNTAX  INTEGER {
                    off(1),
                    on(2)
                }
            ACCESS  read-write
            STATUS  mandatory
            DESCRIPTION
                "Port Map to WAN9 ON/OFF"
            ::= { enetPortmapEntry 11 }

        enPortMapDesLan1  OBJECT-TYPE
            SYNTAX  INTEGER {
                    off(1),
                    on(2)
                }
            ACCESS  read-write
            STATUS  mandatory
            DESCRIPTION
                "Port Map to LAN1 ON/OFF"
            ::= { enetPortmapEntry 12 }

        enPortMapDesLan2  OBJECT-TYPE
            SYNTAX  INTEGER {
                    off(1),
                    on(2)
                }
            ACCESS  read-write
            STATUS  mandatory
            DESCRIPTION
                "Port Map to LAN2 ON/OFF"
            ::= { enetPortmapEntry 13 }

        enPortMapDesLan3  OBJECT-TYPE
            SYNTAX  INTEGER {
                    off(1),
                    on(2)
                }
            ACCESS  read-write
            STATUS  mandatory
            DESCRIPTION
                "Port Map to LAN3 ON/OFF"
            ::= { enetPortmapEntry 14 }

        enPortMapDesLan4  OBJECT-TYPE
            SYNTAX  INTEGER {
                    off(1),
                    on(2)
                }
            ACCESS  read-write
            STATUS  mandatory
            DESCRIPTION
                "Port Map to LAN4 ON/OFF"
            ::= { enetPortmapEntry 15 }

        enPortMapDesLan5  OBJECT-TYPE
            SYNTAX  INTEGER {
                    off(1),
                    on(2)
                }
            ACCESS  read-write
            STATUS  mandatory
            DESCRIPTION
                "Port Map to LAN5 ON/OFF"
            ::= { enetPortmapEntry 16 }

        enPortMapDesLan6  OBJECT-TYPE
            SYNTAX  INTEGER {
                    off(1),
                    on(2)
                }
            ACCESS  read-write
            STATUS  mandatory
            DESCRIPTION
                "Port Map to LAN6 ON/OFF"
            ::= { enetPortmapEntry 17 }

        enPortMapDesLan7  OBJECT-TYPE
            SYNTAX  INTEGER {
                    off(1),
                    on(2)
                }
            ACCESS  read-write
            STATUS  mandatory
            DESCRIPTION
                "Port Map to LAN7 ON/OFF"
            ::= { enetPortmapEntry 18 }

        enPortMapDesLan8  OBJECT-TYPE
            SYNTAX  INTEGER {
                    off(1),
                    on(2)
                }
            ACCESS  read-write
            STATUS  mandatory
            DESCRIPTION
                "Port Map to LAN8 ON/OFF"
            ::= { enetPortmapEntry 19 }

        enPortMapDesLan9  OBJECT-TYPE
            SYNTAX  INTEGER {
                    off(1),
                    on(2)
                }
            ACCESS  read-write
            STATUS  mandatory
            DESCRIPTION
                "Port Map to LAN9 ON/OFF"
            ::= { enetPortmapEntry 20 }

--
--  enetRstpTable
--
    enetRstpTable       OBJECT IDENTIFIER ::= { enetSwitchTable 4 }

--
--  enetV1RstpBrgInfoTab
--
        enetV1RstpBrgInfoTab  OBJECT-TYPE
            SYNTAX  SEQUENCE OF  EnetV1RstpBrgInfoEntry
            ACCESS  not-accessible
            STATUS  mandatory
            DESCRIPTION
                "The Ethernet RSTP bridge info Table for V1.xx.xx."
            ::= { enetRstpTable 1 }

        enetV1RstpBrgInfoEntry  OBJECT-TYPE
            SYNTAX  EnetV1RstpBrgInfoEntry
            ACCESS  not-accessible
            STATUS  mandatory
            DESCRIPTION
                "An entry in The Ethernet RSTP bridge info Table for V1.xx.xx."
            INDEX { enBrgInfoUnit }
            ::= { enetV1RstpBrgInfoTab 1 }

        EnetV1RstpBrgInfoEntry ::= SEQUENCE {
            enBrgInfoUnit               UnitID,
            enBrgInfoRstpEnable         INTEGER,
            enBrgInfoRootMacAddr        DisplayString,
            enBrgInfoRootPriority       INTEGER,
            enBrgInfoRootCost           INTEGER,
            enBrgInfoRootMaxAge         INTEGER,
            enBrgInfoRootHelloTime      INTEGER,
            enBrgInfoRootFwdDelay       INTEGER,
            enBrgInfoBrgMacAddr         DisplayString,
            enBrgInfoBrgPriority        INTEGER,
            enBrgInfoBrgMaxAge          INTEGER,
            enBrgInfoBrgHelloTime       INTEGER,
            enBrgInfoBrgFwdDelay        INTEGER,
            enBrgInfoBrgAgingTime       INTEGER
        }

        enBrgInfoUnit  OBJECT-TYPE
            SYNTAX  UnitID
            ACCESS  read-only
            STATUS  mandatory
            DESCRIPTION
            "unit 1 to 4."
            ::= { enetV1RstpBrgInfoEntry 1 }

        enBrgInfoRstpEnable  OBJECT-TYPE
            SYNTAX  INTEGER {
                    disable(1),
                    enable(2)
                }
            ACCESS  read-write
            STATUS  mandatory
            DESCRIPTION
                "RSTP enable/disable"
            ::= { enetV1RstpBrgInfoEntry 2 }

        enBrgInfoRootMacAddr  OBJECT-TYPE
            SYNTAX  DisplayString (SIZE (0..255))
            ACCESS  read-only
            STATUS  mandatory
            DESCRIPTION
                "Designated Root MAC ADDR"
            ::= { enetV1RstpBrgInfoEntry 3 }

        enBrgInfoRootPriority  OBJECT-TYPE
            SYNTAX  INTEGER
            ACCESS  read-only
            STATUS  mandatory
            DESCRIPTION
                "Designated Root Priority"
            ::= { enetV1RstpBrgInfoEntry 4 }

        enBrgInfoRootCost  OBJECT-TYPE
            SYNTAX  INTEGER
            ACCESS  read-only
            STATUS  mandatory
            DESCRIPTION
                "Designated Root Cost"
            ::= { enetV1RstpBrgInfoEntry 5 }

        enBrgInfoRootMaxAge  OBJECT-TYPE
            SYNTAX  INTEGER
            ACCESS  read-only
            STATUS  mandatory
            DESCRIPTION
                "Root Max Age"
            ::= { enetV1RstpBrgInfoEntry 6 }

        enBrgInfoRootHelloTime  OBJECT-TYPE
            SYNTAX  INTEGER
            ACCESS  read-only
            STATUS  mandatory
            DESCRIPTION
                "Root Hello Time"
            ::= { enetV1RstpBrgInfoEntry 7 }

        enBrgInfoRootFwdDelay  OBJECT-TYPE
            SYNTAX  INTEGER
            ACCESS  read-only
            STATUS  mandatory
            DESCRIPTION
                "Root Forward Delay"
            ::= { enetV1RstpBrgInfoEntry 8 }

        enBrgInfoBrgMacAddr  OBJECT-TYPE
            SYNTAX  DisplayString (SIZE (0..255))
            ACCESS  read-only
            STATUS  mandatory
            DESCRIPTION
                "Bridge ID MAC ADDR"
            ::= { enetV1RstpBrgInfoEntry 9 }

        enBrgInfoBrgPriority  OBJECT-TYPE
            SYNTAX  INTEGER (0..65535)
            ACCESS  read-write
            STATUS  mandatory
            DESCRIPTION
                "Bridge ID Priority"
            ::= { enetV1RstpBrgInfoEntry 10 }

        enBrgInfoBrgMaxAge  OBJECT-TYPE
            SYNTAX  INTEGER (6..40)
            ACCESS  read-write
            STATUS  mandatory
            DESCRIPTION
                "Bridge Max Age"
            ::= { enetV1RstpBrgInfoEntry 11 }

        enBrgInfoBrgHelloTime  OBJECT-TYPE
            SYNTAX  INTEGER (1..10)
            ACCESS  read-write
            STATUS  mandatory
            DESCRIPTION
                "Bridge Hello Time"
            ::= { enetV1RstpBrgInfoEntry 12 }

        enBrgInfoBrgFwdDelay  OBJECT-TYPE
            SYNTAX  INTEGER (4..30)
            ACCESS  read-write
            STATUS  mandatory
            DESCRIPTION
                "Bridge Forward Delay"
            ::= { enetV1RstpBrgInfoEntry 13 }

        enBrgInfoBrgAgingTime  OBJECT-TYPE
            SYNTAX  INTEGER (10..999)
            ACCESS  read-write
            STATUS  mandatory
            DESCRIPTION
                "Bridge Aging Time"
            ::= { enetV1RstpBrgInfoEntry 14 }

--
--  enetV1RstpPortInfoTab
--
        enetV1RstpPortInfoTable  OBJECT-TYPE
            SYNTAX  SEQUENCE OF  EnetV1RstpPortInfoEntry
            ACCESS  not-accessible
            STATUS  mandatory
            DESCRIPTION
                "The Ethernet RSTP port info Table for V1.xx.xx."
            ::= { enetRstpTable 2 }

        enetV1RstpPortInfoEntry  OBJECT-TYPE
            SYNTAX  EnetV1RstpPortInfoEntry
            ACCESS  not-accessible
            STATUS  mandatory
            DESCRIPTION
                "An entry in The Ethernet RSTP port info Table for V1.xx.xx."
            INDEX { enPortInfoUnit , enPortInfoPort }
            ::= { enetV1RstpPortInfoTable 1 }

        EnetV1RstpPortInfoEntry ::= SEQUENCE {
            enPortInfoUnit              UnitID,
            enPortInfoPort              SwPortNum,
            enPortInfoPortEnable        INTEGER,
            enPortInfoRootPort          INTEGER,
            enPortInfoState             INTEGER,
            enPortInfoCost              INTEGER,
            enPortInfoPriority          INTEGER,
            enPortInfoEdgePort          INTEGER,
            enPortInfoPointToPoint      INTEGER
        }

        enPortInfoUnit  OBJECT-TYPE
            SYNTAX  UnitID
            ACCESS  read-only
            STATUS  mandatory
            DESCRIPTION
            "unit 1 to 4."
            ::= { enetV1RstpPortInfoEntry 1 }

        enPortInfoPort  OBJECT-TYPE
            SYNTAX  SwPortNum
            ACCESS  read-only
            STATUS  mandatory
            DESCRIPTION
                "Port WAN1~9, LAN1~9."
            ::= { enetV1RstpPortInfoEntry 2 }

        enPortInfoPortEnable  OBJECT-TYPE
            SYNTAX  INTEGER {
                    disable(1),
                    enable(2)
                }
            ACCESS  read-only
            STATUS  mandatory
            DESCRIPTION
                "Port RSTP enable/disable"
            ::= { enetV1RstpPortInfoEntry 3 }

        enPortInfoRootPort  OBJECT-TYPE
            SYNTAX  INTEGER {
                    no(1),
                    yes(2)
                }
            ACCESS  read-only
            STATUS  mandatory
            DESCRIPTION
                "Port RSTP port role."
            ::= { enetV1RstpPortInfoEntry 4 }

        enPortInfoState  OBJECT-TYPE
            SYNTAX  INTEGER {
                    diable(1),
                    listen(2),
                    learn(3),
                    forward(4),
                    block(5),
                    not-available(100)
                }
            ACCESS  read-only
            STATUS  mandatory
            DESCRIPTION
                "Port RSTP state"
            ::= { enetV1RstpPortInfoEntry 5 }

        enPortInfoCost  OBJECT-TYPE
            SYNTAX  INTEGER (1..999)
            ACCESS  read-write
            STATUS  mandatory
            DESCRIPTION
                "Port RSTP cost"
            ::= { enetV1RstpPortInfoEntry 6 }

        enPortInfoPriority  OBJECT-TYPE
            SYNTAX  INTEGER (0..255)
            ACCESS  read-write
            STATUS  mandatory
            DESCRIPTION
                "Port RSTP Priority"
            ::= { enetV1RstpPortInfoEntry 7 }

        enPortInfoEdgePort  OBJECT-TYPE
            SYNTAX  INTEGER {
                    no(1),
                    yes(2)
                }
            ACCESS  read-write
            STATUS  mandatory
            DESCRIPTION
                "Port RSTP Edge Port"
            ::= { enetV1RstpPortInfoEntry 8 }

        enPortInfoPointToPoint  OBJECT-TYPE
            SYNTAX  INTEGER {
                    no(1),
                    yes(2)
                }
            ACCESS  read-write
            STATUS  mandatory
            DESCRIPTION
                "Port RSTP Point-to-Point"
            ::= { enetV1RstpPortInfoEntry 9 }

--
--  enetStpTable
--
    enetStpTable       OBJECT IDENTIFIER ::= { enetSwitchTable 5 }

--
--  enetMstpBrgInfoTab
--
        enetMstpBrgInfoTab  OBJECT-TYPE
            SYNTAX  SEQUENCE OF  EnetMstpBrgInfoEntry
            ACCESS  not-accessible
            STATUS  mandatory
            DESCRIPTION
                "The Ethernet MSTP bridge info Table."
            ::= { enetStpTable 1 }

        enetMstpBrgInfoEntry  OBJECT-TYPE
            SYNTAX  EnetMstpBrgInfoEntry
            ACCESS  not-accessible
            STATUS  mandatory
            DESCRIPTION
                "An entry in The Ethernet MSTP bridge info Table."
            INDEX { enMstpBrgUnit }
            ::= { enetMstpBrgInfoTab 1 }

        EnetMstpBrgInfoEntry ::= SEQUENCE {
            enMstpBrgUnit               UnitID,
            enMstpBrgEnable             INTEGER,
            enMstpBrgRegion             DisplayString,
            enMstpBrgRevision           INTEGER,
            enMstpBrgMacAddr            DisplayString,
            enMstpBrgPriority           INTEGER,
            enMstpBrgMaxAge             INTEGER,
            enMstpBrgHelloTime          INTEGER,
            enMstpBrgFwdDelay           INTEGER
        }

        enMstpBrgUnit  OBJECT-TYPE
            SYNTAX  UnitID
            ACCESS  read-only
            STATUS  mandatory
            DESCRIPTION
            "unit 1 to 4."
            ::= { enetMstpBrgInfoEntry 1 }

        enMstpBrgEnable  OBJECT-TYPE
            SYNTAX  INTEGER {
                    disable(1),
                    enable(2)
                }
            ACCESS  read-write
            STATUS  mandatory
            DESCRIPTION
                "MSTP enable/disable"
            ::= { enetMstpBrgInfoEntry 2 }

        enMstpBrgRegion  OBJECT-TYPE
            SYNTAX  DisplayString (SIZE (1..36))
            ACCESS  read-write
            STATUS  mandatory
            DESCRIPTION
                "Region Name"
            ::= { enetMstpBrgInfoEntry 3 }

        enMstpBrgRevision  OBJECT-TYPE
            SYNTAX  INTEGER (0..65535)
            ACCESS  read-write
            STATUS  mandatory
            DESCRIPTION
                "Revision"
            ::= { enetMstpBrgInfoEntry 4 }

        enMstpBrgMacAddr  OBJECT-TYPE
            SYNTAX  DisplayString (SIZE (0..255))
            ACCESS  read-only
            STATUS  mandatory
            DESCRIPTION
                "Bridge ID MAC ADDR"
            ::= { enetMstpBrgInfoEntry 5 }

        enMstpBrgPriority  OBJECT-TYPE
            SYNTAX  INTEGER {
                    priority-0(1),
                    priority-4096(2),
                    priority-8192(3),
                    priority-12288(4),
                    priority-16384(5),
                    priority-20480(6),
                    priority-24576(7),
                    priority-28672(8),
                    priority-32768(9),
                    priority-36864(10),
                    priority-40960(11),
                    priority-45056(12),
                    priority-49152(13),
                    priority-53248(14),
                    priority-57344(15),
                    priority-61440(16)
                }
            ACCESS  read-write
            STATUS  mandatory
            DESCRIPTION
                "Bridge ID Priority"
            ::= { enetMstpBrgInfoEntry 6 }

        enMstpBrgMaxAge  OBJECT-TYPE
            SYNTAX  INTEGER (4..40)
            ACCESS  read-write
            STATUS  mandatory
            DESCRIPTION
                "Bridge Max Age"
            ::= { enetMstpBrgInfoEntry 7 }

        enMstpBrgHelloTime  OBJECT-TYPE
            SYNTAX  INTEGER (1..10)
            ACCESS  read-write
            STATUS  mandatory
            DESCRIPTION
                "Bridge Hello Time"
            ::= { enetMstpBrgInfoEntry 8 }

        enMstpBrgFwdDelay  OBJECT-TYPE
            SYNTAX  INTEGER (4..30)
            ACCESS  read-write
            STATUS  mandatory
            DESCRIPTION
                "Bridge Forward Delay"
            ::= { enetMstpBrgInfoEntry 9 }

--
--  enetStpPortEnTab
--
        enetStpPortEnTab  OBJECT-TYPE
            SYNTAX  SEQUENCE OF  EnetStpPortEnEntry
            ACCESS  not-accessible
            STATUS  mandatory
            DESCRIPTION
                "The Ethernet STP port Enable/Disable Table."
            ::= { enetStpTable 2 }

        enetStpPortEnEntry  OBJECT-TYPE
            SYNTAX  EnetStpPortEnEntry
            ACCESS  not-accessible
            STATUS  mandatory
            DESCRIPTION
                "An entry in The Ethernet STP port Enable/Disable Table."
            INDEX { enetStpPortEnUnit , enetStpPortEnPort }
            ::= { enetStpPortEnTab 1 }

        EnetStpPortEnEntry ::= SEQUENCE {
            enetStpPortEnUnit           UnitID,
            enetStpPortEnPort           SwPortNum,
            enetStpPortEnEnable         INTEGER
        }

        enetStpPortEnUnit  OBJECT-TYPE
            SYNTAX  UnitID
            ACCESS  read-only
            STATUS  mandatory
            DESCRIPTION
            "unit 1 to 4."
            ::= { enetStpPortEnEntry 1 }

        enetStpPortEnPort  OBJECT-TYPE
            SYNTAX  SwPortNum
            ACCESS  read-only
            STATUS  mandatory
            DESCRIPTION
                "Port WAN1~9, LAN1~9."
            ::= { enetStpPortEnEntry 2 }

        enetStpPortEnEnable  OBJECT-TYPE
            SYNTAX  INTEGER {
                    disable(1),
                    enable(2)
                }
            ACCESS  read-write
            STATUS  mandatory
            DESCRIPTION
                "STP port enable/disable"
            ::= { enetStpPortEnEntry 3 }

--
--  enetMstpInstanceTab
--

    enetMstpInstanceTab  OBJECT IDENTIFIER ::= { enetStpTable 3 }

    enetMstpInstanceEntry  OBJECT IDENTIFIER ::= { enetMstpInstanceTab 1 }


        enMstpInstanceUnit  OBJECT-TYPE
            SYNTAX  UnitID
            ACCESS  read-write
            STATUS  mandatory
            DESCRIPTION
            "unit 1 to 4."
            ::= { enetMstpInstanceEntry 1 }

        enMstpInstanceInstance  OBJECT-TYPE
            SYNTAX  INTEGER (1..64)
            ACCESS  read-write
            STATUS  mandatory
            DESCRIPTION
                "Mstp Instance 1~64"
            ::= { enetMstpInstanceEntry 2 }

        enMstpInstanceSet  OBJECT-TYPE
            SYNTAX  INTEGER {
                    delete(1),
                    add(2)
                }
            ACCESS  read-write
            STATUS  mandatory
            DESCRIPTION
                "Add / Delete Vlan to MSTP Instance"
            ::= { enetMstpInstanceEntry 3 }

        enMstpInstanceVlanFrom  OBJECT-TYPE
            SYNTAX  INTEGER (1..4096)
            ACCESS  read-write
            STATUS  mandatory
            DESCRIPTION
                "Add / Delete From Which Vlan For MSTP Instance"
            ::= { enetMstpInstanceEntry 4 }

        enMstpInstanceVlanTo  OBJECT-TYPE
            SYNTAX  INTEGER (1..4096)
            ACCESS  read-write
            STATUS  mandatory
            DESCRIPTION
                "Add / Delete To Which Vlan For MSTP Instance"
            ::= { enetMstpInstanceEntry 5 }

        enMstpInstanceActive  OBJECT-TYPE
            SYNTAX  INTEGER {
                    none(1),
                    activate(2)
                }
            ACCESS  read-write
            STATUS  mandatory
            DESCRIPTION
                "Active Setting To MSTP Instance"
            ::= { enetMstpInstanceEntry 6 }


--
--  enetMstpInstPriorTab
--

        enetMstpInstPriorTab  OBJECT-TYPE
            SYNTAX  SEQUENCE OF  EnetMstpInstPriorEntry
            ACCESS  not-accessible
            STATUS  mandatory
            DESCRIPTION
                "The Ethernet MSTP Instance Priority and Display Table."
            ::= { enetStpTable 4 }

        enetMstpInstPriorEntry  OBJECT-TYPE
            SYNTAX  EnetMstpInstPriorEntry
            ACCESS  not-accessible
            STATUS  mandatory
            DESCRIPTION
                "An entry in The Ethernet MSTP Instance Priority and Display Table."
            INDEX { enMstpInstPriorUnit , enMstpInstPriorInstance }
            ::= { enetMstpInstPriorTab 1 }

        EnetMstpInstPriorEntry ::= SEQUENCE {
            enMstpInstPriorUnit         UnitID,
            enMstpInstPriorInstance     INTEGER,
            enMstpInstPriorPriority     INTEGER,
            enMstpInstPriorVlanMap      DisplayString
        }

        enMstpInstPriorUnit  OBJECT-TYPE
            SYNTAX  UnitID
            ACCESS  read-only
            STATUS  mandatory
            DESCRIPTION
            "unit 1 to 4."
            ::= { enetMstpInstPriorEntry 1 }

        enMstpInstPriorInstance  OBJECT-TYPE
            SYNTAX  INTEGER (1..64)
            ACCESS  read-only
            STATUS  mandatory
            DESCRIPTION
                "Mstp Instance 1~64"
            ::= { enetMstpInstPriorEntry 2 }

        enMstpInstPriorPriority  OBJECT-TYPE
            SYNTAX  INTEGER {
                    priority-0(1),
                    priority-4096(2),
                    priority-8192(3),
                    priority-12288(4),
                    priority-16384(5),
                    priority-20480(6),
                    priority-24576(7),
                    priority-28672(8),
                    priority-32768(9),
                    priority-36864(10),
                    priority-40960(11),
                    priority-45056(12),
                    priority-49152(13),
                    priority-53248(14),
                    priority-57344(15),
                    priority-61440(16),
                    not-available(30)
                }
            ACCESS  read-write
            STATUS  mandatory
            DESCRIPTION
                "Mstp Instance Priority"
            ::= { enetMstpInstPriorEntry 3 }

        enMstpInstPriorVlanMap  OBJECT-TYPE
            SYNTAX  DisplayString (SIZE (0..300))
            ACCESS  read-only
            STATUS  mandatory
            DESCRIPTION
                "Vlan Mapping For Mstp Instance"
            ::= { enetMstpInstPriorEntry 4 }


--
--  enetMstpPortInfoTab
--
        enetMstpPortInfoTab  OBJECT-TYPE
            SYNTAX  SEQUENCE OF  EnetMstpPortInfoEntry
            ACCESS  not-accessible
            STATUS  mandatory
            DESCRIPTION
                "The Ethernet MSTP port Info Table."
            ::= { enetStpTable 5 }

        enetMstpPortInfoEntry  OBJECT-TYPE
            SYNTAX  EnetMstpPortInfoEntry
            ACCESS  not-accessible
            STATUS  mandatory
            DESCRIPTION
                "An entry in The Ethernet MSTP port Info Table."
            INDEX { enMstpPortInfoUnit , enMstpPortInfoInstance , enMstpPortInfoPort }
            ::= { enetMstpPortInfoTab 1 }

        EnetMstpPortInfoEntry ::= SEQUENCE {
            enMstpPortInfoUnit          UnitID,
            enMstpPortInfoInstance      INTEGER,
            enMstpPortInfoPort          SwPortNum,
            enMstpPortInfoRole          INTEGER,
            enMstpPortInfoState         INTEGER,
            enMstpPortInfoCost          INTEGER,
            enMstpPortInfoCostSet       INTEGER,
            enMstpPortInfoPrior         INTEGER,
            enMstpPortInfoPriorSet      INTEGER,
            enMstpPortInfoEdge          INTEGER,
            enMstpPortInfoEdgeSet       INTEGER,
            enMstpPortInfoType          INTEGER,
            enMstpPortInfoTypeSet       INTEGER,
            enMstpPortInfoBoundary      INTEGER
        }

        enMstpPortInfoUnit  OBJECT-TYPE
            SYNTAX  UnitID
            ACCESS  read-only
            STATUS  mandatory
            DESCRIPTION
            "unit 1 to 4."
            ::= { enetMstpPortInfoEntry 1 }

        enMstpPortInfoInstance  OBJECT-TYPE
            SYNTAX  INTEGER (0..64)
            ACCESS  read-only
            STATUS  mandatory
            DESCRIPTION
                "Mstp Instance 0~64"
            ::= { enetMstpPortInfoEntry 2 }

        enMstpPortInfoPort  OBJECT-TYPE
            SYNTAX  SwPortNum
            ACCESS  read-only
            STATUS  mandatory
            DESCRIPTION
                "Port WAN1~9, LAN1~9."
            ::= { enetMstpPortInfoEntry 3 }


        enMstpPortInfoRole  OBJECT-TYPE
            SYNTAX  INTEGER {
                    master(1),
                    alternate(2),
                    root(3),
                    designated(4),
                    backup(5),
                    disabled(6),
                    boundary(7)
                }
            ACCESS  read-only
            STATUS  mandatory
            DESCRIPTION
                "MSTP port Role"
            ::= { enetMstpPortInfoEntry 4 }

        enMstpPortInfoState  OBJECT-TYPE
            SYNTAX  INTEGER {
                    disable(1),
                    listening(2),
                    learning(3),
                    forwarding(4),
                    blocking(5)
                }
            ACCESS  read-only
            STATUS  mandatory
            DESCRIPTION
                "MSTP port State"
            ::= { enetMstpPortInfoEntry 5 }

        enMstpPortInfoCost  OBJECT-TYPE
            SYNTAX  INTEGER
            ACCESS  read-only
            STATUS  mandatory
            DESCRIPTION
                "MSTP port Cost"
            ::= { enetMstpPortInfoEntry 6 }

        enMstpPortInfoCostSet  OBJECT-TYPE
            SYNTAX  INTEGER (1..200000000)
            ACCESS  read-write
            STATUS  mandatory
            DESCRIPTION
                "MSTP port Cost Set"
            ::= { enetMstpPortInfoEntry 7 }

        enMstpPortInfoPrior  OBJECT-TYPE
            SYNTAX  INTEGER {
                    priority-0(1),
                    priority-16(2),
                    priority-32(3),
                    priority-48(4),
                    priority-64(5),
                    priority-80(6),
                    priority-96(7),
                    priority-112(8),
                    priority-128(9),
                    priority-144(10),
                    priority-160(11),
                    priority-176(12),
                    priority-192(13),
                    priority-208(14),
                    priority-224(15),
                    priority-240(16)
                }
            ACCESS  read-only
            STATUS  mandatory
            DESCRIPTION
                "MSTP port Priority"
            ::= { enetMstpPortInfoEntry 8 }

        enMstpPortInfoPriorSet  OBJECT-TYPE
            SYNTAX  INTEGER {
                    priority-0(1),
                    priority-16(2),
                    priority-32(3),
                    priority-48(4),
                    priority-64(5),
                    priority-80(6),
                    priority-96(7),
                    priority-112(8),
                    priority-128(9),
                    priority-144(10),
                    priority-160(11),
                    priority-176(12),
                    priority-192(13),
                    priority-208(14),
                    priority-224(15),
                    priority-240(16)
                }
            ACCESS  read-write
            STATUS  mandatory
            DESCRIPTION
                "MSTP port Priority Set"
            ::= { enetMstpPortInfoEntry 9 }

        enMstpPortInfoEdge  OBJECT-TYPE
            SYNTAX  INTEGER {
                    no(1),
                    yes(2),
                    not-available(10)
                }
            ACCESS  read-only
            STATUS  mandatory
            DESCRIPTION
                "MSTP port Edge Port"
            ::= { enetMstpPortInfoEntry 10 }

        enMstpPortInfoEdgeSet  OBJECT-TYPE
            SYNTAX  INTEGER {
                    no(1),
                    yes(2),
                    not-available(10)
                }
            ACCESS  read-write
            STATUS  mandatory
            DESCRIPTION
                "MSTP port Edge Port Set"
            ::= { enetMstpPortInfoEntry 11 }

        enMstpPortInfoType  OBJECT-TYPE
            SYNTAX  INTEGER {
                    share(1),
                    point-to-point(2),
                    auto(3),
                    not-available(10)
                }
            ACCESS  read-only
            STATUS  mandatory
            DESCRIPTION
                "MSTP port Link Type"
            ::= { enetMstpPortInfoEntry 12 }

        enMstpPortInfoTypeSet  OBJECT-TYPE
            SYNTAX  INTEGER {
                    share(1),
                    point-to-point(2),
                    auto(3),
                    not-available(10)
                }
            ACCESS  read-write
            STATUS  mandatory
            DESCRIPTION
                "MSTP port Link Type Set"
            ::= { enetMstpPortInfoEntry 13 }

        enMstpPortInfoBoundary  OBJECT-TYPE
            SYNTAX  INTEGER {
                    internal(1),
                    bound-stp(2),
                    bound-rstp(3),
                    bound-mstp(4),
                    not-available(10)
                }
            ACCESS  read-only
            STATUS  mandatory
            DESCRIPTION
                "MSTP port Link Type"
            ::= { enetMstpPortInfoEntry 14 }

--
--  enetRstpPortInfoTab
--
        enetRstpPortInfoTab  OBJECT-TYPE
            SYNTAX  SEQUENCE OF  EnetRstpPortInfoEntry
            ACCESS  not-accessible
            STATUS  mandatory
            DESCRIPTION
                "The Ethernet RSTP port Info Table."
            ::= { enetStpTable 6 }

        enetRstpPortInfoEntry  OBJECT-TYPE
            SYNTAX  EnetRstpPortInfoEntry
            ACCESS  not-accessible
            STATUS  mandatory
            DESCRIPTION
                "An entry in The Ethernet RSTP port Info Table."
            INDEX { enRstpPortInfoUnit , enRstpPortInfoPort }
            ::= { enetRstpPortInfoTab 1 }

        EnetRstpPortInfoEntry ::= SEQUENCE {
            enRstpPortInfoUnit          UnitID,
            enRstpPortInfoPort          SwPortNum,
            enRstpPortInfoRole          INTEGER,
            enRstpPortInfoState         INTEGER,
            enRstpPortInfoCost          INTEGER,
            enRstpPortInfoCostSet       INTEGER,
            enRstpPortInfoPrior         INTEGER,
            enRstpPortInfoPriorSet      INTEGER,
            enRstpPortInfoEdge          INTEGER,
            enRstpPortInfoEdgeSet       INTEGER,
            enRstpPortInfoType          INTEGER,
            enRstpPortInfoTypeSet       INTEGER
        }

        enRstpPortInfoUnit  OBJECT-TYPE
            SYNTAX  UnitID
            ACCESS  read-only
            STATUS  mandatory
            DESCRIPTION
            "unit 1 to 4."
            ::= { enetRstpPortInfoEntry 1 }

        enRstpPortInfoPort  OBJECT-TYPE
            SYNTAX  SwPortNum
            ACCESS  read-only
            STATUS  mandatory
            DESCRIPTION
                "Port WAN1~9, LAN1~9."
            ::= { enetRstpPortInfoEntry 2 }

        enRstpPortInfoRole  OBJECT-TYPE
            SYNTAX  INTEGER {
                    master(1),
                    alternate(2),
                    root(3),
                    designated(4),
                    backup(5),
                    disabled(6),
                    boundary(7)
                }
            ACCESS  read-only
            STATUS  mandatory
            DESCRIPTION
                "RSTP port Role"
            ::= { enetRstpPortInfoEntry 3 }

        enRstpPortInfoState  OBJECT-TYPE
            SYNTAX  INTEGER {
                    disable(1),
                    listening(2),
                    learning(3),
                    forwarding(4),
                    blocking(5)
                }
            ACCESS  read-only
            STATUS  mandatory
            DESCRIPTION
                "RSTP port State"
            ::= { enetRstpPortInfoEntry 4 }

        enRstpPortInfoCost  OBJECT-TYPE
            SYNTAX  INTEGER
            ACCESS  read-only
            STATUS  mandatory
            DESCRIPTION
                "RSTP port Cost"
            ::= { enetRstpPortInfoEntry 5 }

        enRstpPortInfoCostSet  OBJECT-TYPE
            SYNTAX  INTEGER (1..200000000)
            ACCESS  read-write
            STATUS  mandatory
            DESCRIPTION
                "RSTP port Cost Set"
            ::= { enetRstpPortInfoEntry 6 }

        enRstpPortInfoPrior  OBJECT-TYPE
            SYNTAX  INTEGER {
                    priority-0(1),
                    priority-16(2),
                    priority-32(3),
                    priority-48(4),
                    priority-64(5),
                    priority-80(6),
                    priority-96(7),
                    priority-112(8),
                    priority-128(9),
                    priority-144(10),
                    priority-160(11),
                    priority-176(12),
                    priority-192(13),
                    priority-208(14),
                    priority-224(15),
                    priority-240(16)
                }
            ACCESS  read-only
            STATUS  mandatory
            DESCRIPTION
                "RSTP port Priority"
            ::= { enetRstpPortInfoEntry 7 }

        enRstpPortInfoPriorSet  OBJECT-TYPE
            SYNTAX  INTEGER {
                    priority-0(1),
                    priority-16(2),
                    priority-32(3),
                    priority-48(4),
                    priority-64(5),
                    priority-80(6),
                    priority-96(7),
                    priority-112(8),
                    priority-128(9),
                    priority-144(10),
                    priority-160(11),
                    priority-176(12),
                    priority-192(13),
                    priority-208(14),
                    priority-224(15),
                    priority-240(16)
                }
            ACCESS  read-write
            STATUS  mandatory
            DESCRIPTION
                "RSTP port Priority Set"
            ::= { enetRstpPortInfoEntry 8 }

        enRstpPortInfoEdge  OBJECT-TYPE
            SYNTAX  INTEGER {
                    no(1),
                    yes(2)
                }
            ACCESS  read-only
            STATUS  mandatory
            DESCRIPTION
                "RSTP port Edge Port"
            ::= { enetRstpPortInfoEntry 9 }

        enRstpPortInfoEdgeSet  OBJECT-TYPE
            SYNTAX  INTEGER {
                    no(1),
                    yes(2)
                }
            ACCESS  read-write
            STATUS  mandatory
            DESCRIPTION
                "RSTP port Edge Port Set"
            ::= { enetRstpPortInfoEntry 10 }

        enRstpPortInfoType  OBJECT-TYPE
            SYNTAX  INTEGER {
                    share(1),
                    point-to-point(2),
                    auto(3)
                }
            ACCESS  read-only
            STATUS  mandatory
            DESCRIPTION
                "RSTP port Link Type"
            ::= { enetRstpPortInfoEntry 11 }

        enRstpPortInfoTypeSet  OBJECT-TYPE
            SYNTAX  INTEGER {
                    share(1),
                    point-to-point(2),
                    auto(3)
                }
            ACCESS  read-write
            STATUS  mandatory
            DESCRIPTION
                "RSTP port Link Type Set"
            ::= { enetRstpPortInfoEntry 12 }

--
--  enetRstpBrgInfoTab
--
        enetRstpBrgInfoTab  OBJECT-TYPE
            SYNTAX  SEQUENCE OF  EnetRstpBrgInfoEntry
            ACCESS  not-accessible
            STATUS  mandatory
            DESCRIPTION
                "The Ethernet RSTP bridge info Table."
            ::= { enetStpTable 7 }

        enetRstpBrgInfoEntry  OBJECT-TYPE
            SYNTAX  EnetRstpBrgInfoEntry
            ACCESS  not-accessible
            STATUS  mandatory
            DESCRIPTION
                "An entry in The Ethernet STP bridge info Table."
            INDEX { enRstpBrgUnit }
            ::= { enetRstpBrgInfoTab 1 }

        EnetRstpBrgInfoEntry ::= SEQUENCE {
            enRstpBrgUnit               UnitID,
            enRstpBrgEnable             INTEGER,
            enRstpBrgMacAddr            DisplayString,
            enRstpBrgPriority           INTEGER,
            enRstpBrgMaxAge             INTEGER,
            enRstpBrgHelloTime          INTEGER,
            enRstpBrgFwdDelay           INTEGER
        }

        enRstpBrgUnit  OBJECT-TYPE
            SYNTAX  UnitID
            ACCESS  read-only
            STATUS  mandatory
            DESCRIPTION
            "unit 1 to 4."
            ::= { enetRstpBrgInfoEntry 1 }

        enRstpBrgEnable  OBJECT-TYPE
            SYNTAX  INTEGER {
                    disable(1),
                    enable(2)
                }
            ACCESS  read-write
            STATUS  mandatory
            DESCRIPTION
                "RSTP enable/disable"
            ::= { enetRstpBrgInfoEntry 2 }

        enRstpBrgMacAddr  OBJECT-TYPE
            SYNTAX  DisplayString (SIZE (0..255))
            ACCESS  read-only
            STATUS  mandatory
            DESCRIPTION
                "Bridge ID MAC ADDR"
            ::= { enetRstpBrgInfoEntry 3 }

        enRstpBrgPriority  OBJECT-TYPE
            SYNTAX  INTEGER {
                    priority-0(1),
                    priority-4096(2),
                    priority-8192(3),
                    priority-12288(4),
                    priority-16384(5),
                    priority-20480(6),
                    priority-24576(7),
                    priority-28672(8),
                    priority-32768(9),
                    priority-36864(10),
                    priority-40960(11),
                    priority-45056(12),
                    priority-49152(13),
                    priority-53248(14),
                    priority-57344(15),
                    priority-61440(16)
                }
            ACCESS  read-write
            STATUS  mandatory
            DESCRIPTION
                "Bridge ID Priority"
            ::= { enetRstpBrgInfoEntry 4 }

        enRstpBrgMaxAge  OBJECT-TYPE
            SYNTAX  INTEGER (4..40)
            ACCESS  read-write
            STATUS  mandatory
            DESCRIPTION
                "Bridge Max Age"
            ::= { enetRstpBrgInfoEntry 5 }

        enRstpBrgHelloTime  OBJECT-TYPE
            SYNTAX  INTEGER (1..10)
            ACCESS  read-write
            STATUS  mandatory
            DESCRIPTION
                "Bridge Hello Time"
            ::= { enetRstpBrgInfoEntry 6 }

        enRstpBrgFwdDelay  OBJECT-TYPE
            SYNTAX  INTEGER (4..30)
            ACCESS  read-write
            STATUS  mandatory
            DESCRIPTION
                "Bridge Forward Delay"
            ::= { enetRstpBrgInfoEntry 7 }

--
--   enetPortTrunkTable
--
        enetPortTrunkTable  OBJECT-TYPE
            SYNTAX  SEQUENCE OF  EnetPortTrunkEntry
            ACCESS  not-accessible
            STATUS  mandatory
            DESCRIPTION
                "The Ethernet Port Trunk Table."
            ::= { enetSwitchTable 6 }

        enetPortTrunkEntry  OBJECT-TYPE
            SYNTAX  EnetPortTrunkEntry
            ACCESS  not-accessible
            STATUS  mandatory
            DESCRIPTION
                "An entry in the Ethernet Port Trunk Table."
            INDEX { enTrunkUnit , enTrunkGroup }
            ::= { enetPortTrunkTable 1 }

        EnetPortTrunkEntry ::= SEQUENCE {
            enTrunkUnit                 UnitID,
            enTrunkGroup                INTEGER,
            enTrunkMemberLeaderPort     INTEGER,
            enTrunkWan1                 INTEGER,
            enTrunkWan2                 INTEGER,
            enTrunkWan3                 INTEGER,
            enTrunkWan4                 INTEGER,
            enTrunkWan5                 INTEGER,
            enTrunkWan6                 INTEGER,
            enTrunkWan7                 INTEGER,
            enTrunkWan8                 INTEGER,
            enTrunkWan9                 INTEGER,
            enTrunkLan1                 INTEGER,
            enTrunkLan2                 INTEGER,
            enTrunkLan3                 INTEGER,
            enTrunkLan4                 INTEGER,
            enTrunkLan5                 INTEGER,
            enTrunkLan6                 INTEGER,
            enTrunkLan7                 INTEGER,
            enTrunkLan8                 INTEGER,
            enTrunkLan9                 INTEGER
        }

        enTrunkUnit  OBJECT-TYPE
            SYNTAX  UnitID
            ACCESS  read-only
            STATUS  mandatory
            DESCRIPTION
            "unit 1 to 4."
            ::= { enetPortTrunkEntry 1 }

        enTrunkGroup  OBJECT-TYPE
            SYNTAX  INTEGER {
                    trunk-1(1),
                    trunk-2(2),
                    trunk-3(3),
                    trunk-4(4)
                }
            ACCESS  read-only
            STATUS  mandatory
            DESCRIPTION
                "Trunk 1 to 4"
            ::= { enetPortTrunkEntry 2 }

        enTrunkMemberLeaderPort  OBJECT-TYPE
            SYNTAX  INTEGER {
                    none(1),
                    wan1(2),
                    wan2(3),
                    wan3(4),
                    wan4(5),
                    wan5(6),
                    wan6(7),
                    wan7(8),
                    wan8(9),
                    wan9(10),
                    lan1(11),
                    lan2(12),
                    lan3(13),
                    lan4(14),
                    lan5(15),
                    lan6(16),
                    lan7(17),
                    lan8(18),
                    lan9(19)
                }
            ACCESS  read-write
            STATUS  mandatory
            DESCRIPTION
                "Member/Leader Port"
            ::= { enetPortTrunkEntry 3 }

        enTrunkWan1  OBJECT-TYPE
            SYNTAX  INTEGER {
                    off(1),
                    on(2)
                }
            ACCESS  read-write
            STATUS  mandatory
            DESCRIPTION
                "WAN1 Trunk ON/OFF"
            ::= { enetPortTrunkEntry 4 }

        enTrunkWan2  OBJECT-TYPE
            SYNTAX  INTEGER {
                    off(1),
                    on(2)
                }
            ACCESS  read-write
            STATUS  mandatory
            DESCRIPTION
                "WAN2 Trunk ON/OFF"
            ::= { enetPortTrunkEntry 5 }

        enTrunkWan3  OBJECT-TYPE
            SYNTAX  INTEGER {
                    off(1),
                    on(2)
                }
            ACCESS  read-write
            STATUS  mandatory
            DESCRIPTION
                "WAN3 Trunk ON/OFF"
            ::= { enetPortTrunkEntry 6 }

        enTrunkWan4  OBJECT-TYPE
            SYNTAX  INTEGER {
                    off(1),
                    on(2)
                }
            ACCESS  read-write
            STATUS  mandatory
            DESCRIPTION
                "WAN4 Trunk ON/OFF"
            ::= { enetPortTrunkEntry 7 }

        enTrunkWan5  OBJECT-TYPE
            SYNTAX  INTEGER {
                    off(1),
                    on(2)
                }
            ACCESS  read-write
            STATUS  mandatory
            DESCRIPTION
                "WAN5 Trunk ON/OFF"
            ::= { enetPortTrunkEntry 8 }

        enTrunkWan6  OBJECT-TYPE
            SYNTAX  INTEGER {
                    off(1),
                    on(2)
                }
            ACCESS  read-write
            STATUS  mandatory
            DESCRIPTION
                "WAN6 Trunk ON/OFF"
            ::= { enetPortTrunkEntry 9 }

        enTrunkWan7  OBJECT-TYPE
            SYNTAX  INTEGER {
                    off(1),
                    on(2)
                }
            ACCESS  read-write
            STATUS  mandatory
            DESCRIPTION
                "WAN7 Trunk ON/OFF"
            ::= { enetPortTrunkEntry 10 }

        enTrunkWan8  OBJECT-TYPE
            SYNTAX  INTEGER {
                    off(1),
                    on(2)
                }
            ACCESS  read-write
            STATUS  mandatory
            DESCRIPTION
                "WAN8 Trunk ON/OFF"
            ::= { enetPortTrunkEntry 11 }

        enTrunkWan9  OBJECT-TYPE
            SYNTAX  INTEGER {
                    off(1),
                    on(2)
                }
            ACCESS  read-write
            STATUS  mandatory
            DESCRIPTION
                "WAN9 Trunk ON/OFF"
            ::= { enetPortTrunkEntry 12 }

        enTrunkLan1  OBJECT-TYPE
            SYNTAX  INTEGER {
                    off(1),
                    on(2)
                }
            ACCESS  read-write
            STATUS  mandatory
            DESCRIPTION
                "LAN1 Trunk ON/OFF"
            ::= { enetPortTrunkEntry 13 }

        enTrunkLan2  OBJECT-TYPE
            SYNTAX  INTEGER {
                    off(1),
                    on(2)
                }
            ACCESS  read-write
            STATUS  mandatory
            DESCRIPTION
                "LAN2 Trunk ON/OFF"
            ::= { enetPortTrunkEntry 14 }

        enTrunkLan3  OBJECT-TYPE
            SYNTAX  INTEGER {
                    off(1),
                    on(2)
                }
            ACCESS  read-write
            STATUS  mandatory
            DESCRIPTION
                "LAN3 Trunk ON/OFF"
            ::= { enetPortTrunkEntry 15 }

        enTrunkLan4  OBJECT-TYPE
            SYNTAX  INTEGER {
                    off(1),
                    on(2)
                }
            ACCESS  read-write
            STATUS  mandatory
            DESCRIPTION
                "LAN4 Trunk ON/OFF"
            ::= { enetPortTrunkEntry 16 }

        enTrunkLan5  OBJECT-TYPE
            SYNTAX  INTEGER {
                    off(1),
                    on(2)
                }
            ACCESS  read-write
            STATUS  mandatory
            DESCRIPTION
                "LAN5 Trunk ON/OFF"
            ::= { enetPortTrunkEntry 17 }

        enTrunkLan6  OBJECT-TYPE
            SYNTAX  INTEGER {
                    off(1),
                    on(2)
                }
            ACCESS  read-write
            STATUS  mandatory
            DESCRIPTION
                "LAN6 Trunk ON/OFF"
            ::= { enetPortTrunkEntry 18 }

        enTrunkLan7  OBJECT-TYPE
            SYNTAX  INTEGER {
                    off(1),
                    on(2)
                }
            ACCESS  read-write
            STATUS  mandatory
            DESCRIPTION
                "LAN7 Trunk ON/OFF"
            ::= { enetPortTrunkEntry 19 }

        enTrunkLan8  OBJECT-TYPE
            SYNTAX  INTEGER {
                    off(1),
                    on(2)
                }
            ACCESS  read-write
            STATUS  mandatory
            DESCRIPTION
                "LAN8 Trunk ON/OFF"
            ::= { enetPortTrunkEntry 20 }

        enTrunkLan9  OBJECT-TYPE
            SYNTAX  INTEGER {
                    off(1),
                    on(2)
                }
            ACCESS  read-write
            STATUS  mandatory
            DESCRIPTION
                "LAN9 Trunk ON/OFF"
            ::= { enetPortTrunkEntry 21 }

--
--   enetIgmpSnoopTable
--
    enetIgmpSnoopTable  OBJECT IDENTIFIER ::= { enetSwitchTable 7 }

--
--   enetIgmpSnoopingTab
--
        enetIgmpSnoopingTab  OBJECT-TYPE
            SYNTAX  SEQUENCE OF  EnetIgmpSnoopingEty
            ACCESS  not-accessible
            STATUS  mandatory
            DESCRIPTION
                "The Ethernet IGMP Snooping Table."
            ::= { enetIgmpSnoopTable 1 }

        enetIgmpSnoopingEty  OBJECT-TYPE
            SYNTAX  EnetIgmpSnoopingEty
            ACCESS  not-accessible
            STATUS  mandatory
            DESCRIPTION
                "An entry in the Ethernet IGMP Snooping Table."
            INDEX { enIgmpSnoopUnit }
            ::= { enetIgmpSnoopingTab 1 }

        EnetIgmpSnoopingEty ::= SEQUENCE {
            enIgmpSnoopUnit             UnitID,
            enIgmpSnoopEnable           INTEGER,
            enIgmpSnoopQueryInterval    INTEGER
        }

        enIgmpSnoopUnit  OBJECT-TYPE
            SYNTAX  UnitID
            ACCESS  read-only
            STATUS  mandatory
            DESCRIPTION
            "unit 1 to 4."
            ::= { enetIgmpSnoopingEty 1 }

        enIgmpSnoopEnable  OBJECT-TYPE
            SYNTAX  INTEGER {
                    off(1),
                    on(2)
                }
            ACCESS  read-write
            STATUS  mandatory
            DESCRIPTION
                "IGMP Snooping Enable/Disable"
            ::= { enetIgmpSnoopingEty 2 }

        enIgmpSnoopQueryInterval  OBJECT-TYPE
            SYNTAX  INTEGER (0..65535)
            ACCESS  read-write
            STATUS  mandatory
            DESCRIPTION
                "IGMP Last Query Interval (centi-seconds)"
            ::= { enetIgmpSnoopingEty 3 }

--
--   enetIgmpFastLeaveTab
--
        enetIgmpFastLeaveTab  OBJECT-TYPE
            SYNTAX  SEQUENCE OF  EnetIgmpFastLeaveEty
            ACCESS  not-accessible
            STATUS  mandatory
            DESCRIPTION
                "The Ethernet IGMP Fast Leave Table."
            ::= { enetIgmpSnoopTable 2 }

        enetIgmpFastLeaveEty  OBJECT-TYPE
            SYNTAX  EnetIgmpFastLeaveEty
            ACCESS  not-accessible
            STATUS  mandatory
            DESCRIPTION
                "An entry in the Ethernet IGMP Fast Leave Table."
            INDEX { enIgmpFastLeaveUnit , enIgmpFastLeaveVid }
            ::= { enetIgmpFastLeaveTab 1 }

        EnetIgmpFastLeaveEty ::= SEQUENCE {
            enIgmpFastLeaveUnit         UnitID,
            enIgmpFastLeaveVid          INTEGER,
            enIgmpFastLeaveFastLeave    INTEGER
        }

        enIgmpFastLeaveUnit  OBJECT-TYPE
            SYNTAX  UnitID
            ACCESS  read-only
            STATUS  mandatory
            DESCRIPTION
            "unit 1 to 4."
            ::= { enetIgmpFastLeaveEty 1 }

        enIgmpFastLeaveVid  OBJECT-TYPE
            SYNTAX  INTEGER (1..4094)
            ACCESS  read-only
            STATUS  mandatory
            DESCRIPTION
                "VID 1 to 4094"
            ::= { enetIgmpFastLeaveEty 2 }

        enIgmpFastLeaveFastLeave  OBJECT-TYPE
            SYNTAX  INTEGER {
                    off(1),
                    on(2)
                }
            ACCESS  read-write
            STATUS  mandatory
            DESCRIPTION
                "IGMP Fast Leave"
            ::= { enetIgmpFastLeaveEty 3 }

--
--   enetIgmpRouterPortTab
--
        enetIgmpRouterPortTab  OBJECT-TYPE
            SYNTAX  SEQUENCE OF  EnetIgmpRouterPortEty
            ACCESS  not-accessible
            STATUS  mandatory
            DESCRIPTION
                "The Ethernet IGMP Router Port Table."
            ::= { enetIgmpSnoopTable 3 }

        enetIgmpRouterPortEty  OBJECT-TYPE
            SYNTAX  EnetIgmpRouterPortEty
            ACCESS  not-accessible
            STATUS  mandatory
            DESCRIPTION
                "An entry in the Ethernet IGMP Router Port Table."
            INDEX { enIgmpRtrPrtUnit , enIgmpRtrPrtPort }
            ::= { enetIgmpRouterPortTab 1 }

        EnetIgmpRouterPortEty ::= SEQUENCE {
            enIgmpRtrPrtUnit            UnitID,
            enIgmpRtrPrtPort            SwPortNum,
            enIgmpRtrPrtRouterPort      INTEGER
        }

        enIgmpRtrPrtUnit  OBJECT-TYPE
            SYNTAX  UnitID
            ACCESS  read-only
            STATUS  mandatory
            DESCRIPTION
            "unit 1 to 4."
            ::= { enetIgmpRouterPortEty 1 }

        enIgmpRtrPrtPort  OBJECT-TYPE
            SYNTAX  SwPortNum
            ACCESS  read-only
            STATUS  mandatory
            DESCRIPTION
                "Port WAN1~9, LAN1~9."
            ::= { enetIgmpRouterPortEty 2 }

        enIgmpRtrPrtRouterPort  OBJECT-TYPE
            SYNTAX  INTEGER {
                    no(1),
                    yes(2)
                }
            ACCESS  read-write
            STATUS  mandatory
            DESCRIPTION
                "IGMP Router Port"
            ::= { enetIgmpRouterPortEty 3 }

--
--   enetIgmpCrossVlanTab
--
        enetIgmpCrossVlanTab  OBJECT-TYPE
            SYNTAX  SEQUENCE OF  EnetIgmpCrossVlanEty
            ACCESS  not-accessible
            STATUS  mandatory
            DESCRIPTION
                "The Ethernet IGMP Cross VLAN Table."
            ::= { enetIgmpSnoopTable 4 }

        enetIgmpCrossVlanEty  OBJECT-TYPE
            SYNTAX  EnetIgmpCrossVlanEty
            ACCESS  not-accessible
            STATUS  mandatory
            DESCRIPTION
                "An entry in the Ethernet IGMP Cross VLAN Table."
            INDEX { enIgmpCrossVlanUnit }
            ::= { enetIgmpCrossVlanTab 1 }

        EnetIgmpCrossVlanEty ::= SEQUENCE {
            enIgmpCrossVlanUnit         UnitID,
            enIgmpCrossVlanEnable       INTEGER,
            enIgmpCrossVlanVlanID       INTEGER
        }

        enIgmpCrossVlanUnit  OBJECT-TYPE
            SYNTAX  UnitID
            ACCESS  read-only
            STATUS  mandatory
            DESCRIPTION
            "unit 1 to 4."
            ::= { enetIgmpCrossVlanEty 1 }

        enIgmpCrossVlanEnable  OBJECT-TYPE
            SYNTAX  INTEGER {
                    off(1),
                    on(2)
                }
            ACCESS  read-write
            STATUS  mandatory
            DESCRIPTION
                "Cross VLAN Enable/Disable"
            ::= { enetIgmpCrossVlanEty 2 }

        enIgmpCrossVlanVlanID  OBJECT-TYPE
            SYNTAX  INTEGER (0..65535)
            ACCESS  read-write
            STATUS  mandatory
            DESCRIPTION
                "Cross VLAN ID"
            ::= { enetIgmpCrossVlanEty 3 }

--
--   enetIgmpMulticastIpTab
--
        enetIgmpMulticastIpTab  OBJECT-TYPE
            SYNTAX  SEQUENCE OF  EnetIgmpMulticastIpEty
            ACCESS  not-accessible
            STATUS  mandatory
            DESCRIPTION
                "The Ethernet IGMP Cross VLAN Table."
            ::= { enetIgmpSnoopTable 5 }

        enetIgmpMulticastIpEty  OBJECT-TYPE
            SYNTAX  EnetIgmpMulticastIpEty
            ACCESS  not-accessible
            STATUS  mandatory
            DESCRIPTION
                "An entry in the Ethernet IGMP Cross VLAN Table."
            INDEX { enIgmpMcIpUnit , enIgmpMcIpNumber }
            ::= { enetIgmpMulticastIpTab 1 }

        EnetIgmpMulticastIpEty ::= SEQUENCE {
            enIgmpMcIpUnit              UnitID,
            enIgmpMcIpNumber            INTEGER,
            enIgmpMcIpMulticastIp       IpAddress,
            enIgmpMcIpWan1              INTEGER,
            enIgmpMcIpWan2              INTEGER,
            enIgmpMcIpWan3              INTEGER,
            enIgmpMcIpWan4              INTEGER,
            enIgmpMcIpWan5              INTEGER,
            enIgmpMcIpWan6              INTEGER,
            enIgmpMcIpWan7              INTEGER,
            enIgmpMcIpWan8              INTEGER,
            enIgmpMcIpWan9              INTEGER,
            enIgmpMcIpLan1              INTEGER,
            enIgmpMcIpLan2              INTEGER,
            enIgmpMcIpLan3              INTEGER,
            enIgmpMcIpLan4              INTEGER,
            enIgmpMcIpLan5              INTEGER,
            enIgmpMcIpLan6              INTEGER,
            enIgmpMcIpLan7              INTEGER,
            enIgmpMcIpLan8              INTEGER,
            enIgmpMcIpLan9              INTEGER
        }

        enIgmpMcIpUnit  OBJECT-TYPE
            SYNTAX  UnitID
            ACCESS  read-only
            STATUS  mandatory
            DESCRIPTION
            "unit 1 to 4."
            ::= { enetIgmpMulticastIpEty 1 }

        enIgmpMcIpNumber  OBJECT-TYPE
            SYNTAX  INTEGER (1..32)
            ACCESS  read-only
            STATUS  mandatory
            DESCRIPTION
                "Number 1 to 32"
            ::= { enetIgmpMulticastIpEty 2 }

        enIgmpMcIpMulticastIp  OBJECT-TYPE
            SYNTAX  IpAddress
            ACCESS  read-write
            STATUS  mandatory
            DESCRIPTION
                "IGMP Multicast IP"
            ::= { enetIgmpMulticastIpEty 3 }

        enIgmpMcIpWan1  OBJECT-TYPE
            SYNTAX  INTEGER {
                    off(1),
                    on(2)
                }
            ACCESS  read-write
            STATUS  mandatory
            DESCRIPTION
                "Wan1 For IGMP Multicast IP"
            ::= { enetIgmpMulticastIpEty 4 }

        enIgmpMcIpWan2  OBJECT-TYPE
            SYNTAX  INTEGER {
                    off(1),
                    on(2)
                }
            ACCESS  read-write
            STATUS  mandatory
            DESCRIPTION
                "Wan2 For IGMP Multicast IP"
            ::= { enetIgmpMulticastIpEty 5 }

        enIgmpMcIpWan3  OBJECT-TYPE
            SYNTAX  INTEGER {
                    off(1),
                    on(2)
                }
            ACCESS  read-write
            STATUS  mandatory
            DESCRIPTION
                "Wan3 For IGMP Multicast IP"
            ::= { enetIgmpMulticastIpEty 6 }

        enIgmpMcIpWan4  OBJECT-TYPE
            SYNTAX  INTEGER {
                    off(1),
                    on(2)
                }
            ACCESS  read-write
            STATUS  mandatory
            DESCRIPTION
                "Wan4 For IGMP Multicast IP"
            ::= { enetIgmpMulticastIpEty 7 }

        enIgmpMcIpWan5  OBJECT-TYPE
            SYNTAX  INTEGER {
                    off(1),
                    on(2)
                }
            ACCESS  read-write
            STATUS  mandatory
            DESCRIPTION
                "Wan5 For IGMP Multicast IP"
            ::= { enetIgmpMulticastIpEty 8 }

        enIgmpMcIpWan6  OBJECT-TYPE
            SYNTAX  INTEGER {
                    off(1),
                    on(2)
                }
            ACCESS  read-write
            STATUS  mandatory
            DESCRIPTION
                "Wan6 For IGMP Multicast IP"
            ::= { enetIgmpMulticastIpEty 9 }

        enIgmpMcIpWan7  OBJECT-TYPE
            SYNTAX  INTEGER {
                    off(1),
                    on(2)
                }
            ACCESS  read-write
            STATUS  mandatory
            DESCRIPTION
                "Wan7 For IGMP Multicast IP"
            ::= { enetIgmpMulticastIpEty 10 }

        enIgmpMcIpWan8  OBJECT-TYPE
            SYNTAX  INTEGER {
                    off(1),
                    on(2)
                }
            ACCESS  read-write
            STATUS  mandatory
            DESCRIPTION
                "Wan8 For IGMP Multicast IP"
            ::= { enetIgmpMulticastIpEty 11 }

        enIgmpMcIpWan9  OBJECT-TYPE
            SYNTAX  INTEGER {
                    off(1),
                    on(2)
                }
            ACCESS  read-write
            STATUS  mandatory
            DESCRIPTION
                "Wan9 For IGMP Multicast IP"
            ::= { enetIgmpMulticastIpEty 12 }

        enIgmpMcIpLan1  OBJECT-TYPE
            SYNTAX  INTEGER {
                    off(1),
                    on(2)
                }
            ACCESS  read-write
            STATUS  mandatory
            DESCRIPTION
                "Lan1 For IGMP Multicast IP"
            ::= { enetIgmpMulticastIpEty 13 }

        enIgmpMcIpLan2  OBJECT-TYPE
            SYNTAX  INTEGER {
                    off(1),
                    on(2)
                }
            ACCESS  read-write
            STATUS  mandatory
            DESCRIPTION
                "Lan2 For IGMP Multicast IP"
            ::= { enetIgmpMulticastIpEty 14 }

        enIgmpMcIpLan3  OBJECT-TYPE
            SYNTAX  INTEGER {
                    off(1),
                    on(2)
                }
            ACCESS  read-write
            STATUS  mandatory
            DESCRIPTION
                "Lan3 For IGMP Multicast IP"
            ::= { enetIgmpMulticastIpEty 15 }

        enIgmpMcIpLan4  OBJECT-TYPE
            SYNTAX  INTEGER {
                    off(1),
                    on(2)
                }
            ACCESS  read-write
            STATUS  mandatory
            DESCRIPTION
                "Lan4 For IGMP Multicast IP"
            ::= { enetIgmpMulticastIpEty 16 }

        enIgmpMcIpLan5  OBJECT-TYPE
            SYNTAX  INTEGER {
                    off(1),
                    on(2)
                }
            ACCESS  read-write
            STATUS  mandatory
            DESCRIPTION
                "Lan5 For IGMP Multicast IP"
            ::= { enetIgmpMulticastIpEty 17 }

        enIgmpMcIpLan6  OBJECT-TYPE
            SYNTAX  INTEGER {
                    off(1),
                    on(2)
                }
            ACCESS  read-write
            STATUS  mandatory
            DESCRIPTION
                "Lan6 For IGMP Multicast IP"
            ::= { enetIgmpMulticastIpEty 18 }

        enIgmpMcIpLan7  OBJECT-TYPE
            SYNTAX  INTEGER {
                    off(1),
                    on(2)
                }
            ACCESS  read-write
            STATUS  mandatory
            DESCRIPTION
                "Lan7 For IGMP Multicast IP"
            ::= { enetIgmpMulticastIpEty 19 }

        enIgmpMcIpLan8  OBJECT-TYPE
            SYNTAX  INTEGER {
                    off(1),
                    on(2)
                }
            ACCESS  read-write
            STATUS  mandatory
            DESCRIPTION
                "Lan8 For IGMP Multicast IP"
            ::= { enetIgmpMulticastIpEty 20 }

        enIgmpMcIpLan9  OBJECT-TYPE
            SYNTAX  INTEGER {
                    off(1),
                    on(2)
                }
            ACCESS  read-write
            STATUS  mandatory
            DESCRIPTION
                "Lan9 For IGMP Multicast IP"
            ::= { enetIgmpMulticastIpEty 21 }


--
--   enetIgmpMcIpRangeTab
--
        enetIgmpMcIpRangeTab  OBJECT-TYPE
            SYNTAX  SEQUENCE OF  EnetIgmpMcIpRangeEty
            ACCESS  not-accessible
            STATUS  mandatory
            DESCRIPTION
                "The Ethernet IGMP IP Multicast Range Table."
            ::= { enetIgmpSnoopTable 6 }

        enetIgmpMcIpRangeEty  OBJECT-TYPE
            SYNTAX  EnetIgmpMcIpRangeEty
            ACCESS  not-accessible
            STATUS  mandatory
            DESCRIPTION
                "An entry in the Ethernet IGMP IP Multicast Range Table."
            INDEX { enIgmpMcIpRangeUnit , enIgmpMcIpRangePort }
            ::= { enetIgmpMcIpRangeTab 1 }

        EnetIgmpMcIpRangeEty ::= SEQUENCE {
            enIgmpMcIpRangeUnit         UnitID,
            enIgmpMcIpRangePort         SwPortNum,
            enIgmpMcIpRangeStart        IpAddress,
            enIgmpMcIpRangeEnd          IpAddress
        }

        enIgmpMcIpRangeUnit  OBJECT-TYPE
            SYNTAX  UnitID
            ACCESS  read-only
            STATUS  mandatory
            DESCRIPTION
            "unit 1 to 4."
            ::= { enetIgmpMcIpRangeEty 1 }

        enIgmpMcIpRangePort  OBJECT-TYPE
            SYNTAX  SwPortNum
            ACCESS  read-only
            STATUS  mandatory
            DESCRIPTION
                "Port WAN1~9, LAN1~9."
            ::= { enetIgmpMcIpRangeEty 2 }

        enIgmpMcIpRangeStart  OBJECT-TYPE
            SYNTAX  IpAddress
            ACCESS  read-write
            STATUS  mandatory
            DESCRIPTION
                "Multicast IP Address Start"
            ::= { enetIgmpMcIpRangeEty  3 }

        enIgmpMcIpRangeEnd  OBJECT-TYPE
            SYNTAX  IpAddress
            ACCESS  read-write
            STATUS  mandatory
            DESCRIPTION
                "Multicast IP Address End"
            ::= { enetIgmpMcIpRangeEty  4 }

--
--   enetIPMulticastTab
--
        enetIPMulticastTab  OBJECT-TYPE
            SYNTAX  SEQUENCE OF  EnetIPMulticastEty
            ACCESS  not-accessible
            STATUS  mandatory
            DESCRIPTION
                "The Ethernet IP Multicast Display Table."
            ::= { enetIgmpSnoopTable 7 }

        enetIPMulticastEty  OBJECT-TYPE
            SYNTAX  EnetIPMulticastEty
            ACCESS  not-accessible
            STATUS  mandatory
            DESCRIPTION
                "An entry in the Ethernet IP Multicast Display Table."
            INDEX { enetIPMulticastUnit , enetIPMulticastIndex }
            ::= { enetIPMulticastTab 1 }

        EnetIPMulticastEty ::= SEQUENCE {
            enetIPMulticastUnit         UnitID,
            enetIPMulticastIndex        INTEGER,
            enetIPMulticastVlan         INTEGER,
            enetIPMulticastIp           IpAddress,
            enetIPMulticastWan1         INTEGER,
            enetIPMulticastWan2         INTEGER,
            enetIPMulticastWan3         INTEGER,
            enetIPMulticastWan4         INTEGER,
            enetIPMulticastWan5         INTEGER,
            enetIPMulticastWan6         INTEGER,
            enetIPMulticastWan7         INTEGER,
            enetIPMulticastWan8         INTEGER,
            enetIPMulticastWan9         INTEGER,
            enetIPMulticastLan1         INTEGER,
            enetIPMulticastLan2         INTEGER,
            enetIPMulticastLan3         INTEGER,
            enetIPMulticastLan4         INTEGER,
            enetIPMulticastLan5         INTEGER,
            enetIPMulticastLan6         INTEGER,
            enetIPMulticastLan7         INTEGER,
            enetIPMulticastLan8         INTEGER,
            enetIPMulticastLan9         INTEGER
        }

        enetIPMulticastUnit  OBJECT-TYPE
            SYNTAX  UnitID
            ACCESS  read-only
            STATUS  mandatory
            DESCRIPTION
            "unit 1 to 4."
            ::= { enetIPMulticastEty 1 }

        enetIPMulticastIndex  OBJECT-TYPE
            SYNTAX  INTEGER
            ACCESS  read-only
            STATUS  mandatory
            DESCRIPTION
                "IP Multicast Display Table Index"
            ::= { enetIPMulticastEty 2 }

        enetIPMulticastVlan  OBJECT-TYPE
            SYNTAX  INTEGER (1..4094)
            ACCESS  read-only
            STATUS  mandatory
            DESCRIPTION
                "IP Multicast VlanID "
            ::= { enetIPMulticastEty 3 }

        enetIPMulticastIp  OBJECT-TYPE
            SYNTAX  IpAddress
            ACCESS  read-only
            STATUS  mandatory
            DESCRIPTION
                "IP Multicast IP address"
            ::= { enetIPMulticastEty 4 }

        enetIPMulticastWan1  OBJECT-TYPE
            SYNTAX  INTEGER {
                    off(1),
                    on(2)
                }
            ACCESS  read-only
            STATUS  mandatory
            DESCRIPTION
                "IP Multicast WAN1 on/off"
            ::= { enetIPMulticastEty 5 }

        enetIPMulticastWan2  OBJECT-TYPE
            SYNTAX  INTEGER {
                    off(1),
                    on(2)
                }
            ACCESS  read-only
            STATUS  mandatory
            DESCRIPTION
                "IP Multicast WAN2 on/off"
            ::= { enetIPMulticastEty 6 }

        enetIPMulticastWan3  OBJECT-TYPE
            SYNTAX  INTEGER {
                    off(1),
                    on(2)
                }
            ACCESS  read-only
            STATUS  mandatory
            DESCRIPTION
                "IP Multicast WAN3 on/off"
            ::= { enetIPMulticastEty 7 }


        enetIPMulticastWan4  OBJECT-TYPE
            SYNTAX  INTEGER {
                    off(1),
                    on(2)
                }
            ACCESS  read-only
            STATUS  mandatory
            DESCRIPTION
                "IP Multicast WAN4 on/off"
            ::= { enetIPMulticastEty 8 }


        enetIPMulticastWan5  OBJECT-TYPE
            SYNTAX  INTEGER {
                    off(1),
                    on(2)
                }
            ACCESS  read-only
            STATUS  mandatory
            DESCRIPTION
                "IP Multicast WAN5 on/off"
            ::= { enetIPMulticastEty 9 }


        enetIPMulticastWan6  OBJECT-TYPE
            SYNTAX  INTEGER {
                    off(1),
                    on(2)
                }
            ACCESS  read-only
            STATUS  mandatory
            DESCRIPTION
                "IP Multicast WAN6 on/off"
            ::= { enetIPMulticastEty 10 }


        enetIPMulticastWan7  OBJECT-TYPE
            SYNTAX  INTEGER {
                    off(1),
                    on(2)
                }
            ACCESS  read-only
            STATUS  mandatory
            DESCRIPTION
                "IP Multicast WAN7 on/off"
            ::= { enetIPMulticastEty 11 }


        enetIPMulticastWan8  OBJECT-TYPE
            SYNTAX  INTEGER {
                    off(1),
                    on(2)
                }
            ACCESS  read-only
            STATUS  mandatory
            DESCRIPTION
                "IP Multicast WAN8 on/off"
            ::= { enetIPMulticastEty 12 }


        enetIPMulticastWan9  OBJECT-TYPE
            SYNTAX  INTEGER {
                    off(1),
                    on(2)
                }
            ACCESS  read-only
            STATUS  mandatory
            DESCRIPTION
                "IP Multicast WAN9 on/off"
            ::= { enetIPMulticastEty 13 }

        enetIPMulticastLan1  OBJECT-TYPE
            SYNTAX  INTEGER {
                    off(1),
                    on(2)
                }
            ACCESS  read-only
            STATUS  mandatory
            DESCRIPTION
                "IP Multicast LAN1 on/off"
            ::= { enetIPMulticastEty 14 }

        enetIPMulticastLan2  OBJECT-TYPE
            SYNTAX  INTEGER {
                    off(1),
                    on(2)
                }
            ACCESS  read-only
            STATUS  mandatory
            DESCRIPTION
                "IP Multicast LAN2 on/off"
            ::= { enetIPMulticastEty 15 }

        enetIPMulticastLan3  OBJECT-TYPE
            SYNTAX  INTEGER {
                    off(1),
                    on(2)
                }
            ACCESS  read-only
            STATUS  mandatory
            DESCRIPTION
                "IP Multicast LAN3 on/off"
            ::= { enetIPMulticastEty 16 }


        enetIPMulticastLan4  OBJECT-TYPE
            SYNTAX  INTEGER {
                    off(1),
                    on(2)
                }
            ACCESS  read-only
            STATUS  mandatory
            DESCRIPTION
                "IP Multicast LAN4 on/off"
            ::= { enetIPMulticastEty 17 }


        enetIPMulticastLan5  OBJECT-TYPE
            SYNTAX  INTEGER {
                    off(1),
                    on(2)
                }
            ACCESS  read-only
            STATUS  mandatory
            DESCRIPTION
                "IP Multicast LAN5 on/off"
            ::= { enetIPMulticastEty 18 }


        enetIPMulticastLan6  OBJECT-TYPE
            SYNTAX  INTEGER {
                    off(1),
                    on(2)
                }
            ACCESS  read-only
            STATUS  mandatory
            DESCRIPTION
                "IP Multicast LAN6 on/off"
            ::= { enetIPMulticastEty 19 }


        enetIPMulticastLan7  OBJECT-TYPE
            SYNTAX  INTEGER {
                    off(1),
                    on(2)
                }
            ACCESS  read-only
            STATUS  mandatory
            DESCRIPTION
                "IP Multicast LAN7 on/off"
            ::= { enetIPMulticastEty 20 }


        enetIPMulticastLan8  OBJECT-TYPE
            SYNTAX  INTEGER {
                    off(1),
                    on(2)
                }
            ACCESS  read-only
            STATUS  mandatory
            DESCRIPTION
                "IP Multicast LAN8 on/off"
            ::= { enetIPMulticastEty 21 }


        enetIPMulticastLan9  OBJECT-TYPE
            SYNTAX  INTEGER {
                    off(1),
                    on(2)
                }
            ACCESS  read-only
            STATUS  mandatory
            DESCRIPTION
                "IP Multicast LAN9 on/off"
            ::= { enetIPMulticastEty 22 }



--
--   enetFlowControlTable
--
        enetFlowControlTable  OBJECT-TYPE
            SYNTAX  SEQUENCE OF  EnetFlowControlEntry
            ACCESS  not-accessible
            STATUS  mandatory
            DESCRIPTION
                "The Ethernet Flow Control Table."
            ::= { enetSwitchTable 8 }

        enetFlowControlEntry  OBJECT-TYPE
            SYNTAX  EnetFlowControlEntry
            ACCESS  not-accessible
            STATUS  mandatory
            DESCRIPTION
                "An entry in the Ethernet Flow Control Table."
            INDEX { enFlowCtrlUnit , enFlowCtrlPort }
            ::= { enetFlowControlTable 1 }

        EnetFlowControlEntry ::= SEQUENCE {
            enFlowCtrlUnit              UnitID,
            enFlowCtrlPort              SwPortNum,
            enFlowCtrlFlowCtrl          INTEGER,
            enFlowCtrlAsymmetric        INTEGER
        }

        enFlowCtrlUnit  OBJECT-TYPE
            SYNTAX  UnitID
            ACCESS  read-only
            STATUS  mandatory
            DESCRIPTION
            "unit 1 to 4."
            ::= { enetFlowControlEntry 1 }

        enFlowCtrlPort  OBJECT-TYPE
            SYNTAX  SwPortNum
            ACCESS  read-only
            STATUS  mandatory
            DESCRIPTION
                "Port WAN1~9, LAN1~9."
            ::= { enetFlowControlEntry 2 }

        enFlowCtrlFlowCtrl  OBJECT-TYPE
            SYNTAX  INTEGER {
                    off(1),
                    on(2)
                }
            ACCESS  read-write
            STATUS  mandatory
            DESCRIPTION
                "Flow Control ON/OFF"
            ::= { enetFlowControlEntry 3 }

        enFlowCtrlAsymmetric  OBJECT-TYPE
            SYNTAX  INTEGER {
                    off(1),
                    on(2)
                }
            ACCESS  read-write
            STATUS  mandatory
            DESCRIPTION
                "Flow Control Asymmetric"
            ::= { enetFlowControlEntry 4 }

--
--   enetQosTable
--
    enetQosTable  OBJECT IDENTIFIER ::= { enetSwitchTable 9 }

--
--   enetQosClassOfServTab
--
    enetQosClassOfServTab  OBJECT IDENTIFIER ::= { enetQosTable 1 }

--
--   enetPriorityModeTab
--
        enetPriorityModeTab  OBJECT-TYPE
            SYNTAX  SEQUENCE OF  EnetPriorityModeEty
            ACCESS  not-accessible
            STATUS  mandatory
            DESCRIPTION
                "The Ethernet QoS Priority Mode Table."
            ::= { enetQosClassOfServTab 1 }

        enetPriorityModeEty  OBJECT-TYPE
            SYNTAX  EnetPriorityModeEty
            ACCESS  not-accessible
            STATUS  mandatory
            DESCRIPTION
                "An entry in the Ethernet QoS Priority Mode Table."
            INDEX { enPriModeUnit }
            ::= { enetPriorityModeTab 1 }

        EnetPriorityModeEty ::= SEQUENCE {
            enPriModeUnit               UnitID,
            enPriModeWan1               INTEGER,
            enPriModeWan2               INTEGER,
            enPriModeWan3               INTEGER,
            enPriModeWan4               INTEGER,
            enPriModeWan5               INTEGER,
            enPriModeWan6               INTEGER,
            enPriModeWan7               INTEGER,
            enPriModeWan8               INTEGER,
            enPriModeWan9               INTEGER,
            enPriModeLan1               INTEGER,
            enPriModeLan2               INTEGER,
            enPriModeLan3               INTEGER,
            enPriModeLan4               INTEGER,
            enPriModeLan5               INTEGER,
            enPriModeLan6               INTEGER,
            enPriModeLan7               INTEGER,
            enPriModeLan8               INTEGER,
            enPriModeLan9               INTEGER,
            enPriModePacketPriority     INTEGER
        }

        enPriModeUnit  OBJECT-TYPE
            SYNTAX  UnitID
            ACCESS  read-only
            STATUS  mandatory
            DESCRIPTION
            "unit 1 to 4."
            ::= { enetPriorityModeEty 1 }

        enPriModeWan1  OBJECT-TYPE
            SYNTAX  INTEGER {
                    tag-tos(1),
                    fixed(2)
                }
            ACCESS  read-write
            STATUS  mandatory
            DESCRIPTION
                "WAN1 Priority Mode"
            ::= { enetPriorityModeEty 2 }

        enPriModeWan2  OBJECT-TYPE
            SYNTAX  INTEGER {
                    tag-tos(1),
                    fixed(2)
                }
            ACCESS  read-write
            STATUS  mandatory
            DESCRIPTION
                "WAN2 Priority Mode"
            ::= { enetPriorityModeEty 3 }

        enPriModeWan3  OBJECT-TYPE
            SYNTAX  INTEGER {
                    tag-tos(1),
                    fixed(2)
                }
            ACCESS  read-write
            STATUS  mandatory
            DESCRIPTION
                "WAN3 Priority Mode"
            ::= { enetPriorityModeEty 4 }

        enPriModeWan4  OBJECT-TYPE
            SYNTAX  INTEGER {
                    tag-tos(1),
                    fixed(2)
                }
            ACCESS  read-write
            STATUS  mandatory
            DESCRIPTION
                "WAN4 Priority Mode"
            ::= { enetPriorityModeEty 5 }

        enPriModeWan5  OBJECT-TYPE
            SYNTAX  INTEGER {
                    tag-tos(1),
                    fixed(2)
                }
            ACCESS  read-write
            STATUS  mandatory
            DESCRIPTION
                "WAN5 Priority Mode"
            ::= { enetPriorityModeEty 6 }

        enPriModeWan6  OBJECT-TYPE
            SYNTAX  INTEGER {
                    tag-tos(1),
                    fixed(2)
                }
            ACCESS  read-write
            STATUS  mandatory
            DESCRIPTION
                "WAN6 Priority Mode"
            ::= { enetPriorityModeEty 7 }

        enPriModeWan7  OBJECT-TYPE
            SYNTAX  INTEGER {
                    tag-tos(1),
                    fixed(2)
                }
            ACCESS  read-write
            STATUS  mandatory
            DESCRIPTION
                "WAN7 Priority Mode"
            ::= { enetPriorityModeEty 8 }

        enPriModeWan8  OBJECT-TYPE
            SYNTAX  INTEGER {
                    tag-tos(1),
                    fixed(2)
                }
            ACCESS  read-write
            STATUS  mandatory
            DESCRIPTION
                "WAN8 Priority Mode"
            ::= { enetPriorityModeEty 9 }

        enPriModeWan9  OBJECT-TYPE
            SYNTAX  INTEGER {
                    tag-tos(1),
                    fixed(2)
                }
            ACCESS  read-write
            STATUS  mandatory
            DESCRIPTION
                "WAN9 Priority Mode"
            ::= { enetPriorityModeEty 10 }

        enPriModeLan1  OBJECT-TYPE
            SYNTAX  INTEGER {
                    tag-tos(1),
                    fixed(2)
                }
            ACCESS  read-write
            STATUS  mandatory
            DESCRIPTION
                "LAN1 Priority Mode"
            ::= { enetPriorityModeEty 11 }

        enPriModeLan2  OBJECT-TYPE
            SYNTAX  INTEGER {
                    tag-tos(1),
                    fixed(2)
                }
            ACCESS  read-write
            STATUS  mandatory
            DESCRIPTION
                "LAN2 Priority Mode"
            ::= { enetPriorityModeEty 12 }

        enPriModeLan3  OBJECT-TYPE
            SYNTAX  INTEGER {
                    tag-tos(1),
                    fixed(2)
                }
            ACCESS  read-write
            STATUS  mandatory
            DESCRIPTION
                "LAN3 Priority Mode"
            ::= { enetPriorityModeEty 13 }

        enPriModeLan4  OBJECT-TYPE
            SYNTAX  INTEGER {
                    tag-tos(1),
                    fixed(2)
                }
            ACCESS  read-write
            STATUS  mandatory
            DESCRIPTION
                "LAN4 Priority Mode"
            ::= { enetPriorityModeEty 14 }

        enPriModeLan5  OBJECT-TYPE
            SYNTAX  INTEGER {
                    tag-tos(1),
                    fixed(2)
                }
            ACCESS  read-write
            STATUS  mandatory
            DESCRIPTION
                "LAN5 Priority Mode"
            ::= { enetPriorityModeEty 15 }

        enPriModeLan6  OBJECT-TYPE
            SYNTAX  INTEGER {
                    tag-tos(1),
                    fixed(2)
                }
            ACCESS  read-write
            STATUS  mandatory
            DESCRIPTION
                "LAN6 Priority Mode"
            ::= { enetPriorityModeEty 16 }

        enPriModeLan7  OBJECT-TYPE
            SYNTAX  INTEGER {
                    tag-tos(1),
                    fixed(2)
                }
            ACCESS  read-write
            STATUS  mandatory
            DESCRIPTION
                "LAN7 Priority Mode"
            ::= { enetPriorityModeEty 17 }

        enPriModeLan8  OBJECT-TYPE
            SYNTAX  INTEGER {
                    tag-tos(1),
                    fixed(2)
                }
            ACCESS  read-write
            STATUS  mandatory
            DESCRIPTION
                "LAN8 Priority Mode"
            ::= { enetPriorityModeEty 18 }

        enPriModeLan9  OBJECT-TYPE
            SYNTAX  INTEGER {
                    tag-tos(1),
                    fixed(2)
                }
            ACCESS  read-write
            STATUS  mandatory
            DESCRIPTION
                "LAN9 Priority Mode"
            ::= { enetPriorityModeEty 19 }

        enPriModePacketPriority  OBJECT-TYPE
            SYNTAX  INTEGER {
                    tag(1),
                    tos(2)
                }
            ACCESS  read-write
            STATUS  mandatory
            DESCRIPTION
                "Packet Priority"
            ::= { enetPriorityModeEty 20 }

--
--   enetFixedPriorityTab
--
        enetFixedPriorityTab  OBJECT-TYPE
            SYNTAX  SEQUENCE OF  EnetFixedPriorityEty
            ACCESS  not-accessible
            STATUS  mandatory
            DESCRIPTION
                "The Ethernet QoS Fixed Priority Table."
            ::= { enetQosClassOfServTab 2 }

        enetFixedPriorityEty  OBJECT-TYPE
            SYNTAX  EnetFixedPriorityEty
            ACCESS  not-accessible
            STATUS  mandatory
            DESCRIPTION
                "An entry in the Ethernet QoS Fixed Priority Table."
            INDEX { enFixPriUnit , enFixPriPort }
            ::= { enetFixedPriorityTab 1 }

        EnetFixedPriorityEty ::= SEQUENCE {
            enFixPriUnit                UnitID,
            enFixPriPort                SwPortNum,
            enFixPriTransmitPriority    INTEGER,
            enFixPriDropPrecedence      INTEGER
        }

        enFixPriUnit  OBJECT-TYPE
            SYNTAX  UnitID
            ACCESS  read-only
            STATUS  mandatory
            DESCRIPTION
            "unit 1 to 4."
            ::= { enetFixedPriorityEty 1 }

        enFixPriPort  OBJECT-TYPE
            SYNTAX  SwPortNum
            ACCESS  read-only
            STATUS  mandatory
            DESCRIPTION
                "Port WAN1~9, LAN1~9."
            ::= { enetFixedPriorityEty 2 }

        enFixPriTransmitPriority  OBJECT-TYPE
            SYNTAX  INTEGER {
                    priority-0(1),
                    priority-1(2),
                    priority-2(3),
                    priority-3(4),
                    priority-4(5),
                    priority-5(6),
                    priority-6(7),
                    priority-7(8)
                }
            ACCESS  read-write
            STATUS  mandatory
            DESCRIPTION
                "Transmit Priority"
            ::= { enetFixedPriorityEty 3 }

        enFixPriDropPrecedence  OBJECT-TYPE
            SYNTAX  INTEGER {
                    low-drop(1),
                    high-drop(2)
                }
            ACCESS  read-write
            STATUS  mandatory
            DESCRIPTION
                "Drop Precedence"
            ::= { enetFixedPriorityEty 4 }

--
--   enetVlanTagPriorityTab
--
        enetVlanTagPriorityTab  OBJECT-TYPE
            SYNTAX  SEQUENCE OF  EnetVlanTagPriorityEty
            ACCESS  not-accessible
            STATUS  mandatory
            DESCRIPTION
                "The Ethernet QoS VLAN Tag Priority Table."
            ::= { enetQosClassOfServTab 3 }

        enetVlanTagPriorityEty  OBJECT-TYPE
            SYNTAX  EnetVlanTagPriorityEty
            ACCESS  not-accessible
            STATUS  mandatory
            DESCRIPTION
                "An entry in the Ethernet QoS VLAN Tag Priority Table."
            INDEX { enTagPriUnit , enTagPriTagPriority }
            ::= { enetVlanTagPriorityTab 1 }

        EnetVlanTagPriorityEty ::= SEQUENCE {
            enTagPriUnit                UnitID,
            enTagPriTagPriority         INTEGER,
            enTagPriTransmitPriority    INTEGER,
            enTagPriDropPrecedence      INTEGER
        }

        enTagPriUnit  OBJECT-TYPE
            SYNTAX  UnitID
            ACCESS  read-only
            STATUS  mandatory
            DESCRIPTION
            "unit 1 to 4."
            ::= { enetVlanTagPriorityEty 1 }

        enTagPriTagPriority  OBJECT-TYPE
            SYNTAX  INTEGER {
                    tag-priority-0(1),
                    tag-priority-1(2),
                    tag-priority-2(3),
                    tag-priority-3(4),
                    tag-priority-4(5),
                    tag-priority-5(6),
                    tag-priority-6(7),
                    tag-priority-7(8)
                }
            ACCESS  read-only
            STATUS  mandatory
            DESCRIPTION
                "Vlan Tag Priority 0 to 7"
            ::= { enetVlanTagPriorityEty 2 }

        enTagPriTransmitPriority  OBJECT-TYPE
            SYNTAX  INTEGER {
                    priority-0(1),
                    priority-1(2),
                    priority-2(3),
                    priority-3(4),
                    priority-4(5),
                    priority-5(6),
                    priority-6(7),
                    priority-7(8)
                }
            ACCESS  read-write
            STATUS  mandatory
            DESCRIPTION
                "Transmit Priority"
            ::= { enetVlanTagPriorityEty 3 }

        enTagPriDropPrecedence  OBJECT-TYPE
            SYNTAX  INTEGER {
                    low-drop(1),
                    high-drop(2)
                }
            ACCESS  read-write
            STATUS  mandatory
            DESCRIPTION
                "Drop Precedence"
            ::= { enetVlanTagPriorityEty 4 }

--
--   enetTosPriorityTab
--
        enetTosPriorityTab  OBJECT-TYPE
            SYNTAX  SEQUENCE OF  EnetTosPriorityEty
            ACCESS  not-accessible
            STATUS  mandatory
            DESCRIPTION
                "The Ethernet QoS Tos Priority Table."
            ::= { enetQosClassOfServTab 4 }

        enetTosPriorityEty  OBJECT-TYPE
            SYNTAX  EnetTosPriorityEty
            ACCESS  not-accessible
            STATUS  mandatory
            DESCRIPTION
                "An entry in the Ethernet QoS Tos Priority Table."
            INDEX { enTosPriUnit , enTosPriTosPriority }
            ::= { enetTosPriorityTab 1 }

        EnetTosPriorityEty ::= SEQUENCE {
            enTosPriUnit                UnitID,
            enTosPriTosPriority         INTEGER,
            enTosPriTransmitPriority    INTEGER,
            enTosPriDropPrecedence      INTEGER
        }

        enTosPriUnit  OBJECT-TYPE
            SYNTAX  UnitID
            ACCESS  read-only
            STATUS  mandatory
            DESCRIPTION
            "unit 1 to 4."
            ::= { enetTosPriorityEty 1 }

        enTosPriTosPriority  OBJECT-TYPE
            SYNTAX  INTEGER {
                    tos-priority-0(1),
                    tos-priority-1(2),
                    tos-priority-2(3),
                    tos-priority-3(4),
                    tos-priority-4(5),
                    tos-priority-5(6),
                    tos-priority-6(7),
                    tos-priority-7(8)
                }
            ACCESS  read-only
            STATUS  mandatory
            DESCRIPTION
                "Tos Priority 0 to 7"
            ::= { enetTosPriorityEty 2 }

        enTosPriTransmitPriority  OBJECT-TYPE
            SYNTAX  INTEGER {
                    priority-0(1),
                    priority-1(2),
                    priority-2(3),
                    priority-3(4),
                    priority-4(5),
                    priority-5(6),
                    priority-6(7),
                    priority-7(8)
                }
            ACCESS  read-write
            STATUS  mandatory
            DESCRIPTION
                "Transmit Priority"
            ::= { enetTosPriorityEty 3 }

        enTosPriDropPrecedence  OBJECT-TYPE
            SYNTAX  INTEGER {
                    low-drop(1),
                    high-drop(2)
                }
            ACCESS  read-write
            STATUS  mandatory
            DESCRIPTION
                "Drop Precedence"
            ::= { enetTosPriorityEty 4 }

--
--   enetTosFieldTab
--
        enetTosFieldTab  OBJECT-TYPE
            SYNTAX  SEQUENCE OF  EnetTosFieldEty
            ACCESS  not-accessible
            STATUS  mandatory
            DESCRIPTION
                "The Ethernet QoS Tos Field Table."
            ::= { enetQosClassOfServTab 5 }

        enetTosFieldEty  OBJECT-TYPE
            SYNTAX  EnetTosFieldEty
            ACCESS  not-accessible
            STATUS  mandatory
            DESCRIPTION
                "An entry in the Ethernet QoS Tos Field Table."
            INDEX { enTosFieldUnit }
            ::= { enetTosFieldTab 1 }

        EnetTosFieldEty ::= SEQUENCE {
            enTosFieldUnit              UnitID,
            enTosFieldTosField          INTEGER
        }

        enTosFieldUnit  OBJECT-TYPE
            SYNTAX  UnitID
            ACCESS  read-only
            STATUS  mandatory
            DESCRIPTION
            "unit 1 to 4."
            ::= { enetTosFieldEty 1 }

        enTosFieldTosField  OBJECT-TYPE
            SYNTAX  INTEGER {
                    bit4-bit2(1),
                    bit7-bit5(2)
                }
            ACCESS  read-write
            STATUS  mandatory
            DESCRIPTION
                "Tos Field"
            ::= { enetTosFieldEty 2 }

--
--   enetDistrustedPortTab
--
        enetDistrustedPortTab  OBJECT-TYPE
            SYNTAX  SEQUENCE OF  EnetDistrustedPortEty
            ACCESS  not-accessible
            STATUS  mandatory
            DESCRIPTION
                "The Ethernet QoS Distrusted Port Table."
            ::= { enetQosClassOfServTab 6 }

        enetDistrustedPortEty  OBJECT-TYPE
            SYNTAX  EnetDistrustedPortEty
            ACCESS  not-accessible
            STATUS  mandatory
            DESCRIPTION
                "An entry in the Ethernet QoS Distrusted Port Table."
            INDEX { enDistrustUnit , enDistrustPort }
            ::= { enetDistrustedPortTab 1 }

        EnetDistrustedPortEty ::= SEQUENCE {
            enDistrustUnit              UnitID,
            enDistrustPort              SwPortNum,
            enDistrustDistrusted        INTEGER,
            enDistrustNewTagPriority    INTEGER
        }

        enDistrustUnit  OBJECT-TYPE
            SYNTAX  UnitID
            ACCESS  read-only
            STATUS  mandatory
            DESCRIPTION
            "unit 1 to 4."
            ::= { enetDistrustedPortEty 1 }

        enDistrustPort  OBJECT-TYPE
            SYNTAX  SwPortNum
            ACCESS  read-only
            STATUS  mandatory
            DESCRIPTION
                "Port WAN1~9, LAN1~9."
            ::= { enetDistrustedPortEty 2 }

        enDistrustDistrusted  OBJECT-TYPE
            SYNTAX  INTEGER {
                    trusted(1),
                    distrusted(2)
                }
            ACCESS  read-write
            STATUS  mandatory
            DESCRIPTION
                "Distrusted/Trusted Port Setup"
            ::= { enetDistrustedPortEty 3 }

        enDistrustNewTagPriority  OBJECT-TYPE
            SYNTAX  INTEGER {
                    priority-0(1),
                    priority-1(2),
                    priority-2(3),
                    priority-3(4),
                    priority-4(5),
                    priority-5(6),
                    priority-6(7),
                    priority-7(8)
                }
            ACCESS  read-write
            STATUS  mandatory
            DESCRIPTION
                "New Tag Priority"
            ::= { enetDistrustedPortEty 4 }

--
--   enetQosAccessCtrlTab
--
    enetQosAccessCtrlTab  OBJECT IDENTIFIER ::= { enetQosTable 2 }

--
--   enetWellKnownPortTab
--
        enetWellKnownPortTab  OBJECT-TYPE
            SYNTAX  SEQUENCE OF  EnetWellKnownPortEty
            ACCESS  not-accessible
            STATUS  mandatory
            DESCRIPTION
                "The Ethernet QoS Well Known Port Setup Table."
            ::= { enetQosAccessCtrlTab 1 }

        enetWellKnownPortEty  OBJECT-TYPE
            SYNTAX  EnetWellKnownPortEty
            ACCESS  not-accessible
            STATUS  mandatory
            DESCRIPTION
                "An entry in the Ethernet QoS Well Known Port Setup Table."
            INDEX { enWellKnownPrtUnit , enWellKnownPrtIndex }
            ::= { enetWellKnownPortTab 1 }

        EnetWellKnownPortEty ::= SEQUENCE {
            enWellKnownPrtUnit          UnitID,
            enWellKnownPrtIndex         INTEGER,
            enWellKnownPrtTcpUdpPort    INTEGER,
            enWellKnownPrtEnable        INTEGER,
            enWellKnownPrtPriority      INTEGER,
            enWellKnownPrtPrecedence    INTEGER,
            enWellKnownPrtDiscard       INTEGER
        }

        enWellKnownPrtUnit  OBJECT-TYPE
            SYNTAX  UnitID
            ACCESS  read-only
            STATUS  mandatory
            DESCRIPTION
            "unit 1 to 4."
            ::= { enetWellKnownPortEty 1 }

        enWellKnownPrtIndex  OBJECT-TYPE
            SYNTAX  INTEGER (1..8)
            ACCESS  read-only
            STATUS  mandatory
            DESCRIPTION
                "Index 1-8"
            ::= { enetWellKnownPortEty 2 }

        enWellKnownPrtTcpUdpPort  OBJECT-TYPE
            SYNTAX  INTEGER (1..65535)
            ACCESS  read-only
            STATUS  mandatory
            DESCRIPTION
                "TCP/UDP Port"
            ::= { enetWellKnownPortEty 3 }

        enWellKnownPrtEnable  OBJECT-TYPE
            SYNTAX  INTEGER {
                    disable(1),
                    enable(2)
                }
            ACCESS  read-write
            STATUS  mandatory
            DESCRIPTION
                "Well Known Port Enable/Disable"
            ::= { enetWellKnownPortEty 4 }

        enWellKnownPrtPriority  OBJECT-TYPE
            SYNTAX  INTEGER {
                    priority-0(1),
                    priority-1(2),
                    priority-2(3),
                    priority-3(4)
                }
            ACCESS  read-write
            STATUS  mandatory
            DESCRIPTION
                "Well Known Port Priority(tx)"
            ::= { enetWellKnownPortEty 5 }

        enWellKnownPrtPrecedence  OBJECT-TYPE
            SYNTAX  INTEGER {
                    low-drop(1),
                    high-drop(2)
                }
            ACCESS  read-write
            STATUS  mandatory
            DESCRIPTION
                "Well Known Port Precedence(drop)"
            ::= { enetWellKnownPortEty 6 }

        enWellKnownPrtDiscard  OBJECT-TYPE
            SYNTAX  INTEGER {
                    disable(1),
                    enable(2)
                }
            ACCESS  read-write
            STATUS  mandatory
            DESCRIPTION
                "Well Known Port Discard"
            ::= { enetWellKnownPortEty 7 }

--
--   enetUserDefinePortTab
--
        enetUserDefinePortTab  OBJECT-TYPE
            SYNTAX  SEQUENCE OF  EnetUserDefinePortEty
            ACCESS  not-accessible
            STATUS  mandatory
            DESCRIPTION
                "The Ethernet QoS User Define Port Setup Table."
            ::= { enetQosAccessCtrlTab 2 }

        enetUserDefinePortEty  OBJECT-TYPE
            SYNTAX  EnetUserDefinePortEty
            ACCESS  not-accessible
            STATUS  mandatory
            DESCRIPTION
                "An entry in the Ethernet QoS User Define Port Setup Table."
            INDEX { enUserDefPrtUnit , enUserDefPrtIndex }
            ::= { enetUserDefinePortTab 1 }

        EnetUserDefinePortEty ::= SEQUENCE {
            enUserDefPrtUnit            UnitID,
            enUserDefPrtIndex           INTEGER,
            enUserDefPrtTcpUdpPort      INTEGER,
            enUserDefPrtEnable          INTEGER,
            enUserDefPrtPriority        INTEGER,
            enUserDefPrtPrecedence      INTEGER,
            enUserDefPrtDiscard         INTEGER
        }

        enUserDefPrtUnit  OBJECT-TYPE
            SYNTAX  UnitID
            ACCESS  read-only
            STATUS  mandatory
            DESCRIPTION
            "unit 1 to 4."
            ::= { enetUserDefinePortEty 1 }

        enUserDefPrtIndex  OBJECT-TYPE
            SYNTAX  INTEGER (1..8)
            ACCESS  read-only
            STATUS  mandatory
            DESCRIPTION
                "Index 1-8"
            ::= { enetUserDefinePortEty 2 }

        enUserDefPrtTcpUdpPort  OBJECT-TYPE
            SYNTAX  INTEGER (1..65535)
            ACCESS  read-write
            STATUS  mandatory
            DESCRIPTION
                "TCP/UDP Port"
            ::= { enetUserDefinePortEty 3 }

        enUserDefPrtEnable  OBJECT-TYPE
            SYNTAX  INTEGER {
                    disable(1),
                    enable(2)
                }
            ACCESS  read-write
            STATUS  mandatory
            DESCRIPTION
                "User Define Port Enable/Disable"
            ::= { enetUserDefinePortEty 4 }

        enUserDefPrtPriority  OBJECT-TYPE
            SYNTAX  INTEGER {
                    priority-0(1),
                    priority-1(2),
                    priority-2(3),
                    priority-3(4)
                }
            ACCESS  read-write
            STATUS  mandatory
            DESCRIPTION
                "User Define Port Priority(tx)"
            ::= { enetUserDefinePortEty 5 }

        enUserDefPrtPrecedence  OBJECT-TYPE
            SYNTAX  INTEGER {
                    low-drop(1),
                    high-drop(2)
                }
            ACCESS  read-write
            STATUS  mandatory
            DESCRIPTION
                "User Define Port Precedence(drop)"
            ::= { enetUserDefinePortEty 6 }

        enUserDefPrtDiscard  OBJECT-TYPE
            SYNTAX  INTEGER {
                    disable(1),
                    enable(2)
                }
            ACCESS  read-write
            STATUS  mandatory
            DESCRIPTION
                "User Define Port Discard"
            ::= { enetUserDefinePortEty 7 }

--
--   enetPortRangeTab
--
        enetPortRangeTab  OBJECT-TYPE
            SYNTAX  SEQUENCE OF  EnetPortRangeEty
            ACCESS  not-accessible
            STATUS  mandatory
            DESCRIPTION
                "The Ethernet QoS Port Range Setup Table."
            ::= { enetQosAccessCtrlTab 3 }

        enetPortRangeEty  OBJECT-TYPE
            SYNTAX  EnetPortRangeEty
            ACCESS  not-accessible
            STATUS  mandatory
            DESCRIPTION
                "An entry in the Ethernet QoS Port Range Setup Table."
            INDEX { enPrtRangeUnit }
            ::= { enetPortRangeTab 1 }

        EnetPortRangeEty ::= SEQUENCE {
            enPrtRangeUnit              UnitID,
            enPrtRangePortNumMin        INTEGER,
            enPrtRangePortNumMax        INTEGER,
            enPrtRangeTxPriority        INTEGER,
            enPrtRangeDropPrecedence    INTEGER,
            enPrtRangeFiltering         INTEGER
        }

        enPrtRangeUnit  OBJECT-TYPE
            SYNTAX  UnitID
            ACCESS  read-only
            STATUS  mandatory
            DESCRIPTION
            "unit 1 to 4."
            ::= { enetPortRangeEty 1 }

        enPrtRangePortNumMin  OBJECT-TYPE
            SYNTAX  INTEGER (0..65535)
            ACCESS  read-write
            STATUS  mandatory
            DESCRIPTION
                "Port Num Min"
            ::= { enetPortRangeEty 2 }

        enPrtRangePortNumMax  OBJECT-TYPE
            SYNTAX  INTEGER (0..65535)
            ACCESS  read-write
            STATUS  mandatory
            DESCRIPTION
                "Port Num Max"
            ::= { enetPortRangeEty 3 }

        enPrtRangeTxPriority  OBJECT-TYPE
            SYNTAX  INTEGER {
                    priority-0(1),
                    priority-1(2),
                    priority-2(3),
                    priority-3(4)
                }
            ACCESS  read-write
            STATUS  mandatory
            DESCRIPTION
                "Tx Priority"
            ::= { enetPortRangeEty 4 }

        enPrtRangeDropPrecedence  OBJECT-TYPE
            SYNTAX  INTEGER {
                    low-drop(1),
                    high-drop(2)
                }
            ACCESS  read-write
            STATUS  mandatory
            DESCRIPTION
                "Drop Precedence"
            ::= { enetPortRangeEty 5 }

        enPrtRangeFiltering  OBJECT-TYPE
            SYNTAX  INTEGER {
                    no(1),
                    yes(2)
                }
            ACCESS  read-write
            STATUS  mandatory
            DESCRIPTION
                "Filtering"
            ::= { enetPortRangeEty 6 }

--
--   enetQosTxScheduleTab
--
    enetQosTxScheduleTab  OBJECT IDENTIFIER ::= { enetQosTable 3 }

--
--   enetScheduleAlgorithmTab
--
        enetScheduleAlgorithmTab  OBJECT-TYPE
            SYNTAX  SEQUENCE OF  EnetScheduleAlgorithmEty
            ACCESS  not-accessible
            STATUS  mandatory
            DESCRIPTION
                "The Ethernet QoS Scheduling Algorithm Table."
            ::= { enetQosTxScheduleTab 1 }

        enetScheduleAlgorithmEty  OBJECT-TYPE
            SYNTAX  EnetScheduleAlgorithmEty
            ACCESS  not-accessible
            STATUS  mandatory
            DESCRIPTION
                "An entry in the Ethernet QoS Scheduling Algorithm Table."
            INDEX { enScheduleAlgoUnit , enScheduleAlgoPort }
            ::= { enetScheduleAlgorithmTab 1 }

        EnetScheduleAlgorithmEty ::= SEQUENCE {
            enScheduleAlgoUnit          UnitID,
            enScheduleAlgoPort          SwPortNum,
            enScheduleAlgoP0Queue       INTEGER,
            enScheduleAlgoP1Queue       INTEGER,
            enScheduleAlgoP2Queue       INTEGER,
            enScheduleAlgoP3Queue       INTEGER
        }

        enScheduleAlgoUnit  OBJECT-TYPE
            SYNTAX  UnitID
            ACCESS  read-only
            STATUS  mandatory
            DESCRIPTION
            "unit 1 to 4."
            ::= { enetScheduleAlgorithmEty 1 }

        enScheduleAlgoPort  OBJECT-TYPE
            SYNTAX  SwPortNum
            ACCESS  read-only
            STATUS  mandatory
            DESCRIPTION
                "Port WAN1~9, LAN1~9."
            ::= { enetScheduleAlgorithmEty 2 }

        enScheduleAlgoP0Queue  OBJECT-TYPE
            SYNTAX  INTEGER {
                    strict-priority(1),
                    weighted-fair-queuing(2)
                }
            ACCESS  read-write
            STATUS  mandatory
            DESCRIPTION
                "P0 Queue"
            ::= { enetScheduleAlgorithmEty 3 }

        enScheduleAlgoP1Queue  OBJECT-TYPE
            SYNTAX  INTEGER {
                    strict-priority(1),
                    weighted-fair-queuing(2)
                }
            ACCESS  read-write
            STATUS  mandatory
            DESCRIPTION
                "P1 Queue"
            ::= { enetScheduleAlgorithmEty 4 }

        enScheduleAlgoP2Queue  OBJECT-TYPE
            SYNTAX  INTEGER {
                    strict-priority(1),
                    weighted-fair-queuing(2)
                }
            ACCESS  read-write
            STATUS  mandatory
            DESCRIPTION
                "P2 Queue"
            ::= { enetScheduleAlgorithmEty 5 }

        enScheduleAlgoP3Queue  OBJECT-TYPE
            SYNTAX  INTEGER {
                    strict-priority(1),
                    weighted-fair-queuing(2)
                }
            ACCESS  read-write
            STATUS  mandatory
            DESCRIPTION
                "P3 Queue"
            ::= { enetScheduleAlgorithmEty 6 }

--
--   enetWfqWeightTab
--
        enetWfqWeightTab  OBJECT-TYPE
            SYNTAX  SEQUENCE OF  EnetWfqWeightEty
            ACCESS  not-accessible
            STATUS  mandatory
            DESCRIPTION
                "The Ethernet QoS WFQ Weight Table."
            ::= { enetQosTxScheduleTab 2 }

        enetWfqWeightEty  OBJECT-TYPE
            SYNTAX  EnetWfqWeightEty
            ACCESS  not-accessible
            STATUS  mandatory
            DESCRIPTION
                "An entry in the Ethernet QoS WFQ Weight Table."
            INDEX { enWfqWeightUnit , enWfqWeightPort }
            ::= { enetWfqWeightTab 1 }

        EnetWfqWeightEty ::= SEQUENCE {
            enWfqWeightUnit             UnitID,
            enWfqWeightPort             SwPortNum,
            enWfqWeightP0Queue          INTEGER,
            enWfqWeightP1Queue          INTEGER,
            enWfqWeightP2Queue          INTEGER,
            enWfqWeightP3Queue          INTEGER
        }

        enWfqWeightUnit  OBJECT-TYPE
            SYNTAX  UnitID
            ACCESS  read-only
            STATUS  mandatory
            DESCRIPTION
            "unit 1 to 4."
            ::= { enetWfqWeightEty 1 }

        enWfqWeightPort  OBJECT-TYPE
            SYNTAX  SwPortNum
            ACCESS  read-only
            STATUS  mandatory
            DESCRIPTION
                "Port WAN1~9, LAN1~9."
            ::= { enetWfqWeightEty 2 }

        enWfqWeightP0Queue  OBJECT-TYPE
            SYNTAX  INTEGER (0..100)
            ACCESS  read-write
            STATUS  mandatory
            DESCRIPTION
                "P0 Queue Percentage"
            ::= { enetWfqWeightEty 3 }

        enWfqWeightP1Queue  OBJECT-TYPE
            SYNTAX  INTEGER (0..100)
            ACCESS  read-write
            STATUS  mandatory
            DESCRIPTION
                "P1 Queue Percentage"
            ::= { enetWfqWeightEty 4 }

        enWfqWeightP2Queue  OBJECT-TYPE
            SYNTAX  INTEGER (0..100)
            ACCESS  read-write
            STATUS  mandatory
            DESCRIPTION
                "P2 Queue Percentage"
            ::= { enetWfqWeightEty 5 }

        enWfqWeightP3Queue  OBJECT-TYPE
            SYNTAX  INTEGER (0..100)
            ACCESS  read-write
            STATUS  mandatory
            DESCRIPTION
                "P3 Queue Percentage"
            ::= { enetWfqWeightEty 6 }

--
--   enetQosTxWredTab
--
        enetQosTxWredTab  OBJECT-TYPE
            SYNTAX  SEQUENCE OF  EnetQosTxWredEty
            ACCESS  not-accessible
            STATUS  mandatory
            DESCRIPTION
                "The Ethernet QoS Transmission WRED Table."
            ::= { enetQosTable 4 }

        enetQosTxWredEty  OBJECT-TYPE
            SYNTAX  EnetQosTxWredEty
            ACCESS  not-accessible
            STATUS  mandatory
            DESCRIPTION
                "An entry in the Ethernet QoS Transmission WRED Table."
            INDEX { enTxWredUnit }
            ::= { enetQosTxWredTab 1 }

        EnetQosTxWredEty ::= SEQUENCE {
            enTxWredUnit                UnitID,
            enTxWredX-Percent           INTEGER,
            enTxWredY-Percent           INTEGER,
            enTxWredZ-Percent           INTEGER,
            enTxWredLevel1              INTEGER,
            enTxWredLevel2              INTEGER
        }

        enTxWredUnit  OBJECT-TYPE
            SYNTAX  UnitID
            ACCESS  read-only
            STATUS  mandatory
            DESCRIPTION
            "unit 1 to 4."
            ::= { enetQosTxWredEty 1 }

        enTxWredX-Percent  OBJECT-TYPE
            SYNTAX  INTEGER (0..15)
            ACCESS  read-write
            STATUS  mandatory
            DESCRIPTION
                "Tx WRED X% (Multiple * Granularity 6.25%)"
            ::= { enetQosTxWredEty 2 }

        enTxWredY-Percent  OBJECT-TYPE
            SYNTAX  INTEGER (0..15)
            ACCESS  read-write
            STATUS  mandatory
            DESCRIPTION
                "Tx WRED Y% (Multiple * Granularity 6.25%)"
            ::= { enetQosTxWredEty 3 }

        enTxWredZ-Percent  OBJECT-TYPE
            SYNTAX  INTEGER (0..15)
            ACCESS  read-write
            STATUS  mandatory
            DESCRIPTION
                "Tx WRED Z% (Multiple * Granularity 6.25%)"
            ::= { enetQosTxWredEty 4 }

        enTxWredLevel1  OBJECT-TYPE
            SYNTAX  INTEGER (0..200)
            ACCESS  read-write
            STATUS  mandatory
            DESCRIPTION
                "When destination queue size reaches Level1 threshold, the high-drop packets will be dropped at X%, the low-drop packets will be dropped at Y%."
            ::= { enetQosTxWredEty 5 }

        enTxWredLevel2  OBJECT-TYPE
            SYNTAX  INTEGER (0..200)
            ACCESS  read-write
            STATUS  mandatory
            DESCRIPTION
                "When destination queue size reaches Level2 threshold, the high-drop packets will be dropped at 100%, the low-drop packets will be dropped at Z%."
            ::= { enetQosTxWredEty 6 }

--
--   enetQosRateCtrlTab
--
    enetQosRateCtrlTab  OBJECT IDENTIFIER ::= { enetQosTable 5 }

--
--   enetRateCtrlEnableTab
--
        enetRateCtrlEnableTab  OBJECT-TYPE
            SYNTAX  SEQUENCE OF  EnetRateCtrlEnableEty
            ACCESS  not-accessible
            STATUS  mandatory
            DESCRIPTION
                "The Ethernet QoS Rate Control for egress/ingress Table."
            ::= { enetQosRateCtrlTab 1 }

        enetRateCtrlEnableEty  OBJECT-TYPE
            SYNTAX  EnetRateCtrlEnableEty
            ACCESS  not-accessible
            STATUS  mandatory
            DESCRIPTION
                "An entry in the Ethernet QoS Rate Control for egress/ingress Table."
            INDEX { enRcUnit }
            ::= { enetRateCtrlEnableTab 1 }

        EnetRateCtrlEnableEty ::= SEQUENCE {
            enRcUnit                    UnitID,
            enRcEgressRateCtrl          INTEGER,
            enRcIngressRateCtrl         INTEGER
        }

        enRcUnit  OBJECT-TYPE
            SYNTAX  UnitID
            ACCESS  read-only
            STATUS  mandatory
            DESCRIPTION
            "unit 1 to 4."
            ::= { enetRateCtrlEnableEty 1 }

        enRcEgressRateCtrl  OBJECT-TYPE
            SYNTAX  INTEGER {
                    disable(1),
                    enable(2)
                }
            ACCESS  read-write
            STATUS  mandatory
            DESCRIPTION
                "Egress Rate Control"
            ::= { enetRateCtrlEnableEty 2 }

        enRcIngressRateCtrl  OBJECT-TYPE
            SYNTAX  INTEGER {
                    disable(1),
                    enable(2)
                }
            ACCESS  read-write
            STATUS  mandatory
            DESCRIPTION
                "Ingress Rate Control"
            ::= { enetRateCtrlEnableEty 3 }

--
--   enetIngressWredTab
--
        enetIngressWredTab  OBJECT-TYPE
            SYNTAX  SEQUENCE OF  EnetIngressWredEty
            ACCESS  not-accessible
            STATUS  mandatory
            DESCRIPTION
                "The Ethernet QoS Ingress WRED Table."
            ::= { enetQosRateCtrlTab 2 }

        enetIngressWredEty  OBJECT-TYPE
            SYNTAX  EnetIngressWredEty
            ACCESS  not-accessible
            STATUS  mandatory
            DESCRIPTION
                "An entry in the Ethernet QoS Ingress WRED Table."
            INDEX { enIngressWredUnit }
            ::= { enetIngressWredTab 1 }

        EnetIngressWredEty ::= SEQUENCE {
            enIngressWredUnit           UnitID,
            enIngressWredRa-Percent     INTEGER,
            enIngressWredRb-Percent     INTEGER
        }

        enIngressWredUnit  OBJECT-TYPE
            SYNTAX  UnitID
            ACCESS  read-only
            STATUS  mandatory
            DESCRIPTION
            "unit 1 to 4."
            ::= { enetIngressWredEty 1 }

        enIngressWredRa-Percent  OBJECT-TYPE
            SYNTAX  INTEGER (0..15)
            ACCESS  read-write
            STATUS  mandatory
            DESCRIPTION
                "Ingress WRED Ra% (Multiple * Granularity 6.25%)"
            ::= { enetIngressWredEty 2 }

        enIngressWredRb-Percent  OBJECT-TYPE
            SYNTAX  INTEGER (0..15)
            ACCESS  read-write
            STATUS  mandatory
            DESCRIPTION
                "Ingress WRED Rb% (Multiple * Granularity 6.25%)"
            ::= { enetIngressWredEty 3 }

--
--   enetPortBitrateTab
--
        enetPortBitrateTab  OBJECT-TYPE
            SYNTAX  SEQUENCE OF  EnetPortBitrateEty
            ACCESS  not-accessible
            STATUS  mandatory
            DESCRIPTION
                "The Ethernet QoS Ingress WRED Table."
            ::= { enetQosRateCtrlTab 3 }

        enetPortBitrateEty  OBJECT-TYPE
            SYNTAX  EnetPortBitrateEty
            ACCESS  not-accessible
            STATUS  mandatory
            DESCRIPTION
                "An entry in the Ethernet QoS Ingress WRED Table."
            INDEX { enBitrateUnit , enBitratePort }
            ::= { enetPortBitrateTab 1 }

        EnetPortBitrateEty ::= SEQUENCE {
            enBitrateUnit               UnitID,
            enBitratePort               SwPortNum,
            enBitrateEgressMultiple     INTEGER,
            enBitrateEgressGran         INTEGER,
            enBitrateIngressMultiple    INTEGER,
            enBitrateIngressGran        INTEGER
        }

        enBitrateUnit  OBJECT-TYPE
            SYNTAX  UnitID
            ACCESS  read-only
            STATUS  mandatory
            DESCRIPTION
            "unit 1 to 4."
            ::= { enetPortBitrateEty 1 }

        enBitratePort  OBJECT-TYPE
            SYNTAX  SwPortNum
            ACCESS  read-only
            STATUS  mandatory
            DESCRIPTION
                "Port WAN1~9, LAN1~9."
            ::= { enetPortBitrateEty 2 }

        enBitrateEgressMultiple  OBJECT-TYPE
            SYNTAX  INTEGER (0..1600)
            ACCESS  read-write
            STATUS  mandatory
            DESCRIPTION
                "Egress Multiple (Egress rate = Multiple x Granularity)"
            ::= { enetPortBitrateEty 3 }

        enBitrateEgressGran  OBJECT-TYPE
            SYNTAX  INTEGER {
                    gran-64k(1),
                    gran-640k(2)
                }
            ACCESS  read-write
            STATUS  mandatory
            DESCRIPTION
                "Egress Granularity (Egress rate = Multiple x Granularity)"
            ::= { enetPortBitrateEty 4 }

        enBitrateIngressMultiple  OBJECT-TYPE
            SYNTAX  INTEGER (0..1600)
            ACCESS  read-write
            STATUS  mandatory
            DESCRIPTION
                "Ingress Multiple (Ingress rate = Multiple x Granularity)"
            ::= { enetPortBitrateEty 5 }

        enBitrateIngressGran  OBJECT-TYPE
            SYNTAX  INTEGER {
                    gran-64k(1),
                    gran-640k(2)
                }
            ACCESS  read-write
            STATUS  mandatory
            DESCRIPTION
                "Ingress Granularity (Ingress rate = Multiple x Granularity)"
            ::= { enetPortBitrateEty 6 }

--
--  enetSwMACLearnTable
--
        enetSwMACLearnTable  OBJECT-TYPE
            SYNTAX  SEQUENCE OF  EnetSwMACLearnEntry
            ACCESS  not-accessible
            STATUS  mandatory
            DESCRIPTION
                "The Ethernet Switch MAC Learning Setup Table for e-line."
            ::= { enetSwitchTable 10 }

        enetSwMACLearnEntry  OBJECT-TYPE
            SYNTAX  EnetSwMACLearnEntry
            ACCESS  not-accessible
            STATUS  mandatory
            DESCRIPTION
                "An entry in the Ethernet Switch MAC Learning Setup Table for e-line."
            INDEX { enSwMACLearnUnit }
            ::= { enetSwMACLearnTable 1 }

        EnetSwMACLearnEntry ::= SEQUENCE {
            enSwMACLearnUnit            UnitID,
            enSwMACLearnSetup           INTEGER
        }

        enSwMACLearnUnit  OBJECT-TYPE
            SYNTAX  UnitID
            ACCESS  read-only
            STATUS  mandatory
            DESCRIPTION
            "unit 1 to 4."
            ::= { enetSwMACLearnEntry 1 }


        enSwMACLearnSetup  OBJECT-TYPE
            SYNTAX  INTEGER {
                    enable(1),
                    disable(2)
                }
            ACCESS  read-write
            STATUS  mandatory
            DESCRIPTION
                "MAC Learning Enable/Disable for e-line"
            ::= { enetSwMACLearnEntry 2 }


--
--   enetXcDisplayTable
--
        enetXcDisplayTable  OBJECT-TYPE
            SYNTAX  SEQUENCE OF  EnetXcDisplayEntry
            ACCESS  not-accessible
            STATUS  mandatory
            DESCRIPTION
                "The Ethernet xc display Table."
            ::= { enet-card 11 }

        enetXcDisplayEntry  OBJECT-TYPE
            SYNTAX  EnetXcDisplayEntry
            ACCESS  not-accessible
            STATUS  mandatory
            DESCRIPTION
                "An entry in the Ethernet xc display Table."
            INDEX { enXcDispMap , enXcDispUnit ,
                    enXcDispPort , enXcDispChannel }
            ::= { enetXcDisplayTable 1 }

        EnetXcDisplayEntry ::= SEQUENCE {
            enXcDispMap                 XcMap,
            enXcDispUnit                UnitID,
            enXcDispPort                VcgPortNum,
            enXcDispChannel             ChannelNum,
            enXcDispSrcType             NewXcModel,
            enXcDispSrcSlot             XcSlot,
            enXcDispSrcPort             PortID,
            enXcDispSrcChannel          ChannelNum,
            enXcDispSrcAug1Sts3Path     Aug1Sts3Num,
            enXcDispSrcVc3Sts1Path      Vc3Sts1Num,
            enXcDispSrcVc1xVtxPath      Vc1xVtxNum,
            enXcDispXcGranularity       INTEGER,
            enXcDispXcType              XcType
        }

        enXcDispMap  OBJECT-TYPE
            SYNTAX  XcMap
            ACCESS  read-only
            STATUS  mandatory
            DESCRIPTION
                "xc map index"
            ::= { enetXcDisplayEntry 1 }

        enXcDispUnit  OBJECT-TYPE
            SYNTAX  UnitID
            ACCESS  read-only
            STATUS  mandatory
            DESCRIPTION
            "unit 1 to 4."
            ::= { enetXcDisplayEntry 2 }

        enXcDispPort  OBJECT-TYPE
            SYNTAX  VcgPortNum
            ACCESS  read-only
            STATUS  mandatory
            DESCRIPTION
                "vcg port index: wan1~wan9"
            ::= { enetXcDisplayEntry 3 }

        enXcDispChannel  OBJECT-TYPE
            SYNTAX  ChannelNum
            ACCESS  read-only
            STATUS  mandatory
            DESCRIPTION
                "Channel index"
            ::= { enetXcDisplayEntry 4 }

        enXcDispSrcType  OBJECT-TYPE
            SYNTAX  NewXcModel
            ACCESS  read-only
            STATUS  mandatory
            DESCRIPTION
                " Xc src Unit Type"
            ::= { enetXcDisplayEntry 5 }

        enXcDispSrcSlot  OBJECT-TYPE
            SYNTAX  XcSlot
            ACCESS  read-only
            STATUS  mandatory
            DESCRIPTION
                "Xc src Unit "
            ::= { enetXcDisplayEntry 6 }

        enXcDispSrcPort  OBJECT-TYPE
            SYNTAX  PortID
            ACCESS  read-only
            STATUS  mandatory
            DESCRIPTION
                "Xc src port "
            ::= { enetXcDisplayEntry 7 }

        enXcDispSrcChannel  OBJECT-TYPE
            SYNTAX  ChannelNum
            ACCESS  read-only
            STATUS  mandatory
            DESCRIPTION
                "Xc src channel "
            ::= { enetXcDisplayEntry 8 }

        enXcDispSrcAug1Sts3Path  OBJECT-TYPE
            SYNTAX  Aug1Sts3Num
            ACCESS  read-only
            STATUS  mandatory
            DESCRIPTION
                "Xc src AUG1/STS3 path"
            ::= { enetXcDisplayEntry 9 }

        enXcDispSrcVc3Sts1Path  OBJECT-TYPE
            SYNTAX  Vc3Sts1Num
            ACCESS  read-only
            STATUS  mandatory
            DESCRIPTION
                "Xc src VC3/STS1 path"
            ::= { enetXcDisplayEntry 10 }

        enXcDispSrcVc1xVtxPath  OBJECT-TYPE
            SYNTAX  Vc1xVtxNum
            ACCESS  read-only
            STATUS  mandatory
            DESCRIPTION
                "Xc src VC1x/VTx path"
            ::= { enetXcDisplayEntry 11 }

        enXcDispXcGranularity  OBJECT-TYPE
            SYNTAX  INTEGER {
                    tu3(2),
                    au3-sts1(3),
                    tu11-vt15(4),
                    tu12-vt2(5),
                    vc4-sts3c(6),
                    not-available(100)
                }
            ACCESS  read-only
            STATUS  mandatory
            DESCRIPTION
                "Xc granularity"
            ::= { enetXcDisplayEntry 12 }

        enXcDispXcType  OBJECT-TYPE
            SYNTAX  XcType
            ACCESS  read-only
            STATUS  mandatory
            DESCRIPTION
                "Xc type"
            ::= { enetXcDisplayEntry 13 }

--
--   enetCommandControlTable
--
        enetCommandControlTable  OBJECT-TYPE
            SYNTAX  SEQUENCE OF  EnetCommandControlEntry
            ACCESS  not-accessible
            STATUS  mandatory
            DESCRIPTION
                "The Ethernet Command Control Table."
            ::= { enet-card 12 }

        enetCommandControlEntry  OBJECT-TYPE
            SYNTAX  EnetCommandControlEntry
            ACCESS  not-accessible
            STATUS  mandatory
            DESCRIPTION
                "An entry in the Ethernet xc display Table."
            INDEX { enCmdCtrlUnit }
            ::= { enetCommandControlTable 1 }

        EnetCommandControlEntry ::= SEQUENCE {
            enCmdCtrlUnit               UnitID,
            enCmdCtrlReset              INTEGER,
            enCmdCtrlLoadDefault        INTEGER
        }

        enCmdCtrlUnit  OBJECT-TYPE
            SYNTAX  UnitID
            ACCESS  read-only
            STATUS  mandatory
            DESCRIPTION
            "unit 1 to 4."
            ::= { enetCommandControlEntry 1 }

        enCmdCtrlReset  OBJECT-TYPE
            SYNTAX  INTEGER {
                    cold(2)
                }
            ACCESS  read-write
            STATUS  mandatory
            DESCRIPTION
                "Unit reset"
            ::= { enetCommandControlEntry 2 }

        enCmdCtrlLoadDefault  OBJECT-TYPE
            SYNTAX  INTEGER {
                    load-default(1)
                }
            ACCESS  read-write
            STATUS  mandatory
            DESCRIPTION
                "Unit load default"
            ::= { enetCommandControlEntry 3 }

--
--   enetLinkStatusTable
--
        enetLinkStatusTable  OBJECT-TYPE
            SYNTAX  SEQUENCE OF  EnetLinkStatusEntry
            ACCESS  not-accessible
            STATUS  mandatory
            DESCRIPTION
                "The Ethernet LAN Link Status Table."
            ::= { enet-card 13 }

        enetLinkStatusEntry  OBJECT-TYPE
            SYNTAX  EnetLinkStatusEntry
            ACCESS  not-accessible
            STATUS  mandatory
            DESCRIPTION
                "An entry in the Ethernet LAN Link Status Table."
            INDEX { enLinkStUnit , enLinkStPort }
            ::= { enetLinkStatusTable 1 }

        EnetLinkStatusEntry ::= SEQUENCE {
            enLinkStUnit                UnitID,
            enLinkStPort                LanPortNum,
            enLinkStState               INTEGER,
            enLinkStSpeed               INTEGER
        }

        enLinkStUnit  OBJECT-TYPE
            SYNTAX  UnitID
            ACCESS  read-only
            STATUS  mandatory
            DESCRIPTION
            "unit 1 to 4."
            ::= { enetLinkStatusEntry 1 }

        enLinkStPort  OBJECT-TYPE
            SYNTAX  LanPortNum
            ACCESS  read-only
            STATUS  mandatory
            DESCRIPTION
                "Port LAN1~9."
            ::= { enetLinkStatusEntry 2 }

        enLinkStState  OBJECT-TYPE
            SYNTAX  INTEGER {
                    down(1),
                    up(2)
                }
            ACCESS  read-only
            STATUS  mandatory
            DESCRIPTION
                "The Ethernet LAN Link State"
            ::= { enetLinkStatusEntry 3 }

        enLinkStSpeed  OBJECT-TYPE
            SYNTAX  INTEGER {
                    not-available(1),
                    full-duplex-100M(2),
                    full-duplex-10M(3),
                    half-duplex-100M(4),
                    half-duplex-10M(5),
                    full-duplex-1000M(6)
                }
            ACCESS  read-only
            STATUS  mandatory
            DESCRIPTION
                "The Ethernet LAN Link Speed"
            ::= { enetLinkStatusEntry 4 }

--
-- ENET SNCP/UPSR APS Table
--

        enetSncpApsTab  OBJECT-TYPE
            SYNTAX  SEQUENCE OF  EnetSncpApsEty
            ACCESS  not-accessible
            STATUS  mandatory
            DESCRIPTION
                "ENET SNCP/UPSR APS table "
            ::= { enet-card 14 }

        enetSncpApsEty  OBJECT-TYPE
            SYNTAX  EnetSncpApsEty
            ACCESS  not-accessible
            STATUS  mandatory
            DESCRIPTION
                "ENET SNCP/UPSR APS entry"
            INDEX { enetSncpUnit , enetSncpPort , enetSncpChannel }
            ::= { enetSncpApsTab 1 }

        EnetSncpApsEty ::= SEQUENCE {
            enetSncpUnit                UnitID,
            enetSncpPort                VcgPortNum,
            enetSncpChannel             ChannelNum,
            enetSncpCurrentPathSlot     XcSlot,
            enetSncpCurrentPathPort     PortID,
            enetSncpPrimaryPathSlot     XcSlot,
            enetSncpPrimaryPathPort     PortID,
            enetSncpPPType              XcType,
            enetSncpCmd                 SncpUserCmd
        }

        enetSncpUnit  OBJECT-TYPE
            SYNTAX  UnitID
            ACCESS  read-only
            STATUS  mandatory
            DESCRIPTION
            "unit 1 to 4."
            ::= { enetSncpApsEty 1 }

        enetSncpPort  OBJECT-TYPE
            SYNTAX  VcgPortNum
            ACCESS  read-only
            STATUS  mandatory
            DESCRIPTION
                "VCG #1~#9"
            ::= { enetSncpApsEty 2 }

        enetSncpChannel  OBJECT-TYPE
            SYNTAX  ChannelNum
            ACCESS  read-only
            STATUS  mandatory
            DESCRIPTION
                "CHANNEL #1~#64"
            ::= { enetSncpApsEty 3 }

        enetSncpCurrentPathSlot  OBJECT-TYPE
            SYNTAX  XcSlot
            ACCESS  read-only
            STATUS  mandatory
            DESCRIPTION
                "SNCP/UPSR current path"
            ::= { enetSncpApsEty 4 }

        enetSncpCurrentPathPort  OBJECT-TYPE
            SYNTAX  PortID
            ACCESS  read-only
            STATUS  mandatory
            DESCRIPTION
                "SNCP/UPSR current path"
            ::= { enetSncpApsEty 5 }

        enetSncpPrimaryPathSlot  OBJECT-TYPE
            SYNTAX  XcSlot
            ACCESS  read-only
            STATUS  mandatory
            DESCRIPTION
                "SNCP/UPSR primary path"
            ::= { enetSncpApsEty 6 }

        enetSncpPrimaryPathPort  OBJECT-TYPE
            SYNTAX  PortID
            ACCESS  read-only
            STATUS  mandatory
            DESCRIPTION
                "SNCP/UPSR primary path"
            ::= { enetSncpApsEty 7 }

        enetSncpPPType  OBJECT-TYPE
            SYNTAX  XcType
            ACCESS  read-only
            STATUS  mandatory
            DESCRIPTION
                "SNCP/UPSR path protection type"
            ::= { enetSncpApsEty 8 }

        enetSncpCmd  OBJECT-TYPE
            SYNTAX  SncpUserCmd
            ACCESS  read-write
            STATUS  mandatory
            DESCRIPTION
                "SNCP/UPSR APS command"
            ::= { enetSncpApsEty 9 }

--
-- ENET TPSG Protection Table
--
        enetTPSGProtectTab  OBJECT-TYPE
            SYNTAX  SEQUENCE OF EnetTPSGProtectEty
            ACCESS  not-accessible
            STATUS  mandatory
            DESCRIPTION
                "TPSG protection table"
            ::= { enet-card 15 }

        enetTPSGProtectEty  OBJECT-TYPE
            SYNTAX  EnetTPSGProtectEty
            ACCESS  not-accessible
            STATUS  mandatory
            DESCRIPTION
                "An entry in the TPSG protection table"
            INDEX { enetTPSGProtectUnit }
            ::= { enetTPSGProtectTab 1 }

        EnetTPSGProtectEty ::= SEQUENCE {
            enetTPSGProtectUnit         UnitID,
            enetTPSGProtectActive       INTEGER,
            enetTPSGProtectStatus       INTEGER
        }

        enetTPSGProtectUnit  OBJECT-TYPE
            SYNTAX  UnitID
            ACCESS  read-only
            STATUS  mandatory
            DESCRIPTION
            "unit 1 to 4."
            ::= { enetTPSGProtectEty 1 }

        enetTPSGProtectActive  OBJECT-TYPE
            SYNTAX  INTEGER{
                    none(0),
                    standby(1),
                    working(2)
                }
            ACCESS  read-only
            STATUS  mandatory
            DESCRIPTION
                "TPSG active working/standby"
            ::= { enetTPSGProtectEty 2 }

        enetTPSGProtectStatus  OBJECT-TYPE
            SYNTAX  INTEGER{
                    sync-failed(1),
                    sync-ok(2),
                    start-sync(3),
                    during-sync(4),
                    update-failed(5),
                    unsync(6)
                }
            ACCESS  read-only
            STATUS  mandatory
            DESCRIPTION
                "TPSG Status"
            ::= { enetTPSGProtectEty 3 }

--
-- ENET LCAS Status Table
--
    enetLcasStatusTable       OBJECT IDENTIFIER ::= { enet-card 16 }

--
-- ENET LCAS Sink Status Table
--
        enetLcasSinkStatusTab  OBJECT-TYPE
            SYNTAX  SEQUENCE OF EnetLcasSinkStatusEty
            ACCESS  not-accessible
            STATUS  mandatory
            DESCRIPTION
                "LCAS SINK status table"
            ::= { enetLcasStatusTable 1 }

        enetLcasSinkStatusEty  OBJECT-TYPE
            SYNTAX  EnetLcasSinkStatusEty
            ACCESS  not-accessible
            STATUS  mandatory
            DESCRIPTION
                "An entry in the LCAS SINK status table"
            INDEX { enetLcasSinkUnit , enetLcasSinkPort , enetLcasSinkChannel }
            ::= { enetLcasSinkStatusTab 1 }

        EnetLcasSinkStatusEty ::= SEQUENCE {
            enetLcasSinkUnit            UnitID,
            enetLcasSinkPort            VcgPortNum,
            enetLcasSinkChannel         ChannelNum,
            enetLcasSinkState           INTEGER
        }

        enetLcasSinkUnit  OBJECT-TYPE
            SYNTAX  UnitID
            ACCESS  read-only
            STATUS  mandatory
            DESCRIPTION
            "unit 1 to 4."
            ::= { enetLcasSinkStatusEty 1 }

        enetLcasSinkPort  OBJECT-TYPE
            SYNTAX  VcgPortNum
            ACCESS  read-only
            STATUS  mandatory
            DESCRIPTION
                "vcg port index: wan1~wan9 "
            ::= { enetLcasSinkStatusEty 2 }

        enetLcasSinkChannel  OBJECT-TYPE
            SYNTAX  ChannelNum
            ACCESS  read-only
            STATUS  mandatory
            DESCRIPTION
                "Channel index"
            ::= { enetLcasSinkStatusEty 3 }

        enetLcasSinkState  OBJECT-TYPE
            SYNTAX  INTEGER{
                    not-available(1),
                    add(2),
                    norm(3),
                    eos(4),
                    idle(5),
                    dnu(6),
                    unknown(7)
                }
            ACCESS  read-only
            STATUS  mandatory
            DESCRIPTION
                "LCAS SINK state"
            ::= { enetLcasSinkStatusEty 4 }

--
-- ENET LCAS Source Status Table
--
        enetLcasSourceStatusTab  OBJECT-TYPE
            SYNTAX  SEQUENCE OF EnetLcasSourceStatusEty
            ACCESS  not-accessible
            STATUS  mandatory
            DESCRIPTION
                "LCAS SOURCE status table"
            ::= { enetLcasStatusTable 2 }

        enetLcasSourceStatusEty  OBJECT-TYPE
            SYNTAX  EnetLcasSourceStatusEty
            ACCESS  not-accessible
            STATUS  mandatory
            DESCRIPTION
                "An entry in the LCAS SOURCE status table"
            INDEX { enetLcasSourceUnit , enetLcasSourcePort , enetLcasSourceChannel }
            ::= { enetLcasSourceStatusTab 1 }

        EnetLcasSourceStatusEty ::= SEQUENCE {
            enetLcasSourceUnit          UnitID,
            enetLcasSourcePort          VcgPortNum,
            enetLcasSourceChannel       ChannelNum,
            enetLcasSourceState         INTEGER
        }

        enetLcasSourceUnit  OBJECT-TYPE
            SYNTAX  UnitID
            ACCESS  read-only
            STATUS  mandatory
            DESCRIPTION
            "unit 1 to 4."
            ::= { enetLcasSourceStatusEty 1 }

        enetLcasSourcePort  OBJECT-TYPE
            SYNTAX  VcgPortNum
            ACCESS  read-only
            STATUS  mandatory
            DESCRIPTION
                "vcg port index: wan1~wan9 "
            ::= { enetLcasSourceStatusEty 2 }

        enetLcasSourceChannel  OBJECT-TYPE
            SYNTAX  ChannelNum
            ACCESS  read-only
            STATUS  mandatory
            DESCRIPTION
                "Channel index"
            ::= { enetLcasSourceStatusEty 3 }

        enetLcasSourceState  OBJECT-TYPE
            SYNTAX  INTEGER{
                    not-available(1),
                    add(2),
                    norm(3),
                    eos(4),
                    idle(5),
                    dnu(6),
                    unknown(7)
                }
            ACCESS  read-only
            STATUS  mandatory
            DESCRIPTION
                "LCAS SOURCE state"
            ::= { enetLcasSourceStatusEty 4 }

--2011-3-18 elvis below
--
--   New enetXcDisplayTable
--
        new-enetXcDisplayTable  OBJECT-TYPE
            SYNTAX  SEQUENCE OF  NewEnetXcDisplayEntry
            ACCESS  not-accessible
            STATUS  mandatory
            DESCRIPTION
                "The Ethernet xc display Table."
            ::= { enet-card 17 }

        new-enetXcDisplayEntry  OBJECT-TYPE
            SYNTAX  NewEnetXcDisplayEntry
            ACCESS  not-accessible
            STATUS  mandatory
            DESCRIPTION
                "An entry in the Ethernet xc display Table."
            INDEX { new-enXcDispMap , new-enXcDispUnit ,
                    new-enXcDispPort , new-enXcDispChannel }
            ::= { new-enetXcDisplayTable 1 }

        NewEnetXcDisplayEntry ::= SEQUENCE {
            new-enXcDispMap             XcMap,
            new-enXcDispUnit            UnitID,
            new-enXcDispPort            VcgPortNum,
            new-enXcDispChannel         ChannelNum,
            new-enXcDispPriType         NewXcModel,
            new-enXcDispPriSlot         XcSlot,
            new-enXcDispPriPort         PortID,
            new-enXcDispPriChannel      ChannelNum,
            new-enXcDispPriAug1Sts3Path Aug1Sts3Num,
            new-enXcDispPriVc3Sts1Path  Vc3Sts1Num,
            new-enXcDispPriVc1xVtxPath  Vc1xVtxNum,
            new-enXcDispXcGranularity   INTEGER,
            new-enXcDispXcType          XcType,
            new-enXcDispSecType         NewXcModel,
            new-enXcDispSecSlot         XcSlot,
            new-enXcDispSecPort         PortID,
            new-enXcDispSecChannel      ChannelNum,
            new-enXcDispSecAug1Sts3Path Aug1Sts3Num,
            new-enXcDispSecVc3Sts1Path  Vc3Sts1Num,
            new-enXcDispSecVc1xVtxPath  Vc1xVtxNum
        }

        new-enXcDispMap  OBJECT-TYPE
            SYNTAX  XcMap
            ACCESS  read-only
            STATUS  mandatory
            DESCRIPTION
                "xc map index"
            ::= { new-enetXcDisplayEntry 1 }

        new-enXcDispUnit  OBJECT-TYPE
            SYNTAX  UnitID
            ACCESS  read-only
            STATUS  mandatory
            DESCRIPTION
                "unit 1 to 8, total 8 units."
            ::= { new-enetXcDisplayEntry 2 }

        new-enXcDispPort  OBJECT-TYPE
            SYNTAX  VcgPortNum
            ACCESS  read-only
            STATUS  mandatory
            DESCRIPTION
                "vcg port index: wan1~wan9"
            ::= { new-enetXcDisplayEntry 3 }

        new-enXcDispChannel  OBJECT-TYPE
            SYNTAX  ChannelNum
            ACCESS  read-only
            STATUS  mandatory
            DESCRIPTION
                "Channel index"
            ::= { new-enetXcDisplayEntry 4 }

        new-enXcDispPriType  OBJECT-TYPE
            SYNTAX  NewXcModel
            ACCESS  read-only
            STATUS  mandatory
            DESCRIPTION
                " Xc Primary Unit Type"
            ::= { new-enetXcDisplayEntry 5 }

        new-enXcDispPriSlot  OBJECT-TYPE
            SYNTAX  XcSlot
            ACCESS  read-only
            STATUS  mandatory
            DESCRIPTION
                "Xc Primary Unit "
            ::= { new-enetXcDisplayEntry 6 }

        new-enXcDispPriPort  OBJECT-TYPE
            SYNTAX  PortID
            ACCESS  read-only
            STATUS  mandatory
            DESCRIPTION
                "Xc Primary port "
            ::= { new-enetXcDisplayEntry 7 }

        new-enXcDispPriChannel  OBJECT-TYPE
            SYNTAX  ChannelNum
            ACCESS  read-only
            STATUS  mandatory
            DESCRIPTION
                "Xc Primary channel "
            ::= { new-enetXcDisplayEntry 8 }

        new-enXcDispPriAug1Sts3Path  OBJECT-TYPE
            SYNTAX  Aug1Sts3Num
            ACCESS  read-only
            STATUS  mandatory
            DESCRIPTION
                "Xc Primary AUG1/STS3 path"
            ::= { new-enetXcDisplayEntry 9 }

        new-enXcDispPriVc3Sts1Path  OBJECT-TYPE
            SYNTAX  Vc3Sts1Num
            ACCESS  read-only
            STATUS  mandatory
            DESCRIPTION
                "Xc Primary VC3/STS1 path"
            ::= { new-enetXcDisplayEntry 10 }

        new-enXcDispPriVc1xVtxPath  OBJECT-TYPE
            SYNTAX  Vc1xVtxNum
            ACCESS  read-only
            STATUS  mandatory
            DESCRIPTION
                "Xc Primary VC1x/VTx path"
            ::= { new-enetXcDisplayEntry 11 }

        new-enXcDispXcGranularity  OBJECT-TYPE
            SYNTAX  INTEGER {
                    tu3(2),
                    au3-sts1(3),
                    tu11-vt15(4),
                    tu12-vt2(5),
                    vc4-sts3c(6),
                    not-available(100)
                }
            ACCESS  read-only
            STATUS  mandatory
            DESCRIPTION
                "Xc granularity"
            ::= { new-enetXcDisplayEntry 12 }

        new-enXcDispXcType  OBJECT-TYPE
            SYNTAX  XcType
            ACCESS  read-only
            STATUS  mandatory
            DESCRIPTION
                "Xc type"
            ::= { new-enetXcDisplayEntry 13 }

        new-enXcDispSecType  OBJECT-TYPE
            SYNTAX  NewXcModel
            ACCESS  read-only
            STATUS  mandatory
            DESCRIPTION
                " Xc Secondary Unit Type"
            ::= { new-enetXcDisplayEntry 14 }

        new-enXcDispSecSlot  OBJECT-TYPE
            SYNTAX  XcSlot
            ACCESS  read-only
            STATUS  mandatory
            DESCRIPTION
                "Xc Secondary Unit "
            ::= { new-enetXcDisplayEntry 15 }

        new-enXcDispSecPort  OBJECT-TYPE
            SYNTAX  PortID
            ACCESS  read-only
            STATUS  mandatory
            DESCRIPTION
                "Xc Secondary port "
            ::= { new-enetXcDisplayEntry 16 }

        new-enXcDispSecChannel  OBJECT-TYPE
            SYNTAX  ChannelNum
            ACCESS  read-only
            STATUS  mandatory
            DESCRIPTION
                "Xc Secondary channel "
            ::= { new-enetXcDisplayEntry 17 }

        new-enXcDispSecAug1Sts3Path  OBJECT-TYPE
            SYNTAX  Aug1Sts3Num
            ACCESS  read-only
            STATUS  mandatory
            DESCRIPTION
                "Xc Secondary AUG1/STS3 path"
            ::= { new-enetXcDisplayEntry 18 }

        new-enXcDispSecVc3Sts1Path  OBJECT-TYPE
            SYNTAX  Vc3Sts1Num
            ACCESS  read-only
            STATUS  mandatory
            DESCRIPTION
                "Xc Secondary VC3/STS1 path"
            ::= { new-enetXcDisplayEntry 19 }

        new-enXcDispSecVc1xVtxPath  OBJECT-TYPE
            SYNTAX  Vc1xVtxNum
            ACCESS  read-only
            STATUS  mandatory
            DESCRIPTION
                "Xc Secondary VC1x/VTx path"
            ::= { new-enetXcDisplayEntry 20 }

--
-- New ENET SNCP/UPSR APS Table
--

        new-enetSncpApsTab  OBJECT-TYPE
            SYNTAX  SEQUENCE OF  NewEnetSncpApsEty
            ACCESS  not-accessible
            STATUS  mandatory
            DESCRIPTION
                "ENET SNCP/UPSR APS table "
            ::= { enet-card 18 }

        new-enetSncpApsEty  OBJECT-TYPE
            SYNTAX  NewEnetSncpApsEty
            ACCESS  not-accessible
            STATUS  mandatory
            DESCRIPTION
                "ENET SNCP/UPSR APS entry"
            INDEX { new-enetSncpUnit , new-enetSncpPort , new-enetSncpChannel }
            ::= { new-enetSncpApsTab 1 }

        NewEnetSncpApsEty ::= SEQUENCE {
            new-enetSncpUnit            UnitID,
            new-enetSncpPort            VcgPortNum,
            new-enetSncpChannel         ChannelNum,
            new-enetSncpCurrSlot        XcSlot,
            new-enetSncpCurrPort        PortID,
            new-enetSncpCurrChannel     ChannelNum,
            new-enetSncpCurrAug1Sts3Path    Aug1Sts3Num,
            new-enetSncpCurrVc3Sts1Path     Vc3Sts1Num,
            new-enetSncpCurrVc1xVtxPath     Vc1xVtxNum,
            new-enetSncpPPType              XcType,
            new-enetSncpCmd                 SncpUserCmd,
            new-enetSncpRevertive           INTEGER
        }

        new-enetSncpUnit  OBJECT-TYPE
            SYNTAX  UnitID
            ACCESS  read-only
            STATUS  mandatory
            DESCRIPTION
                "unit 1 to 8, total 8 units."
            ::= { new-enetSncpApsEty 1 }

        new-enetSncpPort  OBJECT-TYPE
            SYNTAX  VcgPortNum
            ACCESS  read-only
            STATUS  mandatory
            DESCRIPTION
                "VCG #1~#9"
            ::= { new-enetSncpApsEty 2 }

        new-enetSncpChannel  OBJECT-TYPE
            SYNTAX  ChannelNum
            ACCESS  read-only
            STATUS  mandatory
            DESCRIPTION
                "CHANNEL #1~#64"
            ::= { new-enetSncpApsEty 3 }

        new-enetSncpCurrSlot  OBJECT-TYPE
            SYNTAX  XcSlot
            ACCESS  read-only
            STATUS  mandatory
            DESCRIPTION
                "SNCP/UPSR current slot"
            ::= { new-enetSncpApsEty 4 }

        new-enetSncpCurrPort  OBJECT-TYPE
            SYNTAX  PortID
            ACCESS  read-only
            STATUS  mandatory
            DESCRIPTION
                "SNCP/UPSR current port"
            ::= { new-enetSncpApsEty 5 }

        new-enetSncpCurrChannel  OBJECT-TYPE
            SYNTAX  ChannelNum
            ACCESS  read-only
            STATUS  mandatory
            DESCRIPTION
                "SNCP/UPSR current channel"
            ::= { new-enetSncpApsEty 6 }

        new-enetSncpCurrAug1Sts3Path  OBJECT-TYPE
            SYNTAX  Aug1Sts3Num
            ACCESS  read-only
            STATUS  mandatory
            DESCRIPTION
                "SNCP/UPSR current Aug1/Sts3"
            ::= { new-enetSncpApsEty 7 }

        new-enetSncpCurrVc3Sts1Path  OBJECT-TYPE
            SYNTAX  Vc3Sts1Num
            ACCESS  read-only
            STATUS  mandatory
            DESCRIPTION
                "SNCP/UPSR current Vc3/Sts1"
            ::= { new-enetSncpApsEty 8 }

        new-enetSncpCurrVc1xVtxPath  OBJECT-TYPE
            SYNTAX  Vc1xVtxNum
            ACCESS  read-only
            STATUS  mandatory
            DESCRIPTION
                "SNCP/UPSR current Vc1x/Vtx"
            ::= { new-enetSncpApsEty 9 }

        new-enetSncpPPType  OBJECT-TYPE
            SYNTAX  XcType
            ACCESS  read-only
            STATUS  mandatory
            DESCRIPTION
                "SNCP/UPSR path protection type"
            ::= { new-enetSncpApsEty 10 }

        new-enetSncpCmd  OBJECT-TYPE
            SYNTAX  SncpUserCmd
            ACCESS  read-write
            STATUS  mandatory
            DESCRIPTION
                "SNCP/UPSR APS command"
            ::= { new-enetSncpApsEty 11 }

        new-enetSncpRevertive  OBJECT-TYPE
            SYNTAX  INTEGER {
                    non-revertive(1),
                    revertive(2)
                }
            ACCESS  read-write
            STATUS  mandatory
            DESCRIPTION
                "SNCP/UPSR revertive or non-revertive"
            ::= { new-enetSncpApsEty 12 }

        enetTotalCard   OBJECT-TYPE
            SYNTAX  INTEGER
            ACCESS  read-only
            STATUS  mandatory
            DESCRIPTION
                "Total cards of enet"
            ::= { enet-card 100 }

--2011-3-18 elvis above

--======================================================================--
--======================================================================--
--  e3-card MIB
--======================================================================--
--======================================================================--

            HoPathPerfAnomalyType ::= INTEGER {
        rei(1),
        bip(2)
    }

--
--  E3 Config
--

    e3Config           OBJECT IDENTIFIER ::= { e3-card 1 }


--
--  E3 Channel Line Interface Setup Table
--

        e3ChLineIntfSetupTab  OBJECT-TYPE
            SYNTAX  SEQUENCE OF E3ChLineIntfSetupEty
            ACCESS  not-accessible
            STATUS  mandatory
            DESCRIPTION
                "Channel line interface setup table"
            ::= { e3Config 1 }

        e3ChLineIntfSetupEty  OBJECT-TYPE
            SYNTAX  E3ChLineIntfSetupEty
            ACCESS  not-accessible
            STATUS  mandatory
            DESCRIPTION
                "An entry in the channel line interface setup table"
            INDEX { e3ChLineIntfUnit ,
                    e3ChLineIntfPort }
            ::= { e3ChLineIntfSetupTab 1 }

        E3ChLineIntfSetupEty ::= SEQUENCE {
            e3ChLineIntfUnit            UnitID,
            e3ChLineIntfPort            PortID,
            e3ChLineIntfCoding          INTEGER,
            e3ChLineIntfType            INTEGER
        }

        e3ChLineIntfUnit  OBJECT-TYPE
            SYNTAX  UnitID
            ACCESS  read-only
            STATUS  mandatory
            DESCRIPTION
            "unit 1 to 4."
            ::= { e3ChLineIntfSetupEty 1 }

        e3ChLineIntfPort  OBJECT-TYPE
            SYNTAX  PortID
            ACCESS  read-only
            STATUS  mandatory
            DESCRIPTION
                "E3 Port 1 to 3"
            ::= { e3ChLineIntfSetupEty 2 }

        e3ChLineIntfCoding  OBJECT-TYPE
            SYNTAX  INTEGER{
                    hdb3(1)
                }
            ACCESS  read-only
            STATUS  mandatory
            DESCRIPTION
                "E3 line coding mode"
            ::= { e3ChLineIntfSetupEty 3 }

        e3ChLineIntfType  OBJECT-TYPE
            SYNTAX  INTEGER{
                    unframe(1),
                    g751(3)
                }
            ACCESS  read-write
            STATUS  mandatory
            DESCRIPTION
                "E3 line type"
            ::= { e3ChLineIntfSetupEty 4 }


--
-- E3 Trace Message & Signal Label Setup Table
--

    e3OverheadSetup           OBJECT IDENTIFIER ::= { e3Config 2 }


--
-- E3 High Order Trace Message & Signal Label Setup Table
--

        e3HoSTSOverheadSetupTab  OBJECT-TYPE
            SYNTAX  SEQUENCE OF E3HoSTSOverheadSetupEty
            ACCESS  not-accessible
            STATUS  mandatory
            DESCRIPTION
                "High order Trace message & Signal label setup table"
            ::= { e3OverheadSetup 1 }

        e3HoSTSOverheadSetupEty  OBJECT-TYPE
            SYNTAX  E3HoSTSOverheadSetupEty
            ACCESS  not-accessible
            STATUS  mandatory
            DESCRIPTION
                "An entry in the trace message & signal label setup table"
            INDEX { e3HoSTSOverheadUnit ,
                    e3HoSTSOverheadPort }
            ::= { e3HoSTSOverheadSetupTab 1 }

        E3HoSTSOverheadSetupEty ::= SEQUENCE {
            e3HoSTSOverheadUnit         UnitID,
            e3HoSTSOverheadPort         PortID,
            e3HoSTSOverheadLength       MsgLen,
            e3HoSTSOverheadExpMsg       DisplayString(SIZE(0..64)),
            e3HoSTSOverheadTxMsg        DisplayString(SIZE(0..64)),
            e3HoSTSOverheadRxMsg        DisplayString(SIZE(0..64)),
            e3HoSTSOverheadEPSL         INTEGER,
            e3HoSTSOverheadExpMsg1B     INTEGER(0..255),
            e3HoSTSOverheadTxMsg1B      INTEGER(0..255),
            e3HoSTSOverheadRxMsg1B      INTEGER(0..255),
            e3HoSTSOverheadTxPSL        INTEGER,
            e3HoSTSOverheadRxPSL        INTEGER
        }

        e3HoSTSOverheadUnit  OBJECT-TYPE
            SYNTAX  UnitID
            ACCESS  read-only
            STATUS  mandatory
            DESCRIPTION
            "unit 1 to 4."
            ::= { e3HoSTSOverheadSetupEty 1 }

        e3HoSTSOverheadPort  OBJECT-TYPE
            SYNTAX  PortID
            ACCESS  read-only
            STATUS  mandatory
            DESCRIPTION
                "E3 Port 1 to 3"
            ::= { e3HoSTSOverheadSetupEty 2 }

        e3HoSTSOverheadLength  OBJECT-TYPE
            SYNTAX  MsgLen
            ACCESS  read-write
            STATUS  mandatory
            DESCRIPTION
                "message length"
            ::= { e3HoSTSOverheadSetupEty 3 }

        e3HoSTSOverheadExpMsg OBJECT-TYPE
            SYNTAX  DisplayString (SIZE(0..64))
            ACCESS  read-write
            STATUS  mandatory
            DESCRIPTION
                "The expected message"
            ::= { e3HoSTSOverheadSetupEty 4 }

        e3HoSTSOverheadTxMsg OBJECT-TYPE
            SYNTAX  DisplayString (SIZE(0..64))
            ACCESS  read-write
            STATUS  mandatory
            DESCRIPTION
                "The tx message"
            ::= { e3HoSTSOverheadSetupEty 5 }

        e3HoSTSOverheadRxMsg OBJECT-TYPE
            SYNTAX  DisplayString (SIZE(0..64))
            ACCESS  read-only
            STATUS  mandatory
            DESCRIPTION
                "The rx message"
            ::= { e3HoSTSOverheadSetupEty 6 }

        e3HoSTSOverheadEPSL  OBJECT-TYPE
            SYNTAX  INTEGER(0..255)
            ACCESS  read-write
            STATUS  mandatory
            DESCRIPTION
                "The expected Path Signal Label"
            ::= { e3HoSTSOverheadSetupEty 7 }

        e3HoSTSOverheadExpMsg1B OBJECT-TYPE
            SYNTAX  INTEGER(0..255)
            ACCESS  read-write
            STATUS  mandatory
            DESCRIPTION
                "The expected message (1byte)"
            ::= { e3HoSTSOverheadSetupEty 8 }

        e3HoSTSOverheadTxMsg1B OBJECT-TYPE
            SYNTAX  INTEGER(0..255)
            ACCESS  read-write
            STATUS  mandatory
            DESCRIPTION
                "The tx message (1byte)"
            ::= { e3HoSTSOverheadSetupEty 9 }

        e3HoSTSOverheadRxMsg1B OBJECT-TYPE
            SYNTAX  INTEGER(0..255)
            ACCESS  read-only
            STATUS  mandatory
            DESCRIPTION
                "The rx message (1byte)"
            ::= { e3HoSTSOverheadSetupEty 10 }

        e3HoSTSOverheadTxPSL  OBJECT-TYPE
            SYNTAX  INTEGER(0..255)
            ACCESS  read-write
            STATUS  mandatory
            DESCRIPTION
                "The Tx Path Signal Label"
            ::= { e3HoSTSOverheadSetupEty 11 }

        e3HoSTSOverheadRxPSL  OBJECT-TYPE
            SYNTAX  INTEGER(0..255)
            ACCESS  read-only
            STATUS  mandatory
            DESCRIPTION
                "The Rx Path Signal Label"
            ::= { e3HoSTSOverheadSetupEty 12 }

--
-- E3 Low Order Trace Message & Signal Label Setup Table
--

        e3LoVTOverheadSetupTab  OBJECT-TYPE
            SYNTAX  SEQUENCE OF E3LoVTOverheadSetupEty
            ACCESS  not-accessible
            STATUS  mandatory
            DESCRIPTION
                "Low Order Trace message & Signal label setup table"
            ::= { e3OverheadSetup 2 }

        e3LoVTOverheadSetupEty  OBJECT-TYPE
            SYNTAX  E3LoVTOverheadSetupEty
            ACCESS  not-accessible
            STATUS  mandatory
            DESCRIPTION
                "An entry in the trace message & signal label setup table"
            INDEX { e3LoVTOverheadUnit ,
                    e3LoVTOverheadPort ,
                    e3LoVTOverheadChannel }
            ::= { e3LoVTOverheadSetupTab 1 }

        E3LoVTOverheadSetupEty ::= SEQUENCE {
            e3LoVTOverheadUnit          UnitID,
            e3LoVTOverheadPort          PortID,
            e3LoVTOverheadChannel       ChannelNum,
            e3LoVTOverheadLength        INTEGER,
            e3LoVTOverheadExpMsg        DisplayString(SIZE(0..64)),
            e3LoVTOverheadTxMsg         DisplayString(SIZE(0..64)),
            e3LoVTOverheadRxMsg         DisplayString(SIZE(0..64)),
            e3LoVTOverheadEPSL          INTEGER,
            e3LoVTOverheadTxPSL         INTEGER,
            e3LoVTOverheadRxPSL         INTEGER
        }

        e3LoVTOverheadUnit  OBJECT-TYPE
            SYNTAX  UnitID
            ACCESS  read-only
            STATUS  mandatory
            DESCRIPTION
            "unit 1 to 4."
            ::= { e3LoVTOverheadSetupEty 1 }

        e3LoVTOverheadPort  OBJECT-TYPE
            SYNTAX  PortID
            ACCESS  read-only
            STATUS  mandatory
            DESCRIPTION
                "E3 Port 1 to 3"
            ::= { e3LoVTOverheadSetupEty 2 }

        e3LoVTOverheadChannel  OBJECT-TYPE
            SYNTAX  ChannelNum
            ACCESS  read-only
            STATUS  mandatory
            DESCRIPTION
                "E3 Channel 1 to 28"
            ::= { e3LoVTOverheadSetupEty 3 }

        e3LoVTOverheadLength  OBJECT-TYPE
            SYNTAX  INTEGER{
                    null(1),
                    len-16-BYTE-space(2),
                    len-16-BYTE-null(4)
                }
            ACCESS  read-write
            STATUS  mandatory
            DESCRIPTION
                "message length"
            ::= { e3LoVTOverheadSetupEty 4 }

        e3LoVTOverheadExpMsg OBJECT-TYPE
            SYNTAX  DisplayString (SIZE(0..64))
            ACCESS  read-write
            STATUS  mandatory
            DESCRIPTION
                "The expected message"
            ::= { e3LoVTOverheadSetupEty 5 }

        e3LoVTOverheadTxMsg OBJECT-TYPE
            SYNTAX  DisplayString (SIZE(0..64))
            ACCESS  read-write
            STATUS  mandatory
            DESCRIPTION
                "The tx message"
            ::= { e3LoVTOverheadSetupEty 6 }

        e3LoVTOverheadRxMsg OBJECT-TYPE
            SYNTAX  DisplayString (SIZE(0..64))
            ACCESS  read-only
            STATUS  mandatory
            DESCRIPTION
                "The rx message"
            ::= { e3LoVTOverheadSetupEty 7 }

        e3LoVTOverheadEPSL  OBJECT-TYPE
            SYNTAX  INTEGER(0..255)
            ACCESS  read-write
            STATUS  mandatory
            DESCRIPTION
                "The expected Path Signal Label"
            ::= { e3LoVTOverheadSetupEty 8 }

        e3LoVTOverheadTxPSL  OBJECT-TYPE
            SYNTAX  INTEGER(0..255)
            ACCESS  read-write
            STATUS  mandatory
            DESCRIPTION
                "The Tx Path Signal Label"
            ::= { e3LoVTOverheadSetupEty 9 }

        e3LoVTOverheadRxPSL  OBJECT-TYPE
            SYNTAX  INTEGER(0..255)
            ACCESS  read-only
            STATUS  mandatory
            DESCRIPTION
                "The Rx Path Signal Label"
            ::= { e3LoVTOverheadSetupEty 10 }

--
--  E3 Customer Information Setup Table
--

        e3CustomerInfoSetupTab  OBJECT-TYPE
            SYNTAX  SEQUENCE OF E3CustomerInfoSetupEty
            ACCESS  not-accessible
            STATUS  mandatory
            DESCRIPTION
                "Customer information setup table"
            ::= { e3Config 3 }

        e3CustomerInfoSetupEty  OBJECT-TYPE
            SYNTAX  E3CustomerInfoSetupEty
            ACCESS  not-accessible
            STATUS  mandatory
            DESCRIPTION
                "An entry in the customer information setup table"
            INDEX { e3CustomerInfoUnit ,
                    e3CustomerInfoPort }
            ::= { e3CustomerInfoSetupTab 1 }

        E3CustomerInfoSetupEty ::= SEQUENCE {
            e3CustomerInfoUnit          UnitID,
            e3CustomerInfoPort          PortID,
            e3CustomerInfoString        DisplayString(SIZE(0..32))
        }

        e3CustomerInfoUnit  OBJECT-TYPE
            SYNTAX  UnitID
            ACCESS  read-only
            STATUS  mandatory
            DESCRIPTION
            "unit 1 to 4."
            ::= { e3CustomerInfoSetupEty 1 }

        e3CustomerInfoPort  OBJECT-TYPE
            SYNTAX  PortID
            ACCESS  read-only
            STATUS  mandatory
            DESCRIPTION
                "E3 Port 1 to 3"
            ::= { e3CustomerInfoSetupEty 2 }

        e3CustomerInfoString OBJECT-TYPE
            SYNTAX  DisplayString (SIZE(0..32))
            ACCESS  read-write
            STATUS  mandatory
            DESCRIPTION
                "Customer information"
            ::= { e3CustomerInfoSetupEty 3 }

--
-- E3 TPSG Protection Setup Table
--
        e3TPSGProtectSetupTab  OBJECT-TYPE
            SYNTAX  SEQUENCE OF E3TPSGProtectSetupEty
            ACCESS  not-accessible
            STATUS  mandatory
            DESCRIPTION
                "TPSG protection setup table"
            ::= { e3Config 4 }

        e3TPSGProtectSetupEty  OBJECT-TYPE
            SYNTAX  E3TPSGProtectSetupEty
            ACCESS  not-accessible
            STATUS  mandatory
            DESCRIPTION
                "An entry in the TPSG protection setup table"
            INDEX { e3TPSGProtectUnit }
            ::= { e3TPSGProtectSetupTab 1 }

        E3TPSGProtectSetupEty ::= SEQUENCE {
            e3TPSGProtectUnit           UnitID,
            e3TPSGProtectActive         INTEGER,
            e3TPSGProtectStatus         INTEGER,
            e3TPSGProtectType           INTEGER,
            e3TPSGProtectMode           INTEGER
        }

        e3TPSGProtectUnit  OBJECT-TYPE
            SYNTAX  UnitID
            ACCESS  read-only
            STATUS  mandatory
            DESCRIPTION
            "unit 1 to 4."
            ::= { e3TPSGProtectSetupEty 1 }

        e3TPSGProtectActive  OBJECT-TYPE
            SYNTAX  INTEGER{
                    none(0),
                    standby(1),
                    working(2)
                }
            ACCESS  read-only
            STATUS  mandatory
            DESCRIPTION
                "TPSG active working/standby"
            ::= { e3TPSGProtectSetupEty 2 }

        e3TPSGProtectStatus  OBJECT-TYPE
            SYNTAX  INTEGER{
                    sync-failed(1),
                    sync-ok(2),
                    start-sync(3),
                    during-sync(4),
                    update-failed(5),
                    unsync(6)
                }
            ACCESS  read-only
            STATUS  mandatory
            DESCRIPTION
                "TPSG Status"
            ::= { e3TPSGProtectSetupEty 3 }

        e3TPSGProtectType  OBJECT-TYPE
            SYNTAX  INTEGER{
                    port-circuit-protection(3),
                    line-1-plus-1(4)
                }
            ACCESS  read-write
            STATUS  mandatory
            DESCRIPTION
                "TPSG protection type"
            ::= { e3TPSGProtectSetupEty 4 }

        e3TPSGProtectMode  OBJECT-TYPE
            SYNTAX  INTEGER{
                    non-revertible(1),
                    revertible(2)
                }
            ACCESS  read-write
            STATUS  mandatory
            DESCRIPTION
                "TPSG protection mode"
            ::= { e3TPSGProtectSetupEty 5 }


--
--  E3 Mapping Mode Setup Table
--

        e3MappingModeSetupTab  OBJECT-TYPE
            SYNTAX  SEQUENCE OF E3MappingModeSetupEty
            ACCESS  not-accessible
            STATUS  mandatory
            DESCRIPTION
                "AU3/TU3 mapping mode setup table"
            ::= { e3Config 5 }

        e3MappingModeSetupEty  OBJECT-TYPE
            SYNTAX  E3MappingModeSetupEty
            ACCESS  not-accessible
            STATUS  mandatory
            DESCRIPTION
                "An entry in the AU3/TU3 mapping mode setup table"
            INDEX { e3MappingModeUnit }
            ::= { e3MappingModeSetupTab 1 }

        E3MappingModeSetupEty ::= SEQUENCE {
            e3MappingModeUnit           UnitID,
            e3MappingMode               INTEGER
        }

        e3MappingModeUnit  OBJECT-TYPE
            SYNTAX  UnitID
            ACCESS  read-only
            STATUS  mandatory
            DESCRIPTION
            "unit 1 to 4."
            ::= { e3MappingModeSetupEty 1 }

        e3MappingMode  OBJECT-TYPE
            SYNTAX  INTEGER{
                    au3-sts1(1),
                    au4-tug3(2)
                }
            ACCESS  read-write
            STATUS  mandatory
            DESCRIPTION
                "AU3/TU3 mapping mode"
            ::= { e3MappingModeSetupEty 2 }

--
-- E3 TPSG Protection Switch Table
--
        e3TPSGProtectSwitchTab  OBJECT-TYPE
            SYNTAX  SEQUENCE OF E3TPSGProtectSwitchEty
            ACCESS  not-accessible
            STATUS  mandatory
            DESCRIPTION
                "TPSG protection switch table"
            ::= { e3Config 6 }

        e3TPSGProtectSwitchEty  OBJECT-TYPE
            SYNTAX  E3TPSGProtectSwitchEty
            ACCESS  not-accessible
            STATUS  mandatory
            DESCRIPTION
                "An entry in the TPSG protection switch table"
            INDEX { e3TPSGProSwitchUnit ,
                    e3TPSGProSwitchPort }
            ::= { e3TPSGProtectSwitchTab 1 }

        E3TPSGProtectSwitchEty ::= SEQUENCE {
            e3TPSGProSwitchUnit         UnitID,
            e3TPSGProSwitchPort         PortID,
            e3TPSGProSwitchSide         INTEGER
        }

        e3TPSGProSwitchUnit  OBJECT-TYPE
            SYNTAX  UnitID
            ACCESS  read-only
            STATUS  mandatory
            DESCRIPTION
            "unit 1 to 4."
            ::= { e3TPSGProtectSwitchEty 1 }

        e3TPSGProSwitchPort  OBJECT-TYPE
            SYNTAX  PortID
            ACCESS  read-only
            STATUS  mandatory
            DESCRIPTION
                "E3 Port 1 to 3"
            ::= { e3TPSGProtectSwitchEty 2 }

        e3TPSGProSwitchSide  OBJECT-TYPE
            SYNTAX  INTEGER {
                    left(1),
                    right(2)
                }
            ACCESS  read-write
            STATUS  mandatory
            DESCRIPTION
                "Switch Side(left/right)"
            ::= { e3TPSGProtectSwitchEty 3 }

--
--  E3 Alarm
--

    e3Alarm           OBJECT IDENTIFIER ::= { e3-card 2 }

--
--  E3 Alarm Mask Setup Table
--

    e3AlarmMask       OBJECT IDENTIFIER ::= { e3Alarm 1 }

--
--   High Order Alarm Mask Setup
--

        e3HoSTSAlmMaskSetupTab  OBJECT-TYPE
            SYNTAX  SEQUENCE OF E3HoSTSAlmMaskSetupEty
            ACCESS  not-accessible
            STATUS  mandatory
            DESCRIPTION
                "High Order/STS Alarm mask setup table"
            ::= { e3AlarmMask 1 }

        e3HoSTSAlmMaskSetupEty  OBJECT-TYPE
            SYNTAX  E3HoSTSAlmMaskSetupEty
            ACCESS  not-accessible
            STATUS  mandatory
            DESCRIPTION
                "An entry in the alarm mask setup table"
            INDEX { e3HoSTSAlmMaskUnit ,
                    e3HoSTSAlmMaskPort }
            ::= { e3HoSTSAlmMaskSetupTab 1 }

        E3HoSTSAlmMaskSetupEty ::= SEQUENCE {
            e3HoSTSAlmMaskUnit          UnitID,
            e3HoSTSAlmMaskPort          PortID,
            e3HoSTSAlmMask-LOP          INTEGER,
            e3HoSTSAlmMask-AIS          INTEGER,
            e3HoSTSAlmMask-UNEQ         INTEGER,
            e3HoSTSAlmMask-PLM          INTEGER,
            e3HoSTSAlmMask-TIM          INTEGER,
            e3HoSTSAlmMask-RDI-P        INTEGER,
            e3HoSTSAlmMask-RDI-S        INTEGER,
            e3HoSTSAlmMask-RDI-C        INTEGER,
            e3HoSTSAlmMask-REI          INTEGER,
            e3HoSTSAlmMask-B3-BIP       INTEGER,
            e3HoSTSAlmMask-B3-LOM       INTEGER
        }

        e3HoSTSAlmMaskUnit  OBJECT-TYPE
            SYNTAX  UnitID
            ACCESS  read-only
            STATUS  mandatory
            DESCRIPTION
            "unit 1 to 4."
            ::= { e3HoSTSAlmMaskSetupEty 1 }

        e3HoSTSAlmMaskPort  OBJECT-TYPE
            SYNTAX  PortID
            ACCESS  read-only
            STATUS  mandatory
            DESCRIPTION
                "E3 Port 1 to 3"
            ::= { e3HoSTSAlmMaskSetupEty 2 }

        e3HoSTSAlmMask-LOP  OBJECT-TYPE
            SYNTAX  INTEGER{
                    disable(1),
                    enable(2)
                }
            ACCESS  read-write
            STATUS  mandatory
            DESCRIPTION
                "au-lop alarm"
            ::= { e3HoSTSAlmMaskSetupEty 3 }

        e3HoSTSAlmMask-AIS  OBJECT-TYPE
            SYNTAX  INTEGER{
                    disable(1),
                    enable(2)
                }
            ACCESS  read-write
            STATUS  mandatory
            DESCRIPTION
                "au-ais alarm"
            ::= { e3HoSTSAlmMaskSetupEty 4 }

        e3HoSTSAlmMask-UNEQ  OBJECT-TYPE
            SYNTAX  INTEGER{
                    disable(1),
                    enable(2)
                }
            ACCESS  read-write
            STATUS  mandatory
            DESCRIPTION
                "hp-uneq alarm"
            ::= { e3HoSTSAlmMaskSetupEty 5 }

        e3HoSTSAlmMask-PLM  OBJECT-TYPE
            SYNTAX  INTEGER{
                    disable(1),
                    enable(2)
                }
            ACCESS  read-write
            STATUS  mandatory
            DESCRIPTION
                "hp-plm alarm"
            ::= { e3HoSTSAlmMaskSetupEty 6 }

        e3HoSTSAlmMask-TIM  OBJECT-TYPE
            SYNTAX  INTEGER{
                    disable(1),
                    enable(2)
                }
            ACCESS  read-write
            STATUS  mandatory
            DESCRIPTION
                "hp-tim alarm"
            ::= { e3HoSTSAlmMaskSetupEty 7 }

        e3HoSTSAlmMask-RDI-P  OBJECT-TYPE
            SYNTAX  INTEGER{
                    disable(1),
                    enable(2)
                }
            ACCESS  read-write
            STATUS  mandatory
            DESCRIPTION
                "hp-rdi-p alarm"
            ::= { e3HoSTSAlmMaskSetupEty 8 }

        e3HoSTSAlmMask-RDI-S  OBJECT-TYPE
            SYNTAX  INTEGER{
                    disable(1),
                    enable(2)
                }
            ACCESS  read-write
            STATUS  mandatory
            DESCRIPTION
                "hp-rdi-s alarm"
            ::= { e3HoSTSAlmMaskSetupEty 9 }

        e3HoSTSAlmMask-RDI-C  OBJECT-TYPE
            SYNTAX  INTEGER{
                    disable(1),
                    enable(2)
                }
            ACCESS  read-write
            STATUS  mandatory
            DESCRIPTION
                "hp-rdi-c alarm"
            ::= { e3HoSTSAlmMaskSetupEty 10 }

        e3HoSTSAlmMask-REI  OBJECT-TYPE
            SYNTAX  INTEGER{
                    disable(1),
                    enable(2)
                }
            ACCESS  read-write
            STATUS  mandatory
            DESCRIPTION
                "hp-rei alarm"
            ::= { e3HoSTSAlmMaskSetupEty 11 }

        e3HoSTSAlmMask-B3-BIP  OBJECT-TYPE
            SYNTAX  INTEGER{
                    disable(1),
                    enable(2)
                }
            ACCESS  read-write
            STATUS  mandatory
            DESCRIPTION
                "hp-bip alarm"
            ::= { e3HoSTSAlmMaskSetupEty 12 }

        e3HoSTSAlmMask-B3-LOM  OBJECT-TYPE
            SYNTAX  INTEGER{
                    disable(1),
                    enable(2)
                }
            ACCESS  read-write
            STATUS  mandatory
            DESCRIPTION
                "hp-lom alarm"
            ::= { e3HoSTSAlmMaskSetupEty 13 }

--
--   Low Order Alarm Mask Setup
--

        e3LoVTAlmMaskSetupTab  OBJECT-TYPE
            SYNTAX  SEQUENCE OF E3LoVTAlmMaskSetupEty
            ACCESS  not-accessible
            STATUS  mandatory
            DESCRIPTION
                "Low Order/VT Alarm mask setup table"
            ::= { e3AlarmMask 2 }

        e3LoVTAlmMaskSetupEty  OBJECT-TYPE
            SYNTAX  E3LoVTAlmMaskSetupEty
            ACCESS  not-accessible
            STATUS  mandatory
            DESCRIPTION
                "An entry in the alarm mask setup table"
            INDEX { e3LoVTAlmMaskUnit ,
                    e3LoVTAlmMaskPort ,
                    e3LoVTAlmMaskChannel }
            ::= { e3LoVTAlmMaskSetupTab 1 }

        E3LoVTAlmMaskSetupEty ::= SEQUENCE {
            e3LoVTAlmMaskUnit           UnitID,
            e3LoVTAlmMaskPort           PortID,
            e3LoVTAlmMaskChannel        ChannelNum,
            e3LoVTAlmMask-LOP           INTEGER,
            e3LoVTAlmMask-AIS           INTEGER,
            e3LoVTAlmMask-UNEQ          INTEGER,
            e3LoVTAlmMask-PLM           INTEGER,
            e3LoVTAlmMask-TIM           INTEGER,
            e3LoVTAlmMask-RDI-P         INTEGER,
            e3LoVTAlmMask-RDI-S         INTEGER,
            e3LoVTAlmMask-RDI-C         INTEGER,
            e3LoVTAlmMask-V5-REI        INTEGER,
            e3LoVTAlmMask-V5-BIP        INTEGER
        }

        e3LoVTAlmMaskUnit  OBJECT-TYPE
            SYNTAX  UnitID
            ACCESS  read-only
            STATUS  mandatory
            DESCRIPTION
            "unit 1 to 4."
            ::= { e3LoVTAlmMaskSetupEty 1 }

        e3LoVTAlmMaskPort  OBJECT-TYPE
            SYNTAX  PortID
            ACCESS  read-only
            STATUS  mandatory
            DESCRIPTION
                "E3 Port 1 to 3"
            ::= { e3LoVTAlmMaskSetupEty 2 }

        e3LoVTAlmMaskChannel  OBJECT-TYPE
            SYNTAX  ChannelNum
            ACCESS  read-only
            STATUS  mandatory
            DESCRIPTION
                "E3 Channel 1 to 28"
            ::= { e3LoVTAlmMaskSetupEty 3 }

        e3LoVTAlmMask-LOP  OBJECT-TYPE
            SYNTAX  INTEGER{
                    disable(1),
                    enable(2)
                }
            ACCESS  read-write
            STATUS  mandatory
            DESCRIPTION
                "tu-lop alarm"
            ::= { e3LoVTAlmMaskSetupEty 4 }

        e3LoVTAlmMask-AIS  OBJECT-TYPE
            SYNTAX  INTEGER{
                    disable(1),
                    enable(2)
                }
            ACCESS  read-write
            STATUS  mandatory
            DESCRIPTION
                "tu-ais alarm"
            ::= { e3LoVTAlmMaskSetupEty 5 }

        e3LoVTAlmMask-UNEQ  OBJECT-TYPE
            SYNTAX  INTEGER{
                    disable(1),
                    enable(2)
                }
            ACCESS  read-write
            STATUS  mandatory
            DESCRIPTION
                "lp-uneq alarm"
            ::= { e3LoVTAlmMaskSetupEty 6 }

        e3LoVTAlmMask-PLM  OBJECT-TYPE
            SYNTAX  INTEGER{
                    disable(1),
                    enable(2)
                }
            ACCESS  read-write
            STATUS  mandatory
            DESCRIPTION
                "lp-plm alarm"
            ::= { e3LoVTAlmMaskSetupEty 7 }

        e3LoVTAlmMask-TIM  OBJECT-TYPE
            SYNTAX  INTEGER{
                    disable(1),
                    enable(2)
                }
            ACCESS  read-write
            STATUS  mandatory
            DESCRIPTION
                "lp-tim alarm"
            ::= { e3LoVTAlmMaskSetupEty 8 }

        e3LoVTAlmMask-RDI-P  OBJECT-TYPE
            SYNTAX  INTEGER{
                    disable(1),
                    enable(2)
                }
            ACCESS  read-write
            STATUS  mandatory
            DESCRIPTION
                "lp-rdi-p alarm"
            ::= { e3LoVTAlmMaskSetupEty 9 }

        e3LoVTAlmMask-RDI-S  OBJECT-TYPE
            SYNTAX  INTEGER{
                    disable(1),
                    enable(2)
                }
            ACCESS  read-write
            STATUS  mandatory
            DESCRIPTION
                "lp-rdi-s alarm"
            ::= { e3LoVTAlmMaskSetupEty 10 }

        e3LoVTAlmMask-RDI-C  OBJECT-TYPE
            SYNTAX  INTEGER{
                    disable(1),
                    enable(2)
                }
            ACCESS  read-write
            STATUS  mandatory
            DESCRIPTION
                "lp-rdi-c alarm"
            ::= { e3LoVTAlmMaskSetupEty 11 }

        e3LoVTAlmMask-V5-REI  OBJECT-TYPE
            SYNTAX  INTEGER{
                    disable(1),
                    enable(2)
                }
            ACCESS  read-write
            STATUS  mandatory
            DESCRIPTION
                "lp-rei alarm"
            ::= { e3LoVTAlmMaskSetupEty 12 }

        e3LoVTAlmMask-V5-BIP  OBJECT-TYPE
            SYNTAX  INTEGER{
                    disable(1),
                    enable(2)
                }
            ACCESS  read-write
            STATUS  mandatory
            DESCRIPTION
                "lp-bip alarm"
            ::= { e3LoVTAlmMaskSetupEty 13 }

--
--   Line Alarm Mask Setup
--

        e3LineAlmMaskSetupTab  OBJECT-TYPE
            SYNTAX  SEQUENCE OF E3LineAlmMaskSetupEty
            ACCESS  not-accessible
            STATUS  mandatory
            DESCRIPTION
                "Line Alarm mask setup table"
            ::= { e3AlarmMask 3 }

        e3LineAlmMaskSetupEty  OBJECT-TYPE
            SYNTAX  E3LineAlmMaskSetupEty
            ACCESS  not-accessible
            STATUS  mandatory
            DESCRIPTION
                "An entry in the alarm mask setup table"
            INDEX { e3LineAlmMaskUnit ,
                    e3LineAlmMaskPort }
            ::= { e3LineAlmMaskSetupTab 1 }

        E3LineAlmMaskSetupEty ::= SEQUENCE {
            e3LineAlmMaskUnit           UnitID,
            e3LineAlmMaskPort           PortID,
            e3LineAlmMask-LOS           INTEGER,
            e3LineAlmMask-AIS           INTEGER,
            e3LineAlmMask-UAS           INTEGER,
            e3LineAlmMask-RAI           INTEGER,
            e3LineAlmMask-LOF           INTEGER,
            e3LineAlmMask-FAS           INTEGER
        }

        e3LineAlmMaskUnit  OBJECT-TYPE
            SYNTAX  UnitID
            ACCESS  read-only
            STATUS  mandatory
            DESCRIPTION
            "unit 1 to 4."
            ::= { e3LineAlmMaskSetupEty 1 }

        e3LineAlmMaskPort  OBJECT-TYPE
            SYNTAX  PortID
            ACCESS  read-only
            STATUS  mandatory
            DESCRIPTION
                "E3 Port 1 to 3"
            ::= { e3LineAlmMaskSetupEty 2 }

        e3LineAlmMask-LOS  OBJECT-TYPE
            SYNTAX  INTEGER{
                    disable(1),
                    enable(2)
                }
            ACCESS  read-write
            STATUS  mandatory
            DESCRIPTION
                "line-los alarm"
            ::= { e3LineAlmMaskSetupEty 3 }

        e3LineAlmMask-AIS  OBJECT-TYPE
            SYNTAX  INTEGER{
                    disable(1),
                    enable(2)
                }
            ACCESS  read-write
            STATUS  mandatory
            DESCRIPTION
                "line-ais alarm"
            ::= { e3LineAlmMaskSetupEty 4 }

        e3LineAlmMask-UAS  OBJECT-TYPE
            SYNTAX  INTEGER{
                    disable(1),
                    enable(2)
                }
            ACCESS  read-write
            STATUS  mandatory
            DESCRIPTION
                "line-uas alarm"
            ::= { e3LineAlmMaskSetupEty 5 }

        e3LineAlmMask-RAI  OBJECT-TYPE
            SYNTAX  INTEGER{
                    disable(1),
                    enable(2)
                }
            ACCESS  read-write
            STATUS  mandatory
            DESCRIPTION
                "line-rai alarm"
            ::= { e3LineAlmMaskSetupEty 6 }

        e3LineAlmMask-LOF  OBJECT-TYPE
            SYNTAX  INTEGER{
                    disable(1),
                    enable(2)
                }
            ACCESS  read-write
            STATUS  mandatory
            DESCRIPTION
                "line-lof alarm"
            ::= { e3LineAlmMaskSetupEty 7 }

        e3LineAlmMask-FAS  OBJECT-TYPE
            SYNTAX  INTEGER{
                    disable(1),
                    enable(2)
                }
            ACCESS  read-write
            STATUS  mandatory
            DESCRIPTION
                "line-fas alarm"
            ::= { e3LineAlmMaskSetupEty 8 }
--
--  E3 Alarm Relay Setup Table
--

    e3AlarmRelay       OBJECT IDENTIFIER ::= { e3Alarm 2 }


--
--   High Order Alarm Relay Setup
--

        e3HoSTSAlmRelaySetupTab  OBJECT-TYPE
            SYNTAX  SEQUENCE OF E3HoSTSAlmRelaySetupEty
            ACCESS  not-accessible
            STATUS  mandatory
            DESCRIPTION
                "High Order/STS Alarm relay setup table"
            ::= { e3AlarmRelay 1 }

        e3HoSTSAlmRelaySetupEty  OBJECT-TYPE
            SYNTAX  E3HoSTSAlmRelaySetupEty
            ACCESS  not-accessible
            STATUS  mandatory
            DESCRIPTION
                "An entry in the alarm relay setup table"
            INDEX { e3HoSTSAlmRelayUnit ,
                    e3HoSTSAlmRelayPort }
            ::= { e3HoSTSAlmRelaySetupTab 1 }

        E3HoSTSAlmRelaySetupEty ::= SEQUENCE {
            e3HoSTSAlmRelayUnit         UnitID,
            e3HoSTSAlmRelayPort         PortID,
            e3HoSTSAlmRelay-LOP         INTEGER,
            e3HoSTSAlmRelay-AIS         INTEGER,
            e3HoSTSAlmRelay-UNEQ        INTEGER,
            e3HoSTSAlmRelay-PLM         INTEGER,
            e3HoSTSAlmRelay-TIM         INTEGER,
            e3HoSTSAlmRelay-RDI-P       INTEGER,
            e3HoSTSAlmRelay-RDI-S       INTEGER,
            e3HoSTSAlmRelay-RDI-C       INTEGER,
            e3HoSTSAlmRelay-REI         INTEGER,
            e3HoSTSAlmRelay-B3-BIP      INTEGER,
            e3HoSTSAlmRelay-B3-LOM      INTEGER
        }

        e3HoSTSAlmRelayUnit  OBJECT-TYPE
            SYNTAX  UnitID
            ACCESS  read-only
            STATUS  mandatory
            DESCRIPTION
            "unit 1 to 4."
            ::= { e3HoSTSAlmRelaySetupEty 1 }

        e3HoSTSAlmRelayPort  OBJECT-TYPE
            SYNTAX  PortID
            ACCESS  read-only
            STATUS  mandatory
            DESCRIPTION
                "E3 Port 1 to 3"
            ::= { e3HoSTSAlmRelaySetupEty 2 }

        e3HoSTSAlmRelay-LOP  OBJECT-TYPE
            SYNTAX  INTEGER{
                    disable(1),
                    enable(2)
                }
            ACCESS  read-write
            STATUS  mandatory
            DESCRIPTION
                "au-lop alarm"
            ::= { e3HoSTSAlmRelaySetupEty 3 }

        e3HoSTSAlmRelay-AIS  OBJECT-TYPE
            SYNTAX  INTEGER{
                    disable(1),
                    enable(2)
                }
            ACCESS  read-write
            STATUS  mandatory
            DESCRIPTION
                "au-ais alarm"
            ::= { e3HoSTSAlmRelaySetupEty 4 }

        e3HoSTSAlmRelay-UNEQ  OBJECT-TYPE
            SYNTAX  INTEGER{
                    disable(1),
                    enable(2)
                }
            ACCESS  read-write
            STATUS  mandatory
            DESCRIPTION
                "hp-uneq alarm"
            ::= { e3HoSTSAlmRelaySetupEty 5 }

        e3HoSTSAlmRelay-PLM  OBJECT-TYPE
            SYNTAX  INTEGER{
                    disable(1),
                    enable(2)
                }
            ACCESS  read-write
            STATUS  mandatory
            DESCRIPTION
                "hp-plm alarm"
            ::= { e3HoSTSAlmRelaySetupEty 6 }

        e3HoSTSAlmRelay-TIM  OBJECT-TYPE
            SYNTAX  INTEGER{
                    disable(1),
                    enable(2)
                }
            ACCESS  read-write
            STATUS  mandatory
            DESCRIPTION
                "hp-tim alarm"
            ::= { e3HoSTSAlmRelaySetupEty 7 }

        e3HoSTSAlmRelay-RDI-P  OBJECT-TYPE
            SYNTAX  INTEGER{
                    disable(1),
                    enable(2)
                }
            ACCESS  read-write
            STATUS  mandatory
            DESCRIPTION
                "hp-rdi-p alarm"
            ::= { e3HoSTSAlmRelaySetupEty 8 }

        e3HoSTSAlmRelay-RDI-S  OBJECT-TYPE
            SYNTAX  INTEGER{
                    disable(1),
                    enable(2)
                }
            ACCESS  read-write
            STATUS  mandatory
            DESCRIPTION
                "hp-rdi-s alarm"
            ::= { e3HoSTSAlmRelaySetupEty 9 }

        e3HoSTSAlmRelay-RDI-C  OBJECT-TYPE
            SYNTAX  INTEGER{
                    disable(1),
                    enable(2)
                }
            ACCESS  read-write
            STATUS  mandatory
            DESCRIPTION
                "hp-rdi-c alarm"
            ::= { e3HoSTSAlmRelaySetupEty 10 }

        e3HoSTSAlmRelay-REI  OBJECT-TYPE
            SYNTAX  INTEGER{
                    disable(1),
                    enable(2)
                }
            ACCESS  read-write
            STATUS  mandatory
            DESCRIPTION
                "hp-rei alarm"
            ::= { e3HoSTSAlmRelaySetupEty 11 }

        e3HoSTSAlmRelay-B3-BIP  OBJECT-TYPE
            SYNTAX  INTEGER{
                    disable(1),
                    enable(2)
                }
            ACCESS  read-write
            STATUS  mandatory
            DESCRIPTION
                "hp-bip alarm"
            ::= { e3HoSTSAlmRelaySetupEty 12 }

        e3HoSTSAlmRelay-B3-LOM  OBJECT-TYPE
            SYNTAX  INTEGER{
                    disable(1),
                    enable(2)
                }
            ACCESS  read-write
            STATUS  mandatory
            DESCRIPTION
                "hp-lom alarm"
            ::= { e3HoSTSAlmRelaySetupEty 13 }

--
--   Low Order Alarm Relay Setup
--

        e3LoVTAlmRelaySetupTab  OBJECT-TYPE
            SYNTAX  SEQUENCE OF E3LoVTAlmRelaySetupEty
            ACCESS  not-accessible
            STATUS  mandatory
            DESCRIPTION
                "Low Order/VT Alarm relay setup table"
            ::= { e3AlarmRelay 2 }

        e3LoVTAlmRelaySetupEty  OBJECT-TYPE
            SYNTAX  E3LoVTAlmRelaySetupEty
            ACCESS  not-accessible
            STATUS  mandatory
            DESCRIPTION
                "An entry in the alarm relay setup table"
            INDEX { e3LoVTAlmRelayUnit ,
                    e3LoVTAlmRelayPort ,
                    e3LoVTAlmRelayChannel }
            ::= { e3LoVTAlmRelaySetupTab 1 }

        E3LoVTAlmRelaySetupEty ::= SEQUENCE {
            e3LoVTAlmRelayUnit          UnitID,
            e3LoVTAlmRelayPort          PortID,
            e3LoVTAlmRelayChannel       ChannelNum,
            e3LoVTAlmRelay-LOP          INTEGER,
            e3LoVTAlmRelay-AIS          INTEGER,
            e3LoVTAlmRelay-UNEQ         INTEGER,
            e3LoVTAlmRelay-PLM          INTEGER,
            e3LoVTAlmRelay-TIM          INTEGER,
            e3LoVTAlmRelay-RDI-P        INTEGER,
            e3LoVTAlmRelay-RDI-S        INTEGER,
            e3LoVTAlmRelay-RDI-C        INTEGER,
            e3LoVTAlmRelay-V5-REI       INTEGER,
            e3LoVTAlmRelay-V5-BIP       INTEGER
        }

        e3LoVTAlmRelayUnit  OBJECT-TYPE
            SYNTAX  UnitID
            ACCESS  read-only
            STATUS  mandatory
            DESCRIPTION
            "unit 1 to 4."
            ::= { e3LoVTAlmRelaySetupEty 1 }

        e3LoVTAlmRelayPort  OBJECT-TYPE
            SYNTAX  PortID
            ACCESS  read-only
            STATUS  mandatory
            DESCRIPTION
                "E3 Port 1 to 3"
            ::= { e3LoVTAlmRelaySetupEty 2 }

        e3LoVTAlmRelayChannel  OBJECT-TYPE
            SYNTAX  ChannelNum
            ACCESS  read-only
            STATUS  mandatory
            DESCRIPTION
                "E3 Channel 1 to 28"
            ::= { e3LoVTAlmRelaySetupEty 3 }

        e3LoVTAlmRelay-LOP  OBJECT-TYPE
            SYNTAX  INTEGER{
                    disable(1),
                    enable(2)
                }
            ACCESS  read-write
            STATUS  mandatory
            DESCRIPTION
                "tu-lop alarm"
            ::= { e3LoVTAlmRelaySetupEty 4 }

        e3LoVTAlmRelay-AIS  OBJECT-TYPE
            SYNTAX  INTEGER{
                    disable(1),
                    enable(2)
                }
            ACCESS  read-write
            STATUS  mandatory
            DESCRIPTION
                "tu-ais alarm"
            ::= { e3LoVTAlmRelaySetupEty 5 }

        e3LoVTAlmRelay-UNEQ  OBJECT-TYPE
            SYNTAX  INTEGER{
                    disable(1),
                    enable(2)
                }
            ACCESS  read-write
            STATUS  mandatory
            DESCRIPTION
                "lp-uneq alarm"
            ::= { e3LoVTAlmRelaySetupEty 6 }

        e3LoVTAlmRelay-PLM  OBJECT-TYPE
            SYNTAX  INTEGER{
                    disable(1),
                    enable(2)
                }
            ACCESS  read-write
            STATUS  mandatory
            DESCRIPTION
                "lp-plm alarm"
            ::= { e3LoVTAlmRelaySetupEty 7 }

        e3LoVTAlmRelay-TIM  OBJECT-TYPE
            SYNTAX  INTEGER{
                    disable(1),
                    enable(2)
                }
            ACCESS  read-write
            STATUS  mandatory
            DESCRIPTION
                "lp-tim alarm"
            ::= { e3LoVTAlmRelaySetupEty 8 }

        e3LoVTAlmRelay-RDI-P  OBJECT-TYPE
            SYNTAX  INTEGER{
                    disable(1),
                    enable(2)
                }
            ACCESS  read-write
            STATUS  mandatory
            DESCRIPTION
                "lp-rdi-p alarm"
            ::= { e3LoVTAlmRelaySetupEty 9 }

        e3LoVTAlmRelay-RDI-S  OBJECT-TYPE
            SYNTAX  INTEGER{
                    disable(1),
                    enable(2)
                }
            ACCESS  read-write
            STATUS  mandatory
            DESCRIPTION
                "lp-rdi-s alarm"
            ::= { e3LoVTAlmRelaySetupEty 10 }

        e3LoVTAlmRelay-RDI-C  OBJECT-TYPE
            SYNTAX  INTEGER{
                    disable(1),
                    enable(2)
                }
            ACCESS  read-write
            STATUS  mandatory
            DESCRIPTION
                "lp-rdi-c alarm"
            ::= { e3LoVTAlmRelaySetupEty 11 }

        e3LoVTAlmRelay-V5-REI  OBJECT-TYPE
            SYNTAX  INTEGER{
                    disable(1),
                    enable(2)
                }
            ACCESS  read-write
            STATUS  mandatory
            DESCRIPTION
                "lp-rei alarm"
            ::= { e3LoVTAlmRelaySetupEty 12 }

        e3LoVTAlmRelay-V5-BIP  OBJECT-TYPE
            SYNTAX  INTEGER{
                    disable(1),
                    enable(2)
                }
            ACCESS  read-write
            STATUS  mandatory
            DESCRIPTION
                "lp-bip alarm"
            ::= { e3LoVTAlmRelaySetupEty 13 }

--
--   Line Alarm Relay Setup
--

        e3LineAlmRelaySetupTab  OBJECT-TYPE
            SYNTAX  SEQUENCE OF E3LineAlmRelaySetupEty
            ACCESS  not-accessible
            STATUS  mandatory
            DESCRIPTION
                "Line Alarm relay setup table"
            ::= { e3AlarmRelay 3 }

        e3LineAlmRelaySetupEty  OBJECT-TYPE
            SYNTAX  E3LineAlmRelaySetupEty
            ACCESS  not-accessible
            STATUS  mandatory
            DESCRIPTION
                "An entry in the alarm relay setup table"
            INDEX { e3LineAlmRelayUnit ,
                    e3LineAlmRelayPort }
            ::= { e3LineAlmRelaySetupTab 1 }

        E3LineAlmRelaySetupEty ::= SEQUENCE {
            e3LineAlmRelayUnit          UnitID,
            e3LineAlmRelayPort          PortID,
            e3LineAlmRelay-LOS          INTEGER,
            e3LineAlmRelay-AIS          INTEGER,
            e3LineAlmRelay-UAS          INTEGER,
            e3LineAlmRelay-RAI          INTEGER,
            e3LineAlmRelay-LOF          INTEGER,
            e3LineAlmRelay-FAS          INTEGER
        }

        e3LineAlmRelayUnit  OBJECT-TYPE
            SYNTAX  UnitID
            ACCESS  read-only
            STATUS  mandatory
            DESCRIPTION
            "unit 1 to 4."
            ::= { e3LineAlmRelaySetupEty 1 }

        e3LineAlmRelayPort  OBJECT-TYPE
            SYNTAX  PortID
            ACCESS  read-only
            STATUS  mandatory
            DESCRIPTION
                "E3 Port 1 to 3"
            ::= { e3LineAlmRelaySetupEty 2 }

        e3LineAlmRelay-LOS  OBJECT-TYPE
            SYNTAX  INTEGER{
                    disable(1),
                    enable(2)
                }
            ACCESS  read-write
            STATUS  mandatory
            DESCRIPTION
                "line-los alarm"
            ::= { e3LineAlmRelaySetupEty 3 }

        e3LineAlmRelay-AIS  OBJECT-TYPE
            SYNTAX  INTEGER{
                    disable(1),
                    enable(2)
                }
            ACCESS  read-write
            STATUS  mandatory
            DESCRIPTION
                "line-ais alarm"
            ::= { e3LineAlmRelaySetupEty 4 }

        e3LineAlmRelay-UAS  OBJECT-TYPE
            SYNTAX  INTEGER{
                    disable(1),
                    enable(2)
                }
            ACCESS  read-write
            STATUS  mandatory
            DESCRIPTION
                "line-uas alarm"
            ::= { e3LineAlmRelaySetupEty 5 }

        e3LineAlmRelay-RAI  OBJECT-TYPE
            SYNTAX  INTEGER{
                    disable(1),
                    enable(2)
                }
            ACCESS  read-write
            STATUS  mandatory
            DESCRIPTION
                "line-rai alarm"
            ::= { e3LineAlmRelaySetupEty 6 }

        e3LineAlmRelay-LOF  OBJECT-TYPE
            SYNTAX  INTEGER{
                    disable(1),
                    enable(2)
                }
            ACCESS  read-write
            STATUS  mandatory
            DESCRIPTION
                "line-lof alarm"
            ::= { e3LineAlmRelaySetupEty 7 }

        e3LineAlmRelay-FAS  OBJECT-TYPE
            SYNTAX  INTEGER{
                    disable(1),
                    enable(2)
                }
            ACCESS  read-write
            STATUS  mandatory
            DESCRIPTION
                "line-fas alarm"
            ::= { e3LineAlmRelaySetupEty 8 }

--
--  E3 Alarm Severity Setup Table
--

        e3AlmSeveritySetupTab  OBJECT-TYPE
            SYNTAX  SEQUENCE OF E3AlmSeveritySetupEty
            ACCESS  not-accessible
            STATUS  mandatory
            DESCRIPTION
                "Alarm severity setup table"
            ::= { e3Alarm 3 }

        e3AlmSeveritySetupEty  OBJECT-TYPE
            SYNTAX  E3AlmSeveritySetupEty
            ACCESS  not-accessible
            STATUS  mandatory
            DESCRIPTION
                "An entry in the alarm severity setup table"
            INDEX { e3AlmSvrityUnit }
            ::= { e3AlmSeveritySetupTab 1 }

        E3AlmSeveritySetupEty ::= SEQUENCE {
            e3AlmSvrityUnit             UnitID,
            e3AlmSvrityHoSTS-LOP        Severity,
            e3AlmSvrityHoSTS-AIS        Severity,
            e3AlmSvrityHoSTS-UNEQ       Severity,
            e3AlmSvrityHoSTS-PLM        Severity,
            e3AlmSvrityHoSTS-TIM        Severity,
            e3AlmSvrityHoSTS-RDI-P      Severity,
            e3AlmSvrityHoSTS-RDI-S      Severity,
            e3AlmSvrityHoSTS-RDI-C      Severity,
            e3AlmSvrityHoSTS-B3-REI     Severity,
            e3AlmSvrityHoSTS-B3-BIP     Severity,
            e3AlmSvrityHoSTS-LOM        Severity,
            e3AlmSvrityLoVT-LOP         Severity,
            e3AlmSvrityLoVT-AIS         Severity,
            e3AlmSvrityLoVT-UNEQ        Severity,
            e3AlmSvrityLoVT-PLM         Severity,
            e3AlmSvrityLoVT-TIM         Severity,
            e3AlmSvrityLoVT-RDI-P       Severity,
            e3AlmSvrityLoVT-RDI-S       Severity,
            e3AlmSvrityLoVT-RDI-C       Severity,
            e3AlmSvrityLoVT-V5-REI      Severity,
            e3AlmSvrityLoVT-V5-BIP      Severity,
            e3AlmSvrityLine-LOS         Severity,
            e3AlmSvrityLine-AIS         Severity,
            e3AlmSvrityLine-UAS         Severity,
            e3AlmSvrityLine-RAI         Severity,
            e3AlmSvrityLine-LOF         Severity,
            e3AlmSvrityLine-FAS         Severity
        }

        e3AlmSvrityUnit  OBJECT-TYPE
            SYNTAX  UnitID
            ACCESS  read-only
            STATUS  mandatory
            DESCRIPTION
            "unit 1 to 4."
            ::= { e3AlmSeveritySetupEty 1 }

        e3AlmSvrityHoSTS-LOP  OBJECT-TYPE
            SYNTAX  Severity
            ACCESS  read-write
            STATUS  mandatory
            DESCRIPTION
                "au-lop alarm severity type"
            ::= { e3AlmSeveritySetupEty 2 }

        e3AlmSvrityHoSTS-AIS  OBJECT-TYPE
            SYNTAX  Severity
            ACCESS  read-write
            STATUS  mandatory
            DESCRIPTION
                "au-ais alarm severity type"
            ::= { e3AlmSeveritySetupEty 3 }

        e3AlmSvrityHoSTS-UNEQ  OBJECT-TYPE
            SYNTAX  Severity
            ACCESS  read-write
            STATUS  mandatory
            DESCRIPTION
                "hp-uneq alarm severity type"
            ::= { e3AlmSeveritySetupEty 4 }

        e3AlmSvrityHoSTS-PLM  OBJECT-TYPE
            SYNTAX  Severity
            ACCESS  read-write
            STATUS  mandatory
            DESCRIPTION
                "hp-plm alarm severity type"
            ::= { e3AlmSeveritySetupEty 5 }

        e3AlmSvrityHoSTS-TIM  OBJECT-TYPE
            SYNTAX  Severity
            ACCESS  read-write
            STATUS  mandatory
            DESCRIPTION
                "hp-tim alarm severity type"
            ::= { e3AlmSeveritySetupEty 6 }

        e3AlmSvrityHoSTS-RDI-P  OBJECT-TYPE
            SYNTAX  Severity
            ACCESS  read-write
            STATUS  mandatory
            DESCRIPTION
                "hp-rdi-p alarm severity type"
            ::= { e3AlmSeveritySetupEty 7 }

        e3AlmSvrityHoSTS-RDI-S  OBJECT-TYPE
            SYNTAX  Severity
            ACCESS  read-write
            STATUS  mandatory
            DESCRIPTION
                "hp-rdi-s alarm severity type"
            ::= { e3AlmSeveritySetupEty 8 }

        e3AlmSvrityHoSTS-RDI-C  OBJECT-TYPE
            SYNTAX  Severity
            ACCESS  read-write
            STATUS  mandatory
            DESCRIPTION
                "hp-rdi-c alarm severity type"
            ::= { e3AlmSeveritySetupEty 9 }

        e3AlmSvrityHoSTS-B3-REI  OBJECT-TYPE
            SYNTAX  Severity
            ACCESS  read-write
            STATUS  mandatory
            DESCRIPTION
                "hp-rei alarm severity type"
            ::= { e3AlmSeveritySetupEty 10 }

        e3AlmSvrityHoSTS-B3-BIP  OBJECT-TYPE
            SYNTAX  Severity
            ACCESS  read-write
            STATUS  mandatory
            DESCRIPTION
                "hp-bip alarm severity type"
            ::= { e3AlmSeveritySetupEty 11 }

        e3AlmSvrityHoSTS-LOM  OBJECT-TYPE
            SYNTAX  Severity
            ACCESS  read-write
            STATUS  mandatory
            DESCRIPTION
                "hp-lom alarm severity type"
            ::= { e3AlmSeveritySetupEty 12 }

        e3AlmSvrityLoVT-LOP  OBJECT-TYPE
            SYNTAX  Severity
            ACCESS  read-write
            STATUS  mandatory
            DESCRIPTION
                "tu-lop alarm severity type"
            ::= { e3AlmSeveritySetupEty 13 }

        e3AlmSvrityLoVT-AIS  OBJECT-TYPE
            SYNTAX  Severity
            ACCESS  read-write
            STATUS  mandatory
            DESCRIPTION
                "tu-ais alarm severity type"
            ::= { e3AlmSeveritySetupEty 14 }

        e3AlmSvrityLoVT-UNEQ  OBJECT-TYPE
            SYNTAX  Severity
            ACCESS  read-write
            STATUS  mandatory
            DESCRIPTION
                "lp-uneq alarm severity type"
            ::= { e3AlmSeveritySetupEty 15 }

        e3AlmSvrityLoVT-PLM  OBJECT-TYPE
            SYNTAX  Severity
            ACCESS  read-write
            STATUS  mandatory
            DESCRIPTION
                "lp-plm alarm severity type"
            ::= { e3AlmSeveritySetupEty 16 }

        e3AlmSvrityLoVT-TIM  OBJECT-TYPE
            SYNTAX  Severity
            ACCESS  read-write
            STATUS  mandatory
            DESCRIPTION
                "lp-tim alarm severity type"
            ::= { e3AlmSeveritySetupEty 17 }

        e3AlmSvrityLoVT-RDI-P  OBJECT-TYPE
            SYNTAX  Severity
            ACCESS  read-write
            STATUS  mandatory
            DESCRIPTION
                "lp-rdi-p alarm severity type"
            ::= { e3AlmSeveritySetupEty 18 }

        e3AlmSvrityLoVT-RDI-S  OBJECT-TYPE
            SYNTAX  Severity
            ACCESS  read-write
            STATUS  mandatory
            DESCRIPTION
                "lp-rdi-s alarm severity type"
            ::= { e3AlmSeveritySetupEty 19 }

        e3AlmSvrityLoVT-RDI-C  OBJECT-TYPE
            SYNTAX  Severity
            ACCESS  read-write
            STATUS  mandatory
            DESCRIPTION
                "lp-rdi-c alarm severity type"
            ::= { e3AlmSeveritySetupEty 20 }

        e3AlmSvrityLoVT-V5-REI  OBJECT-TYPE
            SYNTAX  Severity
            ACCESS  read-write
            STATUS  mandatory
            DESCRIPTION
                "lp-rei alarm severity type"
            ::= { e3AlmSeveritySetupEty 21 }

        e3AlmSvrityLoVT-V5-BIP  OBJECT-TYPE
            SYNTAX  Severity
            ACCESS  read-write
            STATUS  mandatory
            DESCRIPTION
                "lp-bip alarm severity type"
            ::= { e3AlmSeveritySetupEty 22 }

        e3AlmSvrityLine-LOS  OBJECT-TYPE
            SYNTAX  Severity
            ACCESS  read-write
            STATUS  mandatory
            DESCRIPTION
                "line-los alarm severity type"
            ::= { e3AlmSeveritySetupEty 23 }

        e3AlmSvrityLine-AIS  OBJECT-TYPE
            SYNTAX  Severity
            ACCESS  read-write
            STATUS  mandatory
            DESCRIPTION
                "line-ais alarm severity type"
            ::= { e3AlmSeveritySetupEty 24 }

        e3AlmSvrityLine-UAS  OBJECT-TYPE
            SYNTAX  Severity
            ACCESS  read-write
            STATUS  mandatory
            DESCRIPTION
                "line-uas alarm severity type"
            ::= { e3AlmSeveritySetupEty 25 }

        e3AlmSvrityLine-RAI  OBJECT-TYPE
            SYNTAX  Severity
            ACCESS  read-write
            STATUS  mandatory
            DESCRIPTION
                "line-rai alarm severity type"
            ::= { e3AlmSeveritySetupEty 26 }

        e3AlmSvrityLine-LOF  OBJECT-TYPE
            SYNTAX  Severity
            ACCESS  read-write
            STATUS  mandatory
            DESCRIPTION
                "line-lof alarm severity type"
            ::= { e3AlmSeveritySetupEty 27 }

        e3AlmSvrityLine-FAS  OBJECT-TYPE
            SYNTAX  Severity
            ACCESS  read-write
            STATUS  mandatory
            DESCRIPTION
                "line-fas alarm severity type"
            ::= { e3AlmSeveritySetupEty 28 }

--
--  E3 Insert AIS Alarm Setup Table
--

        e3InsertAisAlmSetupTab  OBJECT-TYPE
            SYNTAX  SEQUENCE OF E3InsertAisAlmSetupEty
            ACCESS  not-accessible
            STATUS  mandatory
            DESCRIPTION
                "Insert AIS alarm setup table"
            ::= { e3Alarm 4 }

        e3InsertAisAlmSetupEty  OBJECT-TYPE
            SYNTAX  E3InsertAisAlmSetupEty
            ACCESS  not-accessible
            STATUS  mandatory
            DESCRIPTION
                "An entry in the insert AIS alarm setup table"
            INDEX { e3InstUnit }
            ::= { e3InsertAisAlmSetupTab 1 }

        E3InsertAisAlmSetupEty ::= SEQUENCE {
            e3InstUnit                  UnitID,
            e3InstAuLop-LopPToAis       INTEGER,
            e3InstAuAis-AisPToAis       INTEGER,
            e3InstHpUneq-UneqPToAis     INTEGER,
            e3InstHpTim-TimPToAis       INTEGER,
            e3InstHpLom-LomToAis        INTEGER,
            e3InstHpPlm-PlmPToAis       INTEGER,
            e3InstTuAis-AisVToAis       INTEGER,
            e3InstTuLop-LopVToAis       INTEGER,
            e3InstLpUneq-UneqVToAis     INTEGER,
            e3InstLpTim-TimVToAis       INTEGER,
            e3InstLpPlm-PlmVToAis       INTEGER
        }

        e3InstUnit  OBJECT-TYPE
            SYNTAX  UnitID
            ACCESS  read-only
            STATUS  mandatory
            DESCRIPTION
            "unit 1 to 4."
            ::= { e3InsertAisAlmSetupEty 1 }

        e3InstAuLop-LopPToAis OBJECT-TYPE
            SYNTAX  INTEGER {
                    disable(1),
                    enable(2)
                }
            ACCESS  read-write
            STATUS  mandatory
            DESCRIPTION
                "au-lop to ais"
            ::= { e3InsertAisAlmSetupEty 2 }

        e3InstAuAis-AisPToAis OBJECT-TYPE
            SYNTAX  INTEGER {
                    disable(1),
                    enable(2)
                }
            ACCESS  read-write
            STATUS  mandatory
            DESCRIPTION
                "au-ais to ais"
            ::= { e3InsertAisAlmSetupEty 3 }

        e3InstHpUneq-UneqPToAis OBJECT-TYPE
            SYNTAX  INTEGER {
                    disable(1),
                    enable(2)
                }
            ACCESS  read-write
            STATUS  mandatory
            DESCRIPTION
                "hp-uneq to ais"
            ::= { e3InsertAisAlmSetupEty 4 }

        e3InstHpTim-TimPToAis OBJECT-TYPE
            SYNTAX  INTEGER {
                    disable(1),
                    enable(2)
                }
            ACCESS  read-write
            STATUS  mandatory
            DESCRIPTION
                "hp-tim to ais"
            ::= { e3InsertAisAlmSetupEty 5 }

        e3InstHpLom-LomToAis OBJECT-TYPE
            SYNTAX  INTEGER {
                    disable(1),
                    enable(2)
                }
            ACCESS  read-write
            STATUS  mandatory
            DESCRIPTION
                "hp-lom to ais"
            ::= { e3InsertAisAlmSetupEty 6 }

        e3InstHpPlm-PlmPToAis OBJECT-TYPE
            SYNTAX  INTEGER {
                    disable(1),
                    enable(2)
                }
            ACCESS  read-write
            STATUS  mandatory
            DESCRIPTION
                "hp-plm to ais"
            ::= { e3InsertAisAlmSetupEty 7 }

        e3InstTuAis-AisVToAis OBJECT-TYPE
            SYNTAX  INTEGER {
                    disable(1),
                    enable(2)
                }
            ACCESS  read-write
            STATUS  mandatory
            DESCRIPTION
                "tu-ais to ais"
            ::= { e3InsertAisAlmSetupEty 8 }

        e3InstTuLop-LopVToAis OBJECT-TYPE
            SYNTAX  INTEGER {
                    disable(1),
                    enable(2)
                }
            ACCESS  read-write
            STATUS  mandatory
            DESCRIPTION
                "tu-lop to ais"
            ::= { e3InsertAisAlmSetupEty 9 }

        e3InstLpUneq-UneqVToAis OBJECT-TYPE
            SYNTAX  INTEGER {
                    disable(1),
                    enable(2)
                }
            ACCESS  read-write
            STATUS  mandatory
            DESCRIPTION
                "lp-uneq to ais"
            ::= { e3InsertAisAlmSetupEty 10 }

        e3InstLpTim-TimVToAis OBJECT-TYPE
            SYNTAX  INTEGER {
                    disable(1),
                    enable(2)
                }
            ACCESS  read-write
            STATUS  mandatory
            DESCRIPTION
                "lp-tim to ais"
            ::= { e3InsertAisAlmSetupEty 11 }

        e3InstLpPlm-PlmVToAis OBJECT-TYPE
            SYNTAX  INTEGER {
                    disable(1),
                    enable(2)
                }
            ACCESS  read-write
            STATUS  mandatory
            DESCRIPTION
                "lp-plm to ais"
            ::= { e3InsertAisAlmSetupEty 12 }

--
--  E3 Current Alarm Status Table
--

    e3CurrAlmStatus       OBJECT IDENTIFIER ::= { e3Alarm 5 }

--
--   High Order Current Alarm Status
--

        e3HoSTSCurAlmStatusTab  OBJECT-TYPE
            SYNTAX  SEQUENCE OF E3HoSTSCurAlmStatusEty
            ACCESS  not-accessible
            STATUS  mandatory
            DESCRIPTION
                "High Order/STS current alarm status table"
            ::= { e3CurrAlmStatus 1 }

        e3HoSTSCurAlmStatusEty  OBJECT-TYPE
            SYNTAX  E3HoSTSCurAlmStatusEty
            ACCESS  not-accessible
            STATUS  mandatory
            DESCRIPTION
                "An entry in the alarm mask setup table"
            INDEX { e3HoSTSCurAlmUnit ,
                    e3HoSTSCurAlmPort }
            ::= { e3HoSTSCurAlmStatusTab 1 }

        E3HoSTSCurAlmStatusEty ::= SEQUENCE {
            e3HoSTSCurAlmUnit           UnitID,
            e3HoSTSCurAlmPort           PortID,
            e3HoSTSCurAlm-LOP           AlmStatus,
            e3HoSTSCurAlm-AIS           AlmStatus,
            e3HoSTSCurAlm-UNEQ          AlmStatus,
            e3HoSTSCurAlm-PLM           AlmStatus,
            e3HoSTSCurAlm-TIM           AlmStatus,
            e3HoSTSCurAlm-RDI-P         AlmStatus,
            e3HoSTSCurAlm-RDI-S         AlmStatus,
            e3HoSTSCurAlm-RDI-C         AlmStatus,
            e3HoSTSCurAlm-REI           AlmStatus,
            e3HoSTSCurAlm-B3-BIP        AlmStatus,
            e3HoSTSCurAlm-B3-LOM        AlmStatus
        }

        e3HoSTSCurAlmUnit  OBJECT-TYPE
            SYNTAX  UnitID
            ACCESS  read-only
            STATUS  mandatory
            DESCRIPTION
            "unit 1 to 4."
            ::= { e3HoSTSCurAlmStatusEty 1 }

        e3HoSTSCurAlmPort  OBJECT-TYPE
            SYNTAX  PortID
            ACCESS  read-only
            STATUS  mandatory
            DESCRIPTION
                "E3 Port 1 to 3"
            ::= { e3HoSTSCurAlmStatusEty 2 }

        e3HoSTSCurAlm-LOP  OBJECT-TYPE
            SYNTAX  AlmStatus
            ACCESS  read-only
            STATUS  mandatory
            DESCRIPTION
                "au-lop alarm status"
            ::= { e3HoSTSCurAlmStatusEty 3 }

        e3HoSTSCurAlm-AIS  OBJECT-TYPE
            SYNTAX  AlmStatus
            ACCESS  read-only
            STATUS  mandatory
            DESCRIPTION
                "au-ais alarm status"
            ::= { e3HoSTSCurAlmStatusEty 4 }

        e3HoSTSCurAlm-UNEQ  OBJECT-TYPE
            SYNTAX  AlmStatus
            ACCESS  read-only
            STATUS  mandatory
            DESCRIPTION
                "hp-uneq alarm status"
            ::= { e3HoSTSCurAlmStatusEty 5 }

        e3HoSTSCurAlm-PLM  OBJECT-TYPE
            SYNTAX  AlmStatus
            ACCESS  read-only
            STATUS  mandatory
            DESCRIPTION
                "hp-plm alarm status"
            ::= { e3HoSTSCurAlmStatusEty 6 }

        e3HoSTSCurAlm-TIM  OBJECT-TYPE
            SYNTAX  AlmStatus
            ACCESS  read-only
            STATUS  mandatory
            DESCRIPTION
                "hp-tim alarm status"
            ::= { e3HoSTSCurAlmStatusEty 7 }

        e3HoSTSCurAlm-RDI-P  OBJECT-TYPE
            SYNTAX  AlmStatus
            ACCESS  read-only
            STATUS  mandatory
            DESCRIPTION
                "hp-rdi-p alarm status"
            ::= { e3HoSTSCurAlmStatusEty 8 }

        e3HoSTSCurAlm-RDI-S  OBJECT-TYPE
            SYNTAX  AlmStatus
            ACCESS  read-only
            STATUS  mandatory
            DESCRIPTION
                "hp-rdi-s alarm status"
            ::= { e3HoSTSCurAlmStatusEty 9 }

        e3HoSTSCurAlm-RDI-C  OBJECT-TYPE
            SYNTAX  AlmStatus
            ACCESS  read-only
            STATUS  mandatory
            DESCRIPTION
                "hp-rdi-c alarm status"
            ::= { e3HoSTSCurAlmStatusEty 10 }

        e3HoSTSCurAlm-REI  OBJECT-TYPE
            SYNTAX  AlmStatus
            ACCESS  read-only
            STATUS  mandatory
            DESCRIPTION
                "hp-rei alarm status"
            ::= { e3HoSTSCurAlmStatusEty 11 }

        e3HoSTSCurAlm-B3-BIP  OBJECT-TYPE
            SYNTAX  AlmStatus
            ACCESS  read-only
            STATUS  mandatory
            DESCRIPTION
                "hp-bip alarm status"
            ::= { e3HoSTSCurAlmStatusEty 12 }

        e3HoSTSCurAlm-B3-LOM  OBJECT-TYPE
            SYNTAX  AlmStatus
            ACCESS  read-only
            STATUS  mandatory
            DESCRIPTION
                "hp-lom alarm status"
            ::= { e3HoSTSCurAlmStatusEty 13 }

--
--   Low Order Current Alarm Status
--

        e3LoVTCurAlmStatusTab  OBJECT-TYPE
            SYNTAX  SEQUENCE OF E3LoVTCurAlmStatusEty
            ACCESS  not-accessible
            STATUS  mandatory
            DESCRIPTION
                "Low Order/VT Alarm mask setup table"
            ::= { e3CurrAlmStatus 2 }

        e3LoVTCurAlmStatusEty  OBJECT-TYPE
            SYNTAX  E3LoVTCurAlmStatusEty
            ACCESS  not-accessible
            STATUS  mandatory
            DESCRIPTION
                "An entry in the alarm mask setup table"
            INDEX { e3LoVTCurAlmUnit ,
                    e3LoVTCurAlmPort ,
                    e3LoVTCurAlmChannel }
            ::= { e3LoVTCurAlmStatusTab 1 }

        E3LoVTCurAlmStatusEty ::= SEQUENCE {
            e3LoVTCurAlmUnit            UnitID,
            e3LoVTCurAlmPort            PortID,
            e3LoVTCurAlmChannel         ChannelNum,
            e3LoVTCurAlm-LOP            AlmStatus,
            e3LoVTCurAlm-AIS            AlmStatus,
            e3LoVTCurAlm-UNEQ           AlmStatus,
            e3LoVTCurAlm-PLM            AlmStatus,
            e3LoVTCurAlm-TIM            AlmStatus,
            e3LoVTCurAlm-RDI-P          AlmStatus,
            e3LoVTCurAlm-RDI-S          AlmStatus,
            e3LoVTCurAlm-RDI-C          AlmStatus,
            e3LoVTCurAlm-V5-REI         AlmStatus,
            e3LoVTCurAlm-V5-BIP         AlmStatus
        }

        e3LoVTCurAlmUnit  OBJECT-TYPE
            SYNTAX  UnitID
            ACCESS  read-only
            STATUS  mandatory
            DESCRIPTION
            "unit 1 to 4."
            ::= { e3LoVTCurAlmStatusEty 1 }

        e3LoVTCurAlmPort  OBJECT-TYPE
            SYNTAX  PortID
            ACCESS  read-only
            STATUS  mandatory
            DESCRIPTION
                "E3 Port 1 to 3"
            ::= { e3LoVTCurAlmStatusEty 2 }

        e3LoVTCurAlmChannel  OBJECT-TYPE
            SYNTAX  ChannelNum
            ACCESS  read-only
            STATUS  mandatory
            DESCRIPTION
                "E3 Channel 1 to 28"
            ::= { e3LoVTCurAlmStatusEty 3 }

        e3LoVTCurAlm-LOP  OBJECT-TYPE
            SYNTAX  AlmStatus
            ACCESS  read-only
            STATUS  mandatory
            DESCRIPTION
                "tu-lop alarm status"
            ::= { e3LoVTCurAlmStatusEty 4 }

        e3LoVTCurAlm-AIS  OBJECT-TYPE
            SYNTAX  AlmStatus
            ACCESS  read-only
            STATUS  mandatory
            DESCRIPTION
                "tu-ais alarm status"
            ::= { e3LoVTCurAlmStatusEty 5 }

        e3LoVTCurAlm-UNEQ  OBJECT-TYPE
            SYNTAX  AlmStatus
            ACCESS  read-only
            STATUS  mandatory
            DESCRIPTION
                "lp-uneq alarm status"
            ::= { e3LoVTCurAlmStatusEty 6 }

        e3LoVTCurAlm-PLM  OBJECT-TYPE
            SYNTAX  AlmStatus
            ACCESS  read-only
            STATUS  mandatory
            DESCRIPTION
                "lp-plm alarm status"
            ::= { e3LoVTCurAlmStatusEty 7 }

        e3LoVTCurAlm-TIM  OBJECT-TYPE
            SYNTAX  AlmStatus
            ACCESS  read-only
            STATUS  mandatory
            DESCRIPTION
                "lp-tim alarm status"
            ::= { e3LoVTCurAlmStatusEty 8 }

        e3LoVTCurAlm-RDI-P  OBJECT-TYPE
            SYNTAX  AlmStatus
            ACCESS  read-only
            STATUS  mandatory
            DESCRIPTION
                "lp-rdi-p alarm status"
            ::= { e3LoVTCurAlmStatusEty 9 }

        e3LoVTCurAlm-RDI-S  OBJECT-TYPE
            SYNTAX  AlmStatus
            ACCESS  read-only
            STATUS  mandatory
            DESCRIPTION
                "lp-rdi-s alarm status"
            ::= { e3LoVTCurAlmStatusEty 10 }

        e3LoVTCurAlm-RDI-C  OBJECT-TYPE
            SYNTAX  AlmStatus
            ACCESS  read-only
            STATUS  mandatory
            DESCRIPTION
                "lp-rdi-c alarm status"
            ::= { e3LoVTCurAlmStatusEty 11 }

        e3LoVTCurAlm-V5-REI  OBJECT-TYPE
            SYNTAX  AlmStatus
            ACCESS  read-only
            STATUS  mandatory
            DESCRIPTION
                "lp-rei alarm status"
            ::= { e3LoVTCurAlmStatusEty 12 }

        e3LoVTCurAlm-V5-BIP  OBJECT-TYPE
            SYNTAX  AlmStatus
            ACCESS  read-only
            STATUS  mandatory
            DESCRIPTION
                "lp-bip alarm status"
            ::= { e3LoVTCurAlmStatusEty 13 }

--
--   Line Alarm Current Alarm Status
--

        e3LineCurAlmStatusTab  OBJECT-TYPE
            SYNTAX  SEQUENCE OF E3LineCurAlmStatusEty
            ACCESS  not-accessible
            STATUS  mandatory
            DESCRIPTION
                "Line Alarm mask setup table"
            ::= { e3CurrAlmStatus 3 }

        e3LineCurAlmStatusEty  OBJECT-TYPE
            SYNTAX  E3LineCurAlmStatusEty
            ACCESS  not-accessible
            STATUS  mandatory
            DESCRIPTION
                "An entry in the alarm mask setup table"
            INDEX { e3LineCurAlmUnit ,
                    e3LineCurAlmPort }
            ::= { e3LineCurAlmStatusTab 1 }

        E3LineCurAlmStatusEty ::= SEQUENCE {
            e3LineCurAlmUnit            UnitID,
            e3LineCurAlmPort            PortID,
            e3LineCurAlm-LOS            AlmStatus,
            e3LineCurAlm-AIS            AlmStatus,
            e3LineCurAlm-UAS            AlmStatus,
            e3LineCurAlm-RAI            AlmStatus,
            e3LineCurAlm-LOF            AlmStatus,
            e3LineCurAlm-FAS            AlmStatus
        }

        e3LineCurAlmUnit  OBJECT-TYPE
            SYNTAX  UnitID
            ACCESS  read-only
            STATUS  mandatory
            DESCRIPTION
            "unit 1 to 4."
            ::= { e3LineCurAlmStatusEty 1 }

        e3LineCurAlmPort  OBJECT-TYPE
            SYNTAX  PortID
            ACCESS  read-only
            STATUS  mandatory
            DESCRIPTION
                "E3 Port 1 to 3"
            ::= { e3LineCurAlmStatusEty 2 }

        e3LineCurAlm-LOS  OBJECT-TYPE
            SYNTAX  AlmStatus
            ACCESS  read-only
            STATUS  mandatory
            DESCRIPTION
                "line-los alarm status"
            ::= { e3LineCurAlmStatusEty 3 }

        e3LineCurAlm-AIS  OBJECT-TYPE
            SYNTAX  AlmStatus
            ACCESS  read-only
            STATUS  mandatory
            DESCRIPTION
                "line-ais alarm status"
            ::= { e3LineCurAlmStatusEty 4 }

        e3LineCurAlm-UAS  OBJECT-TYPE
            SYNTAX  AlmStatus
            ACCESS  read-only
            STATUS  mandatory
            DESCRIPTION
                "line-uas alarm status"
            ::= { e3LineCurAlmStatusEty 5 }

        e3LineCurAlm-RAI  OBJECT-TYPE
            SYNTAX  AlmStatus
            ACCESS  read-only
            STATUS  mandatory
            DESCRIPTION
                "line-rai alarm status"
            ::= { e3LineCurAlmStatusEty 6 }

        e3LineCurAlm-LOF  OBJECT-TYPE
            SYNTAX  AlmStatus
            ACCESS  read-only
            STATUS  mandatory
            DESCRIPTION
                "line-lof alarm status"
            ::= { e3LineCurAlmStatusEty 7 }

        e3LineCurAlm-FAS  OBJECT-TYPE
            SYNTAX  AlmStatus
            ACCESS  read-only
            STATUS  mandatory
            DESCRIPTION
                "line-fas alarm status"
            ::= { e3LineCurAlmStatusEty 8 }

--
--  E3 Current Active Alarm Summary Table
--
        e3CurrActAlmSummaryTab  OBJECT-TYPE
            SYNTAX  SEQUENCE OF E3CurrActAlmSummaryEty
            ACCESS  not-accessible
            STATUS  mandatory
            DESCRIPTION
                "E3 Current Active Alarm Summary Table."
            ::= { e3Alarm 6 }

        e3CurrActAlmSummaryEty  OBJECT-TYPE
            SYNTAX  E3CurrActAlmSummaryEty
            ACCESS  not-accessible
            STATUS  mandatory
            DESCRIPTION
                "e3 current active alarm summary entry"
            INDEX { e3AlmSumUnit ,
                    e3AlmSumIndex }
            ::= { e3CurrActAlmSummaryTab 1 }

        E3CurrActAlmSummaryEty ::= SEQUENCE {
            e3AlmSumUnit                UnitID,
            e3AlmSumIndex               INTEGER,
            e3AlmSumString              DisplayString (SIZE(0..255)),
            e3AlmSumUnitNum             CardID,
            e3AlmSumCardModel           CardModel,
            e3AlmSumPortNum             PortID,
            e3AlmSumChannel             ChannelNum,
            e3AlmSumAlmNum              AlarmNum,
            e3AlmSumStatus              AlmStatus,
            e3AlmSumSeverity            Severity
        }

        e3AlmSumUnit  OBJECT-TYPE
            SYNTAX  UnitID
            ACCESS  read-only
            STATUS  mandatory
            DESCRIPTION
            "unit 1 to 4."
            ::= { e3CurrActAlmSummaryEty 1 }

        e3AlmSumIndex  OBJECT-TYPE
            SYNTAX  INTEGER
            ACCESS  read-only
            STATUS  mandatory
            DESCRIPTION
                "Select Alarm Summary Index"
            ::= { e3CurrActAlmSummaryEty 2 }

        e3AlmSumString  OBJECT-TYPE
            SYNTAX  DisplayString (SIZE (0..255))
            ACCESS  read-only
            STATUS  mandatory
            DESCRIPTION
                "Alarm Summary String"
            ::= { e3CurrActAlmSummaryEty 3 }

        e3AlmSumUnitNum  OBJECT-TYPE
            SYNTAX  CardID
            ACCESS  read-only
            STATUS  mandatory
            DESCRIPTION
            "Xcu or Unit 1~4,11~16"
            ::= { e3CurrActAlmSummaryEty 4 }

        e3AlmSumCardModel  OBJECT-TYPE
            SYNTAX  CardModel
            ACCESS  read-only
            STATUS  mandatory
            DESCRIPTION
                "Card Model"
            ::= { e3CurrActAlmSummaryEty 5 }

        e3AlmSumPortNum  OBJECT-TYPE
            SYNTAX  PortID
            ACCESS  read-only
            STATUS  mandatory
            DESCRIPTION
                "Port number(1..3)"
            ::= { e3CurrActAlmSummaryEty 6 }

        e3AlmSumChannel  OBJECT-TYPE
            SYNTAX  ChannelNum
            ACCESS  read-only
            STATUS  mandatory
            DESCRIPTION
                "Channel number(1..28)"
            ::= { e3CurrActAlmSummaryEty 7 }

        e3AlmSumAlmNum  OBJECT-TYPE
            SYNTAX  AlarmNum
            ACCESS  read-only
            STATUS  mandatory
            DESCRIPTION
                "Alarm Num"
            ::= { e3CurrActAlmSummaryEty 8 }

        e3AlmSumStatus  OBJECT-TYPE
            SYNTAX  AlmStatus
            ACCESS  read-only
            STATUS  mandatory
            DESCRIPTION
                "The Status of Alarm"
            ::= { e3CurrActAlmSummaryEty 9 }

        e3AlmSumSeverity  OBJECT-TYPE
            SYNTAX  Severity
            ACCESS  read-only
            STATUS  mandatory
            DESCRIPTION
                "Alarm Severity"
            ::= { e3CurrActAlmSummaryEty 10 }

--
--  E3 Loopback & Diagnostics
--

    e3LoopbackAndDiagnostics           OBJECT IDENTIFIER ::= { e3-card 3 }

--
--  E3 Loopback Setup Table
--

        e3LoopbackSetupTab  OBJECT-TYPE
            SYNTAX  SEQUENCE OF E3LoopbackSetupEty
            ACCESS  not-accessible
            STATUS  mandatory
            DESCRIPTION
                "Loopback setup table"
            ::= { e3LoopbackAndDiagnostics 1 }

        e3LoopbackSetupEty  OBJECT-TYPE
            SYNTAX  E3LoopbackSetupEty
            ACCESS  not-accessible
            STATUS  mandatory
            DESCRIPTION
                "An entry in the loopback setup table"
            INDEX { e3LoopbackUnit ,
                    e3LoopbackPort }
            ::= { e3LoopbackSetupTab 1 }

        E3LoopbackSetupEty ::= SEQUENCE {
            e3LoopbackUnit              UnitID,
            e3LoopbackPort              PortID,
            e3LoopbackLoopbackType      INTEGER
        }

        e3LoopbackUnit  OBJECT-TYPE
            SYNTAX  UnitID
            ACCESS  read-only
            STATUS  mandatory
            DESCRIPTION
            "unit 1 to 4."
            ::= { e3LoopbackSetupEty 1 }

        e3LoopbackPort  OBJECT-TYPE
            SYNTAX  PortID
            ACCESS  read-only
            STATUS  mandatory
            DESCRIPTION
                "E3 Port 1 to 3"
            ::= { e3LoopbackSetupEty 2 }

        e3LoopbackLoopbackType  OBJECT-TYPE
            SYNTAX  INTEGER{
                    off(1),
                    local(2),
                    line(3)
                }
            ACCESS  read-write
            STATUS  mandatory
            DESCRIPTION
                "Loopback type"
            ::= { e3LoopbackSetupEty 3 }


--
--  E3 Diagnostics Setup Table
--

        e3DiagnosticsSetupTab  OBJECT-TYPE
            SYNTAX  SEQUENCE OF E3DiagnosticsSetupEty
            ACCESS  not-accessible
            STATUS  mandatory
            DESCRIPTION
                "Diagnostics setup table"
            ::= { e3LoopbackAndDiagnostics 2 }

        e3DiagnosticsSetupEty  OBJECT-TYPE
            SYNTAX  E3DiagnosticsSetupEty
            ACCESS  not-accessible
            STATUS  mandatory
            DESCRIPTION
                "An entry in the diagnostics setup table"
            INDEX { e3DiagUnit ,
                    e3DiagPort }
            ::= { e3DiagnosticsSetupTab 1 }

        E3DiagnosticsSetupEty ::= SEQUENCE {
            e3DiagUnit                  UnitID,
            e3DiagPort                  PortID,
            e3DiagBertDirection         INTEGER,
            e3DiagBertPattern           INTEGER,
            e3DiagBertAction            INTEGER,
            e3DiagBertStatus            INTEGER,
            e3DiagElapseSecond          INTEGER,
            e3DiagBitError              INTEGER,
            e3DiagErrorSecond           INTEGER,
            e3DiagSevereErrorSecond     INTEGER
        }

        e3DiagUnit  OBJECT-TYPE
            SYNTAX  UnitID
            ACCESS  read-only
            STATUS  mandatory
            DESCRIPTION
            "unit 1 to 4."
            ::= { e3DiagnosticsSetupEty 1 }

        e3DiagPort  OBJECT-TYPE
            SYNTAX  PortID
            ACCESS  read-only
            STATUS  mandatory
            DESCRIPTION
                "E3 Port 1 to 3"
            ::= { e3DiagnosticsSetupEty 2 }

        e3DiagBertDirection  OBJECT-TYPE
            SYNTAX  INTEGER{
                    optical-site(1),
                    line-site(2)
                }
            ACCESS  read-write
            STATUS  mandatory
            DESCRIPTION
                "BERT test direction"
            ::= { e3DiagnosticsSetupEty 3 }

        e3DiagBertPattern  OBJECT-TYPE
            SYNTAX  INTEGER{
                    off(1),
                    patt-2exp11-1(2),
                    patt-2exp15-1(3),
                    patt-2exp20-1(4),
                    patt-2exp23-1(5)
                }
            ACCESS  read-write
            STATUS  mandatory
            DESCRIPTION
                "BERT test pattern"
            ::= { e3DiagnosticsSetupEty 4 }

        e3DiagBertAction  OBJECT-TYPE
            SYNTAX  INTEGER{
                    none(0),
                    reset(1),
                    insert-error(2)
                }
            ACCESS  read-write
            STATUS  mandatory
            DESCRIPTION
                "BERT test action"
            ::= { e3DiagnosticsSetupEty 5 }

        e3DiagBertStatus  OBJECT-TYPE
            SYNTAX  INTEGER{
                    unsync(1),
                    sync(2)
                }
            ACCESS  read-only
            STATUS  mandatory
            DESCRIPTION
                "BERT status"
            ::= { e3DiagnosticsSetupEty 6 }

        e3DiagElapseSecond  OBJECT-TYPE
            SYNTAX  INTEGER
            ACCESS  read-only
            STATUS  mandatory
            DESCRIPTION
                "BERT elapsed time(s)"
            ::= { e3DiagnosticsSetupEty 7 }

        e3DiagBitError  OBJECT-TYPE
            SYNTAX  INTEGER
            ACCESS  read-only
            STATUS  mandatory
            DESCRIPTION
                "BERT Bit Error"
            ::= { e3DiagnosticsSetupEty 8 }

        e3DiagErrorSecond  OBJECT-TYPE
            SYNTAX  INTEGER
            ACCESS  read-only
            STATUS  mandatory
            DESCRIPTION
                "BERT Error Seconds"
            ::= { e3DiagnosticsSetupEty 9 }

        e3DiagSevereErrorSecond  OBJECT-TYPE
            SYNTAX  INTEGER
            ACCESS  read-only
            STATUS  mandatory
            DESCRIPTION
                "BERT SES"
            ::= { e3DiagnosticsSetupEty 10 }

--
--  E3 Performance
--

    e3Performance           OBJECT IDENTIFIER ::= { e3-card 4 }

--
--  E3 Performance Report
--

    e3PerformanceReport           OBJECT IDENTIFIER ::= { e3Performance 1 }

--
--  E3 Performance Report HoPath/STSPath Current Table
--

        e3HoPath-STSPathCurrTab  OBJECT-TYPE
            SYNTAX  SEQUENCE OF E3HoPath-STSPathCurrEty
            ACCESS  not-accessible
            STATUS  mandatory
            DESCRIPTION
                "Performance report current"
            ::= { e3PerformanceReport 1 }

        e3HoPath-STSPathCurrEty  OBJECT-TYPE
            SYNTAX  E3HoPath-STSPathCurrEty
            ACCESS  not-accessible
            STATUS  mandatory
            DESCRIPTION
                "An entry in the performance report current table"
            INDEX { e3HoSTSCurrUnit ,
                    e3HoSTSCurrPort ,
                    e3HoSTSCurrAnomalyType }
            ::= { e3HoPath-STSPathCurrTab 1 }

        E3HoPath-STSPathCurrEty ::= SEQUENCE {
            e3HoSTSCurrUnit             UnitID,
            e3HoSTSCurrPort             PortID,
            e3HoSTSCurrAnomalyType      HoPathPerfAnomalyType,
            e3HoSTSCurrEB-Count         INTEGER,
            e3HoSTSCurrBBE-Count        INTEGER,
            e3HoSTSCurrES-Count         INTEGER,
            e3HoSTSCurrUAS-Count        INTEGER,
            e3HoSTSCurrBES-Count        INTEGER,
            e3HoSTSCurrSES-Count        INTEGER,
            e3HoSTSCurr15MinTimeElaps   INTEGER,
            e3HoSTSCurr24hrValid15Min   INTEGER,
            e3HoSTSCurrDayValid15Min    INTEGER,
            e3HoSTSCurr7DayValidDays    INTEGER
        }

        e3HoSTSCurrUnit  OBJECT-TYPE
            SYNTAX  UnitID
            ACCESS  read-only
            STATUS  mandatory
            DESCRIPTION
            "unit 1 to 4."
            ::= { e3HoPath-STSPathCurrEty 1 }

        e3HoSTSCurrPort  OBJECT-TYPE
            SYNTAX  PortID
            ACCESS  read-only
            STATUS  mandatory
            DESCRIPTION
                "E3 Port 1 to 3"
            ::= { e3HoPath-STSPathCurrEty 2 }

        e3HoSTSCurrAnomalyType  OBJECT-TYPE
            SYNTAX  HoPathPerfAnomalyType
            ACCESS  read-only
            STATUS  mandatory
            DESCRIPTION
                "Performance report HoPath/STSPath Anomaly Type"
            ::= { e3HoPath-STSPathCurrEty 3 }

        e3HoSTSCurrEB-Count  OBJECT-TYPE
            SYNTAX  INTEGER
            ACCESS  read-only
            STATUS  mandatory
            DESCRIPTION
                "Current Error Block"
            ::= { e3HoPath-STSPathCurrEty 4 }

        e3HoSTSCurrBBE-Count  OBJECT-TYPE
            SYNTAX  INTEGER
            ACCESS  read-only
            STATUS  mandatory
            DESCRIPTION
                "Current Background Block Error"
            ::= { e3HoPath-STSPathCurrEty 5 }

        e3HoSTSCurrES-Count  OBJECT-TYPE
            SYNTAX  INTEGER
            ACCESS  read-only
            STATUS  mandatory
            DESCRIPTION
                "Error Second"
            ::= { e3HoPath-STSPathCurrEty 6 }

        e3HoSTSCurrUAS-Count  OBJECT-TYPE
            SYNTAX  INTEGER
            ACCESS  read-only
            STATUS  mandatory
            DESCRIPTION
                "Unavailable Second"
            ::= { e3HoPath-STSPathCurrEty 7 }

        e3HoSTSCurrBES-Count  OBJECT-TYPE
            SYNTAX  INTEGER
            ACCESS  read-only
            STATUS  mandatory
            DESCRIPTION
                "Background Error Second"
            ::= { e3HoPath-STSPathCurrEty 8 }

        e3HoSTSCurrSES-Count  OBJECT-TYPE
            SYNTAX  INTEGER
            ACCESS  read-only
            STATUS  mandatory
            DESCRIPTION
                "Severly Error Second"
            ::= { e3HoPath-STSPathCurrEty 9 }

        e3HoSTSCurr15MinTimeElaps  OBJECT-TYPE
            SYNTAX  INTEGER
            ACCESS  read-only
            STATUS  mandatory
            DESCRIPTION
                "Valid Seconds in Current 15-Min Interval"
            ::= { e3HoPath-STSPathCurrEty 10 }

        e3HoSTSCurr24hrValid15Min  OBJECT-TYPE
            SYNTAX  INTEGER
            ACCESS  read-only
            STATUS  mandatory
            DESCRIPTION
                "Valid 15-Min Intervals in Current 24-Hour Interval"
            ::= { e3HoPath-STSPathCurrEty 11 }

        e3HoSTSCurrDayValid15Min  OBJECT-TYPE
            SYNTAX  INTEGER
            ACCESS  read-only
            STATUS  mandatory
            DESCRIPTION
                "Valid 15-Min Intervals in Current Day"
            ::= { e3HoPath-STSPathCurrEty 12 }

        e3HoSTSCurr7DayValidDays  OBJECT-TYPE
            SYNTAX  INTEGER
            ACCESS  read-only
            STATUS  mandatory
            DESCRIPTION
                "Valid Days in Current Seven Day"
            ::= { e3HoPath-STSPathCurrEty 13 }


--
--  E3 Performance Report HoPath/STSPath Interval Table
--

        e3HoPath-STSPathIntvTab  OBJECT-TYPE
            SYNTAX  SEQUENCE OF E3HoPath-STSPathIntvEty
            ACCESS  not-accessible
            STATUS  mandatory
            DESCRIPTION
                "Performance report Inteval"
            ::= { e3PerformanceReport 2 }

        e3HoPath-STSPathIntvEty  OBJECT-TYPE
            SYNTAX  E3HoPath-STSPathIntvEty
            ACCESS  not-accessible
            STATUS  mandatory
            DESCRIPTION
                "An entry in the performance report interval table"
            INDEX { e3HoSTSIntvUnit ,
                    e3HoSTSIntvPort ,
                    e3HoSTSIntvAnomalyType ,
                    e3HoSTSIntvPeriod }
            ::= { e3HoPath-STSPathIntvTab 1 }

        E3HoPath-STSPathIntvEty ::= SEQUENCE {
            e3HoSTSIntvUnit             UnitID,
            e3HoSTSIntvPort             PortID,
            e3HoSTSIntvAnomalyType      HoPathPerfAnomalyType,
            e3HoSTSIntvPeriod           INTEGER (1..96),
            e3HoSTSIntvEB-Count         INTEGER,
            e3HoSTSIntvBBE-Count        INTEGER,
            e3HoSTSIntvES-Count         INTEGER,
            e3HoSTSIntvUAS-Count        INTEGER,
            e3HoSTSIntvBES-Count        INTEGER,
            e3HoSTSIntvSES-Count        INTEGER
        }

        e3HoSTSIntvUnit  OBJECT-TYPE
            SYNTAX  UnitID
            ACCESS  read-only
            STATUS  mandatory
            DESCRIPTION
            "unit 1 to 4."
            ::= { e3HoPath-STSPathIntvEty 1 }

        e3HoSTSIntvPort  OBJECT-TYPE
            SYNTAX  PortID
            ACCESS  read-only
            STATUS  mandatory
            DESCRIPTION
                "E3 Port 1 to 3"
            ::= { e3HoPath-STSPathIntvEty 2 }

        e3HoSTSIntvAnomalyType  OBJECT-TYPE
            SYNTAX  HoPathPerfAnomalyType
            ACCESS  read-only
            STATUS  mandatory
            DESCRIPTION
                "Performance report HoPath/STSPath Anomaly Type"
            ::= { e3HoPath-STSPathIntvEty 3 }

        e3HoSTSIntvPeriod  OBJECT-TYPE
            SYNTAX  INTEGER (1..96)
            ACCESS  read-only
            STATUS  mandatory
            DESCRIPTION
                "HoPath Interval Period"
            ::= { e3HoPath-STSPathIntvEty 4 }

        e3HoSTSIntvEB-Count  OBJECT-TYPE
            SYNTAX  INTEGER
            ACCESS  read-only
            STATUS  mandatory
            DESCRIPTION
                "Current Error Block"
            ::= { e3HoPath-STSPathIntvEty 5 }

        e3HoSTSIntvBBE-Count  OBJECT-TYPE
            SYNTAX  INTEGER
            ACCESS  read-only
            STATUS  mandatory
            DESCRIPTION
                "Current Background Block Error"
            ::= { e3HoPath-STSPathIntvEty 6 }

        e3HoSTSIntvES-Count  OBJECT-TYPE
            SYNTAX  INTEGER
            ACCESS  read-only
            STATUS  mandatory
            DESCRIPTION
                "Error Second"
            ::= { e3HoPath-STSPathIntvEty 7 }

        e3HoSTSIntvUAS-Count  OBJECT-TYPE
            SYNTAX  INTEGER
            ACCESS  read-only
            STATUS  mandatory
            DESCRIPTION
                "Unavailable Second"
            ::= { e3HoPath-STSPathIntvEty 8 }

        e3HoSTSIntvBES-Count  OBJECT-TYPE
            SYNTAX  INTEGER
            ACCESS  read-only
            STATUS  mandatory
            DESCRIPTION
                "Background Error Second"
            ::= { e3HoPath-STSPathIntvEty 9 }

        e3HoSTSIntvSES-Count  OBJECT-TYPE
            SYNTAX  INTEGER
            ACCESS  read-only
            STATUS  mandatory
            DESCRIPTION
                "Severly Error Second"
            ::= { e3HoPath-STSPathIntvEty 10 }


--
--  E3 Performance Report HoPath/STS-Path Seven Days Table
--

        e3HoPath-STSPath7DaysTab  OBJECT-TYPE
            SYNTAX  SEQUENCE OF E3HoPath-STSPath7DaysEty
            ACCESS  not-accessible
            STATUS  mandatory
            DESCRIPTION
                "Performance report Seven Days"
            ::= { e3PerformanceReport 3 }

        e3HoPath-STSPath7DaysEty  OBJECT-TYPE
            SYNTAX  E3HoPath-STSPath7DaysEty
            ACCESS  not-accessible
            STATUS  mandatory
            DESCRIPTION
                "An entry in the performance report seven days table"
            INDEX { e3HoSTS7DaysUnit ,
                    e3HoSTS7DaysPort ,
                    e3HoSTS7DaysAnomalyType ,
                    e3HoSTS7DaysDayIndex }
            ::= { e3HoPath-STSPath7DaysTab 1 }

        E3HoPath-STSPath7DaysEty ::= SEQUENCE {
            e3HoSTS7DaysUnit            UnitID,
            e3HoSTS7DaysPort            PortID,
            e3HoSTS7DaysAnomalyType     HoPathPerfAnomalyType,
            e3HoSTS7DaysDayIndex        INTEGER (1..7),
            e3HoSTS7DaysDate            DisplayString (SIZE (0..255) ),
            e3HoSTS7DaysEB-Count        INTEGER,
            e3HoSTS7DaysBBE-Count       INTEGER,
            e3HoSTS7DaysES-Count        INTEGER,
            e3HoSTS7DaysUAS-Count       INTEGER,
            e3HoSTS7DaysBES-Count       INTEGER,
            e3HoSTS7DaysSES-Count       INTEGER
        }

        e3HoSTS7DaysUnit  OBJECT-TYPE
            SYNTAX  UnitID
            ACCESS  read-only
            STATUS  mandatory
            DESCRIPTION
            "unit 1 to 4."
            ::= { e3HoPath-STSPath7DaysEty 1 }

        e3HoSTS7DaysPort  OBJECT-TYPE
            SYNTAX  PortID
            ACCESS  read-only
            STATUS  mandatory
            DESCRIPTION
                "E3 Port 1 to 3"
            ::= { e3HoPath-STSPath7DaysEty 2 }

        e3HoSTS7DaysAnomalyType  OBJECT-TYPE
            SYNTAX  HoPathPerfAnomalyType
            ACCESS  read-only
            STATUS  mandatory
            DESCRIPTION
                "Performance report HoPath/STSPath Anomaly Type"
            ::= { e3HoPath-STSPath7DaysEty 3 }

        e3HoSTS7DaysDayIndex  OBJECT-TYPE
            SYNTAX  INTEGER (1..7)
            ACCESS  read-only
            STATUS  mandatory
            DESCRIPTION
                "HoPath Seven Days day index"
            ::= { e3HoPath-STSPath7DaysEty 4 }

        e3HoSTS7DaysDate  OBJECT-TYPE
            SYNTAX  DisplayString (SIZE (0..255) )
            ACCESS  read-only
            STATUS  mandatory
            DESCRIPTION
                "Seven Days Date"
            ::= { e3HoPath-STSPath7DaysEty 5 }

        e3HoSTS7DaysEB-Count  OBJECT-TYPE
            SYNTAX  INTEGER
            ACCESS  read-only
            STATUS  mandatory
            DESCRIPTION
                "Current Error Block"
            ::= { e3HoPath-STSPath7DaysEty 6 }

        e3HoSTS7DaysBBE-Count  OBJECT-TYPE
            SYNTAX  INTEGER
            ACCESS  read-only
            STATUS  mandatory
            DESCRIPTION
                "Current Background Block Error"
            ::= { e3HoPath-STSPath7DaysEty 7 }

        e3HoSTS7DaysES-Count  OBJECT-TYPE
            SYNTAX  INTEGER
            ACCESS  read-only
            STATUS  mandatory
            DESCRIPTION
                "Error Second"
            ::= { e3HoPath-STSPath7DaysEty 8 }

        e3HoSTS7DaysUAS-Count  OBJECT-TYPE
            SYNTAX  INTEGER
            ACCESS  read-only
            STATUS  mandatory
            DESCRIPTION
                "Unavailable Second"
            ::= { e3HoPath-STSPath7DaysEty 9 }

        e3HoSTS7DaysBES-Count  OBJECT-TYPE
            SYNTAX  INTEGER
            ACCESS  read-only
            STATUS  mandatory
            DESCRIPTION
                "Background Error Second"
            ::= { e3HoPath-STSPath7DaysEty 10 }

        e3HoSTS7DaysSES-Count  OBJECT-TYPE
            SYNTAX  INTEGER
            ACCESS  read-only
            STATUS  mandatory
            DESCRIPTION
                "Severly Error Second"
            ::= { e3HoPath-STSPath7DaysEty 11 }


--
--  E3 Performance Report HoPath/STSPath Total Table
--

        e3HoPath-STSPathTotalTab  OBJECT-TYPE
            SYNTAX  SEQUENCE OF E3HoPath-STSPathTotalEty
            ACCESS  not-accessible
            STATUS  mandatory
            DESCRIPTION
                "Performance report Total"
            ::= { e3PerformanceReport 4 }

        e3HoPath-STSPathTotalEty  OBJECT-TYPE
            SYNTAX  E3HoPath-STSPathTotalEty
            ACCESS  not-accessible
            STATUS  mandatory
            DESCRIPTION
                "An entry in the performance report total table"
            INDEX { e3HoSTSTotalUnit ,
                    e3HoSTSTotalPort ,
                    e3HoSTSTotalAnomalyType }
            ::= { e3HoPath-STSPathTotalTab 1 }

        E3HoPath-STSPathTotalEty ::= SEQUENCE {
            e3HoSTSTotalUnit            UnitID,
            e3HoSTSTotalPort            PortID,
            e3HoSTSTotalAnomalyType     HoPathPerfAnomalyType,
            e3HoSTSTotalEB-Count        INTEGER,
            e3HoSTSTotalBBE-Count       INTEGER,
            e3HoSTSTotalES-Count        INTEGER,
            e3HoSTSTotalUAS-Count       INTEGER,
            e3HoSTSTotalBES-Count       INTEGER,
            e3HoSTSTotalSES-Count       INTEGER
        }

        e3HoSTSTotalUnit  OBJECT-TYPE
            SYNTAX  UnitID
            ACCESS  read-only
            STATUS  mandatory
            DESCRIPTION
            "unit 1 to 4."
            ::= { e3HoPath-STSPathTotalEty 1 }

        e3HoSTSTotalPort  OBJECT-TYPE
            SYNTAX  PortID
            ACCESS  read-only
            STATUS  mandatory
            DESCRIPTION
                "E3 Port 1 to 3"
            ::= { e3HoPath-STSPathTotalEty 2 }

        e3HoSTSTotalAnomalyType  OBJECT-TYPE
            SYNTAX  HoPathPerfAnomalyType
            ACCESS  read-only
            STATUS  mandatory
            DESCRIPTION
                "Performance report HoPath/STSPath Anomaly Type"
            ::= { e3HoPath-STSPathTotalEty 3 }

        e3HoSTSTotalEB-Count  OBJECT-TYPE
            SYNTAX  INTEGER
            ACCESS  read-only
            STATUS  mandatory
            DESCRIPTION
                "Current Error Block"
            ::= { e3HoPath-STSPathTotalEty 4 }

        e3HoSTSTotalBBE-Count  OBJECT-TYPE
            SYNTAX  INTEGER
            ACCESS  read-only
            STATUS  mandatory
            DESCRIPTION
                "Current Background Block Error"
            ::= { e3HoPath-STSPathTotalEty 5 }

        e3HoSTSTotalES-Count  OBJECT-TYPE
            SYNTAX  INTEGER
            ACCESS  read-only
            STATUS  mandatory
            DESCRIPTION
                "Error Second"
            ::= { e3HoPath-STSPathTotalEty 6 }

        e3HoSTSTotalUAS-Count  OBJECT-TYPE
            SYNTAX  INTEGER
            ACCESS  read-only
            STATUS  mandatory
            DESCRIPTION
                "Unavailable Second"
            ::= { e3HoPath-STSPathTotalEty 7 }

        e3HoSTSTotalBES-Count  OBJECT-TYPE
            SYNTAX  INTEGER
            ACCESS  read-only
            STATUS  mandatory
            DESCRIPTION
                "Background Error Second"
            ::= { e3HoPath-STSPathTotalEty 8 }

        e3HoSTSTotalSES-Count  OBJECT-TYPE
            SYNTAX  INTEGER
            ACCESS  read-only
            STATUS  mandatory
            DESCRIPTION
                "Severly Error Second"
            ::= { e3HoPath-STSPathTotalEty 9 }

--
--  E3 Performance Report LoPath/VTPath Current Table
--

        e3LoPath-VTPathCurrTab  OBJECT-TYPE
            SYNTAX  SEQUENCE OF E3LoPath-VTPathCurrEty
            ACCESS  not-accessible
            STATUS  mandatory
            DESCRIPTION
                "Performance report current"
            ::= { e3PerformanceReport 5 }

        e3LoPath-VTPathCurrEty  OBJECT-TYPE
            SYNTAX  E3LoPath-VTPathCurrEty
            ACCESS  not-accessible
            STATUS  mandatory
            DESCRIPTION
                "An entry in the performance report current table"
            INDEX { e3LoVTCurrUnit ,
                    e3LoVTCurrPort ,
                    e3LoVTCurrChannel ,
                    e3LoVTCurrAnomalyType }
            ::= { e3LoPath-VTPathCurrTab 1 }

        E3LoPath-VTPathCurrEty ::= SEQUENCE {
            e3LoVTCurrUnit              UnitID,
            e3LoVTCurrPort              PortID,
            e3LoVTCurrChannel           ChannelNum,
            e3LoVTCurrAnomalyType       LoPathPerfAnomalyType,
            e3LoVTCurrEB-Count          INTEGER,
            e3LoVTCurrBBE-Count         INTEGER,
            e3LoVTCurrES-Count          INTEGER,
            e3LoVTCurrUAS-Count         INTEGER,
            e3LoVTCurrBES-Count         INTEGER,
            e3LoVTCurrSES-Count         INTEGER,
            e3LoVTCurr15MinTimeElaps    INTEGER,
            e3LoVTCurr24hrValid15Min    INTEGER,
            e3LoVTCurrDayValid15Min     INTEGER,
            e3LoVTCurr7DayValidDays     INTEGER
        }

        e3LoVTCurrUnit  OBJECT-TYPE
            SYNTAX  UnitID
            ACCESS  read-only
            STATUS  mandatory
            DESCRIPTION
            "unit 1 to 4."
            ::= { e3LoPath-VTPathCurrEty 1 }

        e3LoVTCurrPort  OBJECT-TYPE
            SYNTAX  PortID
            ACCESS  read-only
            STATUS  mandatory
            DESCRIPTION
                "E3 Port 1 to 3"
            ::= { e3LoPath-VTPathCurrEty 2 }

        e3LoVTCurrChannel  OBJECT-TYPE
            SYNTAX  ChannelNum
            ACCESS  read-only
            STATUS  mandatory
            DESCRIPTION
                "E3 Channel 1 to 28"
            ::= { e3LoPath-VTPathCurrEty 3 }

        e3LoVTCurrAnomalyType  OBJECT-TYPE
            SYNTAX  LoPathPerfAnomalyType
            ACCESS  read-only
            STATUS  mandatory
            DESCRIPTION
                "Performance report LoPath/VTPath Anomaly Type"
            ::= { e3LoPath-VTPathCurrEty 4 }

        e3LoVTCurrEB-Count  OBJECT-TYPE
            SYNTAX  INTEGER
            ACCESS  read-only
            STATUS  mandatory
            DESCRIPTION
                "Current Error Block"
            ::= { e3LoPath-VTPathCurrEty 5 }

        e3LoVTCurrBBE-Count  OBJECT-TYPE
            SYNTAX  INTEGER
            ACCESS  read-only
            STATUS  mandatory
            DESCRIPTION
                "Current Background Block Error"
            ::= { e3LoPath-VTPathCurrEty 6 }

        e3LoVTCurrES-Count  OBJECT-TYPE
            SYNTAX  INTEGER
            ACCESS  read-only
            STATUS  mandatory
            DESCRIPTION
                "Error Second"
            ::= { e3LoPath-VTPathCurrEty 7 }

        e3LoVTCurrUAS-Count  OBJECT-TYPE
            SYNTAX  INTEGER
            ACCESS  read-only
            STATUS  mandatory
            DESCRIPTION
                "Unavailable Second"
            ::= { e3LoPath-VTPathCurrEty 8 }

        e3LoVTCurrBES-Count  OBJECT-TYPE
            SYNTAX  INTEGER
            ACCESS  read-only
            STATUS  mandatory
            DESCRIPTION
                "Background Error Second"
            ::= { e3LoPath-VTPathCurrEty 9 }

        e3LoVTCurrSES-Count  OBJECT-TYPE
            SYNTAX  INTEGER
            ACCESS  read-only
            STATUS  mandatory
            DESCRIPTION
                "Severly Error Second"
            ::= { e3LoPath-VTPathCurrEty 10 }

        e3LoVTCurr15MinTimeElaps  OBJECT-TYPE
            SYNTAX  INTEGER
            ACCESS  read-only
            STATUS  mandatory
            DESCRIPTION
                "Valid Seconds in Current 15-Min Interval"
            ::= { e3LoPath-VTPathCurrEty 11 }

        e3LoVTCurr24hrValid15Min  OBJECT-TYPE
            SYNTAX  INTEGER
            ACCESS  read-only
            STATUS  mandatory
            DESCRIPTION
                "Valid 15-Min Intervals in Current 24-Hour Interval"
            ::= { e3LoPath-VTPathCurrEty 12 }

        e3LoVTCurrDayValid15Min  OBJECT-TYPE
            SYNTAX  INTEGER
            ACCESS  read-only
            STATUS  mandatory
            DESCRIPTION
                "Valid 15-Min Intervals in Current Day"
            ::= { e3LoPath-VTPathCurrEty 13 }

        e3LoVTCurr7DayValidDays  OBJECT-TYPE
            SYNTAX  INTEGER
            ACCESS  read-only
            STATUS  mandatory
            DESCRIPTION
                "Valid Days in Current Seven Day"
            ::= { e3LoPath-VTPathCurrEty 14 }


--
--  E3 Performance Report LoPath/VTPath Interval Table
--

        e3LoPath-VTPathIntvTab  OBJECT-TYPE
            SYNTAX  SEQUENCE OF E3LoPath-VTPathIntvEty
            ACCESS  not-accessible
            STATUS  mandatory
            DESCRIPTION
                "Performance report Inteval"
            ::= { e3PerformanceReport 6 }

        e3LoPath-VTPathIntvEty  OBJECT-TYPE
            SYNTAX  E3LoPath-VTPathIntvEty
            ACCESS  not-accessible
            STATUS  mandatory
            DESCRIPTION
                "An entry in the performance report interval table"
            INDEX { e3LoVTIntvUnit ,
                    e3LoVTIntvPort ,
                    e3LoVTIntvChannel ,
                    e3LoVTIntvAnomalyType ,
                    e3LoVTIntvPeriod }
            ::= { e3LoPath-VTPathIntvTab 1 }

        E3LoPath-VTPathIntvEty ::= SEQUENCE {
            e3LoVTIntvUnit              UnitID,
            e3LoVTIntvPort              PortID,
            e3LoVTIntvChannel           ChannelNum,
            e3LoVTIntvAnomalyType       LoPathPerfAnomalyType,
            e3LoVTIntvPeriod            INTEGER (1..96),
            e3LoVTIntvEB-Count          INTEGER,
            e3LoVTIntvBBE-Count         INTEGER,
            e3LoVTIntvES-Count          INTEGER,
            e3LoVTIntvUAS-Count         INTEGER,
            e3LoVTIntvBES-Count         INTEGER,
            e3LoVTIntvSES-Count         INTEGER
        }

        e3LoVTIntvUnit  OBJECT-TYPE
            SYNTAX  UnitID
            ACCESS  read-only
            STATUS  mandatory
            DESCRIPTION
            "unit 1 to 4."
            ::= { e3LoPath-VTPathIntvEty 1 }

        e3LoVTIntvPort  OBJECT-TYPE
            SYNTAX  PortID
            ACCESS  read-only
            STATUS  mandatory
            DESCRIPTION
                "E3 Port 1 to 3"
            ::= { e3LoPath-VTPathIntvEty 2 }

        e3LoVTIntvChannel  OBJECT-TYPE
            SYNTAX  ChannelNum
            ACCESS  read-only
            STATUS  mandatory
            DESCRIPTION
                "E3 Channel 1 to 28"
            ::= { e3LoPath-VTPathIntvEty 3 }

        e3LoVTIntvAnomalyType  OBJECT-TYPE
            SYNTAX  LoPathPerfAnomalyType
            ACCESS  read-only
            STATUS  mandatory
            DESCRIPTION
                "Performance report LoPath/VTPath Anomaly Type"
            ::= { e3LoPath-VTPathIntvEty 4 }

        e3LoVTIntvPeriod  OBJECT-TYPE
            SYNTAX  INTEGER (1..96)
            ACCESS  read-only
            STATUS  mandatory
            DESCRIPTION
                "LoPath Interval Period"
            ::= { e3LoPath-VTPathIntvEty 5 }

        e3LoVTIntvEB-Count  OBJECT-TYPE
            SYNTAX  INTEGER
            ACCESS  read-only
            STATUS  mandatory
            DESCRIPTION
                "Current Error Block"
            ::= { e3LoPath-VTPathIntvEty 6 }

        e3LoVTIntvBBE-Count  OBJECT-TYPE
            SYNTAX  INTEGER
            ACCESS  read-only
            STATUS  mandatory
            DESCRIPTION
                "Current Background Block Error"
            ::= { e3LoPath-VTPathIntvEty 7 }

        e3LoVTIntvES-Count  OBJECT-TYPE
            SYNTAX  INTEGER
            ACCESS  read-only
            STATUS  mandatory
            DESCRIPTION
                "Error Second"
            ::= { e3LoPath-VTPathIntvEty 8 }

        e3LoVTIntvUAS-Count  OBJECT-TYPE
            SYNTAX  INTEGER
            ACCESS  read-only
            STATUS  mandatory
            DESCRIPTION
                "Unavailable Second"
            ::= { e3LoPath-VTPathIntvEty 9 }

        e3LoVTIntvBES-Count  OBJECT-TYPE
            SYNTAX  INTEGER
            ACCESS  read-only
            STATUS  mandatory
            DESCRIPTION
                "Background Error Second"
            ::= { e3LoPath-VTPathIntvEty 10 }

        e3LoVTIntvSES-Count  OBJECT-TYPE
            SYNTAX  INTEGER
            ACCESS  read-only
            STATUS  mandatory
            DESCRIPTION
                "Severly Error Second"
            ::= { e3LoPath-VTPathIntvEty 11 }


--
--  E3 Performance Report LoPath/VT-Path Seven Days Table
--

        e3LoPath-VTPath7DaysTab  OBJECT-TYPE
            SYNTAX  SEQUENCE OF E3LoPath-VTPath7DaysEty
            ACCESS  not-accessible
            STATUS  mandatory
            DESCRIPTION
                "Performance report Seven Days"
            ::= { e3PerformanceReport 7 }

        e3LoPath-VTPath7DaysEty  OBJECT-TYPE
            SYNTAX  E3LoPath-VTPath7DaysEty
            ACCESS  not-accessible
            STATUS  mandatory
            DESCRIPTION
                "An entry in the performance report seven days table"
            INDEX { e3LoVT7DaysUnit ,
                    e3LoVT7DaysPort ,
                    e3LoVT7DaysChannel ,
                    e3LoVT7DaysAnomalyType ,
                    e3LoVT7DaysDayIndex }
            ::= { e3LoPath-VTPath7DaysTab 1 }

        E3LoPath-VTPath7DaysEty ::= SEQUENCE {
            e3LoVT7DaysUnit             UnitID,
            e3LoVT7DaysPort             PortID,
            e3LoVT7DaysChannel          ChannelNum,
            e3LoVT7DaysAnomalyType      LoPathPerfAnomalyType,
            e3LoVT7DaysDayIndex         INTEGER (1..7),
            e3LoVT7DaysDate             DisplayString (SIZE (0..255) ),
            e3LoVT7DaysEB-Count         INTEGER,
            e3LoVT7DaysBBE-Count        INTEGER,
            e3LoVT7DaysES-Count         INTEGER,
            e3LoVT7DaysUAS-Count        INTEGER,
            e3LoVT7DaysBES-Count        INTEGER,
            e3LoVT7DaysSES-Count        INTEGER
        }

        e3LoVT7DaysUnit  OBJECT-TYPE
            SYNTAX  UnitID
            ACCESS  read-only
            STATUS  mandatory
            DESCRIPTION
            "unit 1 to 4."
            ::= { e3LoPath-VTPath7DaysEty 1 }

        e3LoVT7DaysPort  OBJECT-TYPE
            SYNTAX  PortID
            ACCESS  read-only
            STATUS  mandatory
            DESCRIPTION
                "E3 Port 1 to 3"
            ::= { e3LoPath-VTPath7DaysEty 2 }

        e3LoVT7DaysChannel  OBJECT-TYPE
            SYNTAX  ChannelNum
            ACCESS  read-only
            STATUS  mandatory
            DESCRIPTION
                "E3 Channel 1 to 28"
            ::= { e3LoPath-VTPath7DaysEty 3 }

        e3LoVT7DaysAnomalyType  OBJECT-TYPE
            SYNTAX  LoPathPerfAnomalyType
            ACCESS  read-only
            STATUS  mandatory
            DESCRIPTION
                "Performance report LoPath/VTPath Anomaly Type"
            ::= { e3LoPath-VTPath7DaysEty 4 }

        e3LoVT7DaysDayIndex  OBJECT-TYPE
            SYNTAX  INTEGER (1..7)
            ACCESS  read-only
            STATUS  mandatory
            DESCRIPTION
                "LoPath Seven Days day index"
            ::= { e3LoPath-VTPath7DaysEty 5 }

        e3LoVT7DaysDate  OBJECT-TYPE
            SYNTAX  DisplayString (SIZE (0..255) )
            ACCESS  read-only
            STATUS  mandatory
            DESCRIPTION
                "Seven Days Date"
            ::= { e3LoPath-VTPath7DaysEty 6 }

        e3LoVT7DaysEB-Count  OBJECT-TYPE
            SYNTAX  INTEGER
            ACCESS  read-only
            STATUS  mandatory
            DESCRIPTION
                "Current Error Block"
            ::= { e3LoPath-VTPath7DaysEty 7 }

        e3LoVT7DaysBBE-Count  OBJECT-TYPE
            SYNTAX  INTEGER
            ACCESS  read-only
            STATUS  mandatory
            DESCRIPTION
                "Current Background Block Error"
            ::= { e3LoPath-VTPath7DaysEty 8 }

        e3LoVT7DaysES-Count  OBJECT-TYPE
            SYNTAX  INTEGER
            ACCESS  read-only
            STATUS  mandatory
            DESCRIPTION
                "Error Second"
            ::= { e3LoPath-VTPath7DaysEty 9 }

        e3LoVT7DaysUAS-Count  OBJECT-TYPE
            SYNTAX  INTEGER
            ACCESS  read-only
            STATUS  mandatory
            DESCRIPTION
                "Unavailable Second"
            ::= { e3LoPath-VTPath7DaysEty 10 }

        e3LoVT7DaysBES-Count  OBJECT-TYPE
            SYNTAX  INTEGER
            ACCESS  read-only
            STATUS  mandatory
            DESCRIPTION
                "Background Error Second"
            ::= { e3LoPath-VTPath7DaysEty 11 }

        e3LoVT7DaysSES-Count  OBJECT-TYPE
            SYNTAX  INTEGER
            ACCESS  read-only
            STATUS  mandatory
            DESCRIPTION
                "Severly Error Second"
            ::= { e3LoPath-VTPath7DaysEty 12 }


--
--  E3 Performance Report LoPath/VTPath Total Table
--

        e3LoPath-VTPathTotalTab  OBJECT-TYPE
            SYNTAX  SEQUENCE OF E3LoPath-VTPathTotalEty
            ACCESS  not-accessible
            STATUS  mandatory
            DESCRIPTION
                "Performance report Total"
            ::= { e3PerformanceReport 8 }

        e3LoPath-VTPathTotalEty  OBJECT-TYPE
            SYNTAX  E3LoPath-VTPathTotalEty
            ACCESS  not-accessible
            STATUS  mandatory
            DESCRIPTION
                "An entry in the performance report total table"
            INDEX { e3LoVTTotalUnit ,
                    e3LoVTTotalPort ,
                    e3LoVTTotalChannel ,
                    e3LoVTTotalAnomalyType }
            ::= { e3LoPath-VTPathTotalTab 1 }

        E3LoPath-VTPathTotalEty ::= SEQUENCE {
            e3LoVTTotalUnit             UnitID,
            e3LoVTTotalPort             PortID,
            e3LoVTTotalChannel          ChannelNum,
            e3LoVTTotalAnomalyType      LoPathPerfAnomalyType,
            e3LoVTTotalEB-Count         INTEGER,
            e3LoVTTotalBBE-Count        INTEGER,
            e3LoVTTotalES-Count         INTEGER,
            e3LoVTTotalUAS-Count        INTEGER,
            e3LoVTTotalBES-Count        INTEGER,
            e3LoVTTotalSES-Count        INTEGER
        }

        e3LoVTTotalUnit  OBJECT-TYPE
            SYNTAX  UnitID
            ACCESS  read-only
            STATUS  mandatory
            DESCRIPTION
            "unit 1 to 4."
            ::= { e3LoPath-VTPathTotalEty 1 }

        e3LoVTTotalPort  OBJECT-TYPE
            SYNTAX  PortID
            ACCESS  read-only
            STATUS  mandatory
            DESCRIPTION
                "E3 Port 1 to 3"
            ::= { e3LoPath-VTPathTotalEty 2 }

        e3LoVTTotalChannel  OBJECT-TYPE
            SYNTAX  ChannelNum
            ACCESS  read-only
            STATUS  mandatory
            DESCRIPTION
                "E3 Channel 1 to 28"
            ::= { e3LoPath-VTPathTotalEty 3 }

        e3LoVTTotalAnomalyType  OBJECT-TYPE
            SYNTAX  LoPathPerfAnomalyType
            ACCESS  read-only
            STATUS  mandatory
            DESCRIPTION
                "Performance report LoPath/VTPath Anomaly Type"
            ::= { e3LoPath-VTPathTotalEty 4 }

        e3LoVTTotalEB-Count  OBJECT-TYPE
            SYNTAX  INTEGER
            ACCESS  read-only
            STATUS  mandatory
            DESCRIPTION
                "Current Error Block"
            ::= { e3LoPath-VTPathTotalEty 5 }

        e3LoVTTotalBBE-Count  OBJECT-TYPE
            SYNTAX  INTEGER
            ACCESS  read-only
            STATUS  mandatory
            DESCRIPTION
                "Current Background Block Error"
            ::= { e3LoPath-VTPathTotalEty 6 }

        e3LoVTTotalES-Count  OBJECT-TYPE
            SYNTAX  INTEGER
            ACCESS  read-only
            STATUS  mandatory
            DESCRIPTION
                "Error Second"
            ::= { e3LoPath-VTPathTotalEty 7 }

        e3LoVTTotalUAS-Count  OBJECT-TYPE
            SYNTAX  INTEGER
            ACCESS  read-only
            STATUS  mandatory
            DESCRIPTION
                "Unavailable Second"
            ::= { e3LoPath-VTPathTotalEty 8 }

        e3LoVTTotalBES-Count  OBJECT-TYPE
            SYNTAX  INTEGER
            ACCESS  read-only
            STATUS  mandatory
            DESCRIPTION
                "Background Error Second"
            ::= { e3LoPath-VTPathTotalEty 9 }

        e3LoVTTotalSES-Count  OBJECT-TYPE
            SYNTAX  INTEGER
            ACCESS  read-only
            STATUS  mandatory
            DESCRIPTION
                "Severly Error Second"
            ::= { e3LoPath-VTPathTotalEty 10 }

--
--  E3 Performance Report Line Current Table
--

        e3LineCurrTab  OBJECT-TYPE
            SYNTAX  SEQUENCE OF E3LineCurrEty
            ACCESS  not-accessible
            STATUS  mandatory
            DESCRIPTION
                "Performance report current"
            ::= { e3PerformanceReport 9 }

        e3LineCurrEty  OBJECT-TYPE
            SYNTAX  E3LineCurrEty
            ACCESS  not-accessible
            STATUS  mandatory
            DESCRIPTION
                "An entry in the performance report current table"
            INDEX { e3LineCurrUnit ,
                    e3LineCurrPort }
            ::= { e3LineCurrTab 1 }

        E3LineCurrEty ::= SEQUENCE {
            e3LineCurrUnit              UnitID,
            e3LineCurrPort              PortID,
            e3LineCurrES-Count          INTEGER,
            e3LineCurrUAS-Count         INTEGER,
            e3LineCurrBES-Count         INTEGER,
            e3LineCurrSES-Count         INTEGER,
            e3LineCurrBPV-Count         INTEGER,
            e3LineCurr15MinTimeElaps    INTEGER,
            e3LineCurr24hrValid15Min    INTEGER,
            e3LineCurrDayValid15Min     INTEGER,
            e3LineCurr7DayValidDays     INTEGER
        }

        e3LineCurrUnit  OBJECT-TYPE
            SYNTAX  UnitID
            ACCESS  read-only
            STATUS  mandatory
            DESCRIPTION
            "unit 1 to 4."
            ::= { e3LineCurrEty 1 }

        e3LineCurrPort  OBJECT-TYPE
            SYNTAX  PortID
            ACCESS  read-only
            STATUS  mandatory
            DESCRIPTION
                "E3 Port 1 to 3"
            ::= { e3LineCurrEty 2 }


        e3LineCurrES-Count  OBJECT-TYPE
            SYNTAX  INTEGER
            ACCESS  read-only
            STATUS  mandatory
            DESCRIPTION
                "Error Second"
            ::= { e3LineCurrEty 3 }

        e3LineCurrUAS-Count  OBJECT-TYPE
            SYNTAX  INTEGER
            ACCESS  read-only
            STATUS  mandatory
            DESCRIPTION
                "Unavailable Second"
            ::= { e3LineCurrEty 4 }

        e3LineCurrBES-Count  OBJECT-TYPE
            SYNTAX  INTEGER
            ACCESS  read-only
            STATUS  mandatory
            DESCRIPTION
                "Background Error Second"
            ::= { e3LineCurrEty 5 }

        e3LineCurrSES-Count  OBJECT-TYPE
            SYNTAX  INTEGER
            ACCESS  read-only
            STATUS  mandatory
            DESCRIPTION
                "Severly Error Second"
            ::= { e3LineCurrEty 6 }

        e3LineCurrBPV-Count  OBJECT-TYPE
            SYNTAX  INTEGER
            ACCESS  read-only
            STATUS  mandatory
            DESCRIPTION
                "Bipolar Violation"
            ::= { e3LineCurrEty 7 }

        e3LineCurr15MinTimeElaps  OBJECT-TYPE
            SYNTAX  INTEGER
            ACCESS  read-only
            STATUS  mandatory
            DESCRIPTION
                "Valid Seconds in Current 15-Min Interval"
            ::= { e3LineCurrEty 8 }

        e3LineCurr24hrValid15Min  OBJECT-TYPE
            SYNTAX  INTEGER
            ACCESS  read-only
            STATUS  mandatory
            DESCRIPTION
                "Valid 15-Min Intervals in Current 24-Hour Interval"
            ::= { e3LineCurrEty 9 }

        e3LineCurrDayValid15Min  OBJECT-TYPE
            SYNTAX  INTEGER
            ACCESS  read-only
            STATUS  mandatory
            DESCRIPTION
                "Valid 15-Min Intervals in Current Day"
            ::= { e3LineCurrEty 10 }

        e3LineCurr7DayValidDays  OBJECT-TYPE
            SYNTAX  INTEGER
            ACCESS  read-only
            STATUS  mandatory
            DESCRIPTION
                "Valid Days in Current Seven Day"
            ::= { e3LineCurrEty 11 }


--
--  E3 Performance Report Line Interval Table
--

        e3LineIntervalTab  OBJECT-TYPE
            SYNTAX  SEQUENCE OF E3LineIntervalEty
            ACCESS  not-accessible
            STATUS  mandatory
            DESCRIPTION
                "Performance report Inteval"
            ::= { e3PerformanceReport 10 }

        e3LineIntervalEty  OBJECT-TYPE
            SYNTAX  E3LineIntervalEty
            ACCESS  not-accessible
            STATUS  mandatory
            DESCRIPTION
                "An entry in the performance report interval table"
            INDEX { e3LineIntvUnit ,
                    e3LineIntvPort ,
                    e3LineIntvPeriod }
            ::= { e3LineIntervalTab 1 }

        E3LineIntervalEty ::= SEQUENCE {
            e3LineIntvUnit              UnitID,
            e3LineIntvPort              PortID,
            e3LineIntvPeriod            INTEGER (1..96),
            e3LineIntvES-Count          INTEGER,
            e3LineIntvUAS-Count         INTEGER,
            e3LineIntvBES-Count         INTEGER,
            e3LineIntvSES-Count         INTEGER,
            e3LineIntvBPV-Count         INTEGER
        }

        e3LineIntvUnit  OBJECT-TYPE
            SYNTAX  UnitID
            ACCESS  read-only
            STATUS  mandatory
            DESCRIPTION
            "unit 1 to 4."
            ::= { e3LineIntervalEty 1 }

        e3LineIntvPort  OBJECT-TYPE
            SYNTAX  PortID
            ACCESS  read-only
            STATUS  mandatory
            DESCRIPTION
                "E3 Port 1 to 3"
            ::= { e3LineIntervalEty 2 }

        e3LineIntvPeriod  OBJECT-TYPE
            SYNTAX  INTEGER (1..96)
            ACCESS  read-only
            STATUS  mandatory
            DESCRIPTION
                "Line Interval Period"
            ::= { e3LineIntervalEty 3 }

        e3LineIntvES-Count  OBJECT-TYPE
            SYNTAX  INTEGER
            ACCESS  read-only
            STATUS  mandatory
            DESCRIPTION
                "Error Second"
            ::= { e3LineIntervalEty 4 }

        e3LineIntvUAS-Count  OBJECT-TYPE
            SYNTAX  INTEGER
            ACCESS  read-only
            STATUS  mandatory
            DESCRIPTION
                "Unavailable Second"
            ::= { e3LineIntervalEty 5 }

        e3LineIntvBES-Count  OBJECT-TYPE
            SYNTAX  INTEGER
            ACCESS  read-only
            STATUS  mandatory
            DESCRIPTION
                "Background Error Second"
            ::= { e3LineIntervalEty 6 }

        e3LineIntvSES-Count  OBJECT-TYPE
            SYNTAX  INTEGER
            ACCESS  read-only
            STATUS  mandatory
            DESCRIPTION
                "Severly Error Second"
            ::= { e3LineIntervalEty 7 }

        e3LineIntvBPV-Count  OBJECT-TYPE
            SYNTAX  INTEGER
            ACCESS  read-only
            STATUS  mandatory
            DESCRIPTION
                "Bipolar Violation"
            ::= { e3LineIntervalEty 8 }

--
--  E3 Performance Report Line Seven Days Table
--

        e3Line7DaysTab  OBJECT-TYPE
            SYNTAX  SEQUENCE OF E3Line7DaysEty
            ACCESS  not-accessible
            STATUS  mandatory
            DESCRIPTION
                "Performance report seven days"
            ::= { e3PerformanceReport 11 }

        e3Line7DaysEty  OBJECT-TYPE
            SYNTAX  E3Line7DaysEty
            ACCESS  not-accessible
            STATUS  mandatory
            DESCRIPTION
                "An entry in the performance report seven days table"
            INDEX { e3Line7DaysUnit ,
                    e3Line7DaysPort ,
                    e3Line7DaysDayIndex }
            ::= { e3Line7DaysTab 1 }

        E3Line7DaysEty ::= SEQUENCE {
            e3Line7DaysUnit             UnitID,
            e3Line7DaysPort             PortID,
            e3Line7DaysDayIndex         INTEGER (1..7),
            e3Line7DaysDate             DisplayString (SIZE (0..255) ),
            e3Line7DaysES-Count         INTEGER,
            e3Line7DaysUAS-Count        INTEGER,
            e3Line7DaysBES-Count        INTEGER,
            e3Line7DaysSES-Count        INTEGER,
            e3Line7DaysBPV-Count        INTEGER
        }

        e3Line7DaysUnit  OBJECT-TYPE
            SYNTAX  UnitID
            ACCESS  read-only
            STATUS  mandatory
            DESCRIPTION
            "unit 1 to 4."
            ::= { e3Line7DaysEty 1 }

        e3Line7DaysPort  OBJECT-TYPE
            SYNTAX  PortID
            ACCESS  read-only
            STATUS  mandatory
            DESCRIPTION
                "E3 Port 1 to 3"
            ::= { e3Line7DaysEty 2 }

        e3Line7DaysDayIndex  OBJECT-TYPE
            SYNTAX  INTEGER (1..7)
            ACCESS  read-only
            STATUS  mandatory
            DESCRIPTION
                "Line Seven Days day index"
            ::= { e3Line7DaysEty 3 }

        e3Line7DaysDate  OBJECT-TYPE
            SYNTAX  DisplayString (SIZE (0..255) )
            ACCESS  read-only
            STATUS  mandatory
            DESCRIPTION
                "Seven Days Date"
            ::= { e3Line7DaysEty 4 }

        e3Line7DaysES-Count  OBJECT-TYPE
            SYNTAX  INTEGER
            ACCESS  read-only
            STATUS  mandatory
            DESCRIPTION
                "Error Second"
            ::= { e3Line7DaysEty 5 }

        e3Line7DaysUAS-Count  OBJECT-TYPE
            SYNTAX  INTEGER
            ACCESS  read-only
            STATUS  mandatory
            DESCRIPTION
                "Unavailable Second"
            ::= { e3Line7DaysEty 6 }

        e3Line7DaysBES-Count  OBJECT-TYPE
            SYNTAX  INTEGER
            ACCESS  read-only
            STATUS  mandatory
            DESCRIPTION
                "Background Error Second"
            ::= { e3Line7DaysEty 7 }

        e3Line7DaysSES-Count  OBJECT-TYPE
            SYNTAX  INTEGER
            ACCESS  read-only
            STATUS  mandatory
            DESCRIPTION
                "Severly Error Second"
            ::= { e3Line7DaysEty 8 }

        e3Line7DaysBPV-Count  OBJECT-TYPE
            SYNTAX  INTEGER
            ACCESS  read-only
            STATUS  mandatory
            DESCRIPTION
                "Bipolar Violation"
            ::= { e3Line7DaysEty 9 }


--
--  E3 Performance Report Line Total Table
--

        e3LineTotalTab  OBJECT-TYPE
            SYNTAX  SEQUENCE OF E3LineTotalEty
            ACCESS  not-accessible
            STATUS  mandatory
            DESCRIPTION
                "Performance report Total"
            ::= { e3PerformanceReport 12 }

        e3LineTotalEty  OBJECT-TYPE
            SYNTAX  E3LineTotalEty
            ACCESS  not-accessible
            STATUS  mandatory
            DESCRIPTION
                "An entry in the performance report total table"
            INDEX { e3LineTotalUnit ,
                    e3LineTotalPort }
            ::= { e3LineTotalTab 1 }

        E3LineTotalEty ::= SEQUENCE {
            e3LineTotalUnit             UnitID,
            e3LineTotalPort             PortID,
            e3LineTotalES-Count         INTEGER,
            e3LineTotalUAS-Count        INTEGER,
            e3LineTotalBES-Count        INTEGER,
            e3LineTotalSES-Count        INTEGER,
            e3LineTotalBPV-Count        INTEGER
        }

        e3LineTotalUnit  OBJECT-TYPE
            SYNTAX  UnitID
            ACCESS  read-only
            STATUS  mandatory
            DESCRIPTION
            "unit 1 to 4."
            ::= { e3LineTotalEty 1 }

        e3LineTotalPort  OBJECT-TYPE
            SYNTAX  PortID
            ACCESS  read-only
            STATUS  mandatory
            DESCRIPTION
                "E3 Port 1 to 3"
            ::= { e3LineTotalEty 2 }

        e3LineTotalES-Count  OBJECT-TYPE
            SYNTAX  INTEGER
            ACCESS  read-only
            STATUS  mandatory
            DESCRIPTION
                "Error Second"
            ::= { e3LineTotalEty 3 }

        e3LineTotalUAS-Count  OBJECT-TYPE
            SYNTAX  INTEGER
            ACCESS  read-only
            STATUS  mandatory
            DESCRIPTION
                "Unavailable Second"
            ::= { e3LineTotalEty 4 }

        e3LineTotalBES-Count  OBJECT-TYPE
            SYNTAX  INTEGER
            ACCESS  read-only
            STATUS  mandatory
            DESCRIPTION
                "Background Error Second"
            ::= { e3LineTotalEty 5 }

        e3LineTotalSES-Count  OBJECT-TYPE
            SYNTAX  INTEGER
            ACCESS  read-only
            STATUS  mandatory
            DESCRIPTION
                "Severly Error Second"
            ::= { e3LineTotalEty 6 }

        e3LineTotalBPV-Count  OBJECT-TYPE
            SYNTAX  INTEGER
            ACCESS  read-only
            STATUS  mandatory
            DESCRIPTION
                "Bipolar Violation"
            ::= { e3LineTotalEty 7 }

--
--  E3 Performance Report FAS Current Table
--

        e3FASCurrTab  OBJECT-TYPE
            SYNTAX  SEQUENCE OF E3FASCurrEty
            ACCESS  not-accessible
            STATUS  mandatory
            DESCRIPTION
                "Performance report current"
            ::= { e3PerformanceReport 13 }

        e3FASCurrEty  OBJECT-TYPE
            SYNTAX  E3FASCurrEty
            ACCESS  not-accessible
            STATUS  mandatory
            DESCRIPTION
                "An entry in the performance report current table"
            INDEX { e3FASCurrUnit ,
                    e3FASCurrPort }
            ::= { e3FASCurrTab 1 }

        E3FASCurrEty ::= SEQUENCE {
            e3FASCurrUnit               UnitID,
            e3FASCurrPort               PortID,
            e3FASCurrES-Count           INTEGER,
            e3FASCurrUAS-Count          INTEGER,
            e3FASCurrBES-Count          INTEGER,
            e3FASCurrSES-Count          INTEGER,
            e3FASCurrBPV-Count          INTEGER,
            e3FASCurr15MinTimeElaps     INTEGER,
            e3FASCurr24hrValid15Min     INTEGER,
            e3FASCurrDayValid15Min      INTEGER,
            e3FASCurr7DayValidDays      INTEGER
        }

        e3FASCurrUnit  OBJECT-TYPE
            SYNTAX  UnitID
            ACCESS  read-only
            STATUS  mandatory
            DESCRIPTION
            "unit 1 to 4."
            ::= { e3FASCurrEty 1 }

        e3FASCurrPort  OBJECT-TYPE
            SYNTAX  PortID
            ACCESS  read-only
            STATUS  mandatory
            DESCRIPTION
                "E3 Port 1 to 3"
            ::= { e3FASCurrEty 2 }


        e3FASCurrES-Count  OBJECT-TYPE
            SYNTAX  INTEGER
            ACCESS  read-only
            STATUS  mandatory
            DESCRIPTION
                "Error Second"
            ::= { e3FASCurrEty 3 }

        e3FASCurrUAS-Count  OBJECT-TYPE
            SYNTAX  INTEGER
            ACCESS  read-only
            STATUS  mandatory
            DESCRIPTION
                "Unavailable Second"
            ::= { e3FASCurrEty 4 }

        e3FASCurrBES-Count  OBJECT-TYPE
            SYNTAX  INTEGER
            ACCESS  read-only
            STATUS  mandatory
            DESCRIPTION
                "Background Error Second"
            ::= { e3FASCurrEty 5 }

        e3FASCurrSES-Count  OBJECT-TYPE
            SYNTAX  INTEGER
            ACCESS  read-only
            STATUS  mandatory
            DESCRIPTION
                "Severly Error Second"
            ::= { e3FASCurrEty 6 }

        e3FASCurrBPV-Count  OBJECT-TYPE
            SYNTAX  INTEGER
            ACCESS  read-only
            STATUS  mandatory
            DESCRIPTION
                "Bipolar Violation"
            ::= { e3FASCurrEty 7 }

        e3FASCurr15MinTimeElaps  OBJECT-TYPE
            SYNTAX  INTEGER
            ACCESS  read-only
            STATUS  mandatory
            DESCRIPTION
                "Valid Seconds in Current 15-Min Interval"
            ::= { e3FASCurrEty 8 }

        e3FASCurr24hrValid15Min  OBJECT-TYPE
            SYNTAX  INTEGER
            ACCESS  read-only
            STATUS  mandatory
            DESCRIPTION
                "Valid 15-Min Intervals in Current 24-Hour Interval"
            ::= { e3FASCurrEty 9 }

        e3FASCurrDayValid15Min  OBJECT-TYPE
            SYNTAX  INTEGER
            ACCESS  read-only
            STATUS  mandatory
            DESCRIPTION
                "Valid 15-Min Intervals in Current Day"
            ::= { e3FASCurrEty 10 }

        e3FASCurr7DayValidDays  OBJECT-TYPE
            SYNTAX  INTEGER
            ACCESS  read-only
            STATUS  mandatory
            DESCRIPTION
                "Valid Days in Current Seven Day"
            ::= { e3FASCurrEty 11 }


--
--  E3 Performance Report FAS Interval Table
--

        e3FASIntervalTab  OBJECT-TYPE
            SYNTAX  SEQUENCE OF E3FASIntervalEty
            ACCESS  not-accessible
            STATUS  mandatory
            DESCRIPTION
                "Performance report Inteval"
            ::= { e3PerformanceReport 14 }

        e3FASIntervalEty  OBJECT-TYPE
            SYNTAX  E3FASIntervalEty
            ACCESS  not-accessible
            STATUS  mandatory
            DESCRIPTION
                "An entry in the performance report interval table"
            INDEX { e3FASIntvUnit ,
                    e3FASIntvPort ,
                    e3FASIntvPeriod }
            ::= { e3FASIntervalTab 1 }

        E3FASIntervalEty ::= SEQUENCE {
            e3FASIntvUnit               UnitID,
            e3FASIntvPort               PortID,
            e3FASIntvPeriod             INTEGER (1..96),
            e3FASIntvES-Count           INTEGER,
            e3FASIntvUAS-Count          INTEGER,
            e3FASIntvBES-Count          INTEGER,
            e3FASIntvSES-Count          INTEGER,
            e3FASIntvBPV-Count          INTEGER
        }

        e3FASIntvUnit  OBJECT-TYPE
            SYNTAX  UnitID
            ACCESS  read-only
            STATUS  mandatory
            DESCRIPTION
            "unit 1 to 4."
            ::= { e3FASIntervalEty 1 }

        e3FASIntvPort  OBJECT-TYPE
            SYNTAX  PortID
            ACCESS  read-only
            STATUS  mandatory
            DESCRIPTION
                "E3 Port 1 to 3"
            ::= { e3FASIntervalEty 2 }

        e3FASIntvPeriod  OBJECT-TYPE
            SYNTAX  INTEGER (1..96)
            ACCESS  read-only
            STATUS  mandatory
            DESCRIPTION
                "FAS Interval Period"
            ::= { e3FASIntervalEty 3 }

        e3FASIntvES-Count  OBJECT-TYPE
            SYNTAX  INTEGER
            ACCESS  read-only
            STATUS  mandatory
            DESCRIPTION
                "Error Second"
            ::= { e3FASIntervalEty 4 }

        e3FASIntvUAS-Count  OBJECT-TYPE
            SYNTAX  INTEGER
            ACCESS  read-only
            STATUS  mandatory
            DESCRIPTION
                "Unavailable Second"
            ::= { e3FASIntervalEty 5 }

        e3FASIntvBES-Count  OBJECT-TYPE
            SYNTAX  INTEGER
            ACCESS  read-only
            STATUS  mandatory
            DESCRIPTION
                "Background Error Second"
            ::= { e3FASIntervalEty 6 }

        e3FASIntvSES-Count  OBJECT-TYPE
            SYNTAX  INTEGER
            ACCESS  read-only
            STATUS  mandatory
            DESCRIPTION
                "Severly Error Second"
            ::= { e3FASIntervalEty 7 }

        e3FASIntvBPV-Count  OBJECT-TYPE
            SYNTAX  INTEGER
            ACCESS  read-only
            STATUS  mandatory
            DESCRIPTION
                "Bipolar Violation"
            ::= { e3FASIntervalEty 8 }

--
--  E3 Performance Report FAS Seven Days Table
--

        e3FAS7DaysTab  OBJECT-TYPE
            SYNTAX  SEQUENCE OF E3FAS7DaysEty
            ACCESS  not-accessible
            STATUS  mandatory
            DESCRIPTION
                "Performance report seven days"
            ::= { e3PerformanceReport 15 }

        e3FAS7DaysEty  OBJECT-TYPE
            SYNTAX  E3FAS7DaysEty
            ACCESS  not-accessible
            STATUS  mandatory
            DESCRIPTION
                "An entry in the performance report seven days table"
            INDEX { e3FAS7DaysUnit ,
                    e3FAS7DaysPort ,
                    e3FAS7DaysDayIndex }
            ::= { e3FAS7DaysTab 1 }

        E3FAS7DaysEty ::= SEQUENCE {
            e3FAS7DaysUnit              UnitID,
            e3FAS7DaysPort              PortID,
            e3FAS7DaysDayIndex          INTEGER (1..7),
            e3FAS7DaysDate              DisplayString (SIZE (0..255) ),
            e3FAS7DaysES-Count          INTEGER,
            e3FAS7DaysUAS-Count         INTEGER,
            e3FAS7DaysBES-Count         INTEGER,
            e3FAS7DaysSES-Count         INTEGER,
            e3FAS7DaysBPV-Count         INTEGER
        }

        e3FAS7DaysUnit  OBJECT-TYPE
            SYNTAX  UnitID
            ACCESS  read-only
            STATUS  mandatory
            DESCRIPTION
            "unit 1 to 4."
            ::= { e3FAS7DaysEty 1 }

        e3FAS7DaysPort  OBJECT-TYPE
            SYNTAX  PortID
            ACCESS  read-only
            STATUS  mandatory
            DESCRIPTION
                "E3 Port 1 to 3"
            ::= { e3FAS7DaysEty 2 }

        e3FAS7DaysDayIndex  OBJECT-TYPE
            SYNTAX  INTEGER (1..7)
            ACCESS  read-only
            STATUS  mandatory
            DESCRIPTION
                "FAS Seven Days day index"
            ::= { e3FAS7DaysEty 3 }

        e3FAS7DaysDate  OBJECT-TYPE
            SYNTAX  DisplayString (SIZE (0..255) )
            ACCESS  read-only
            STATUS  mandatory
            DESCRIPTION
                "Seven Days Date"
            ::= { e3FAS7DaysEty 4 }

        e3FAS7DaysES-Count  OBJECT-TYPE
            SYNTAX  INTEGER
            ACCESS  read-only
            STATUS  mandatory
            DESCRIPTION
                "Error Second"
            ::= { e3FAS7DaysEty 5 }

        e3FAS7DaysUAS-Count  OBJECT-TYPE
            SYNTAX  INTEGER
            ACCESS  read-only
            STATUS  mandatory
            DESCRIPTION
                "Unavailable Second"
            ::= { e3FAS7DaysEty 6 }

        e3FAS7DaysBES-Count  OBJECT-TYPE
            SYNTAX  INTEGER
            ACCESS  read-only
            STATUS  mandatory
            DESCRIPTION
                "Background Error Second"
            ::= { e3FAS7DaysEty 7 }

        e3FAS7DaysSES-Count  OBJECT-TYPE
            SYNTAX  INTEGER
            ACCESS  read-only
            STATUS  mandatory
            DESCRIPTION
                "Severly Error Second"
            ::= { e3FAS7DaysEty 8 }

        e3FAS7DaysBPV-Count  OBJECT-TYPE
            SYNTAX  INTEGER
            ACCESS  read-only
            STATUS  mandatory
            DESCRIPTION
                "Bipolar Violation"
            ::= { e3FAS7DaysEty 9 }


--
--  E3 Performance Report FAS Total Table
--

        e3FASTotalTab  OBJECT-TYPE
            SYNTAX  SEQUENCE OF E3FASTotalEty
            ACCESS  not-accessible
            STATUS  mandatory
            DESCRIPTION
                "Performance report Total"
            ::= { e3PerformanceReport 16 }

        e3FASTotalEty  OBJECT-TYPE
            SYNTAX  E3FASTotalEty
            ACCESS  not-accessible
            STATUS  mandatory
            DESCRIPTION
                "An entry in the performance report total table"
            INDEX { e3FASTotalUnit ,
                    e3FASTotalPort }
            ::= { e3FASTotalTab 1 }

        E3FASTotalEty ::= SEQUENCE {
            e3FASTotalUnit              UnitID,
            e3FASTotalPort              PortID,
            e3FASTotalES-Count          INTEGER,
            e3FASTotalUAS-Count         INTEGER,
            e3FASTotalBES-Count         INTEGER,
            e3FASTotalSES-Count         INTEGER,
            e3FASTotalBPV-Count         INTEGER
        }

        e3FASTotalUnit  OBJECT-TYPE
            SYNTAX  UnitID
            ACCESS  read-only
            STATUS  mandatory
            DESCRIPTION
            "unit 1 to 4."
            ::= { e3FASTotalEty 1 }

        e3FASTotalPort  OBJECT-TYPE
            SYNTAX  PortID
            ACCESS  read-only
            STATUS  mandatory
            DESCRIPTION
                "E3 Port 1 to 3"
            ::= { e3FASTotalEty 2 }

        e3FASTotalES-Count  OBJECT-TYPE
            SYNTAX  INTEGER
            ACCESS  read-only
            STATUS  mandatory
            DESCRIPTION
                "Error Second"
            ::= { e3FASTotalEty 3 }

        e3FASTotalUAS-Count  OBJECT-TYPE
            SYNTAX  INTEGER
            ACCESS  read-only
            STATUS  mandatory
            DESCRIPTION
                "Unavailable Second"
            ::= { e3FASTotalEty 4 }

        e3FASTotalBES-Count  OBJECT-TYPE
            SYNTAX  INTEGER
            ACCESS  read-only
            STATUS  mandatory
            DESCRIPTION
                "Background Error Second"
            ::= { e3FASTotalEty 5 }

        e3FASTotalSES-Count  OBJECT-TYPE
            SYNTAX  INTEGER
            ACCESS  read-only
            STATUS  mandatory
            DESCRIPTION
                "Severly Error Second"
            ::= { e3FASTotalEty 6 }

        e3FASTotalBPV-Count  OBJECT-TYPE
            SYNTAX  INTEGER
            ACCESS  read-only
            STATUS  mandatory
            DESCRIPTION
                "Bipolar Violation"
            ::= { e3FASTotalEty 7 }

--
--  E3 Performance Threshold Setup Table
--

        e3PerfThreshSetupTab  OBJECT-TYPE
            SYNTAX  SEQUENCE OF E3PerfThreshSetupEty
            ACCESS  not-accessible
            STATUS  mandatory
            DESCRIPTION
                "Performance threshold setup"
            ::= { e3Performance 2 }

        e3PerfThreshSetupEty  OBJECT-TYPE
            SYNTAX  E3PerfThreshSetupEty
            ACCESS  not-accessible
            STATUS  mandatory
            DESCRIPTION
                "An entry in the performance threshold setup table"
            INDEX { e3PerfTCAUnit ,
                    e3PerfTCAMonitorPoint }
            ::= { e3PerfThreshSetupTab 1 }

        E3PerfThreshSetupEty ::= SEQUENCE {
            e3PerfTCAUnit               UnitID,
            e3PerfTCAMonitorPoint       INTEGER,
            e3PerfTCAEnable             INTEGER,
            e3PerfTCASeverity           Severity,
            e3PerfTCAThreshold          INTEGER
        }

        e3PerfTCAUnit  OBJECT-TYPE
            SYNTAX  UnitID
            ACCESS  read-only
            STATUS  mandatory
            DESCRIPTION
            "unit 1 to 4."
            ::= { e3PerfThreshSetupEty 1 }

        e3PerfTCAMonitorPoint  OBJECT-TYPE
            SYNTAX  INTEGER {
                    hp-bip(1),
                    hp-rei(2),
                    lp-bipv5(3),
                    lp-reiv5(4),
                    lp-bipb3(5),
                    lp-reib3(6),
                    line(7),
                    fas(8)
                }
            ACCESS  read-only
            STATUS  mandatory
            DESCRIPTION
                "TCA monitor point index"
            ::= { e3PerfThreshSetupEty 2 }

        e3PerfTCAEnable  OBJECT-TYPE
            SYNTAX  INTEGER {
                    disable(1),
                    enable(2)
                }
            ACCESS  read-write
            STATUS  mandatory
            DESCRIPTION
                "TCA disable/enable"
            ::= { e3PerfThreshSetupEty 3 }

        e3PerfTCASeverity  OBJECT-TYPE
            SYNTAX  Severity
            ACCESS  read-write
            STATUS  mandatory
            DESCRIPTION
                "TCA Severity"
            ::= { e3PerfThreshSetupEty 4 }

        e3PerfTCAThreshold  OBJECT-TYPE
            SYNTAX  INTEGER (1..99999)
            ACCESS  read-write
            STATUS  mandatory
            DESCRIPTION
                "TCA threshold"
            ::= { e3PerfThreshSetupEty 5 }

--
--  E3 Performance Control Setup Table
--

        e3PerfControlTab  OBJECT-TYPE
            SYNTAX  SEQUENCE OF E3PerfControlEty
            ACCESS  not-accessible
            STATUS  mandatory
            DESCRIPTION
                "Performance control"
            ::= { e3Performance 3 }

        e3PerfControlEty  OBJECT-TYPE
            SYNTAX  E3PerfControlEty
            ACCESS  not-accessible
            STATUS  mandatory
            DESCRIPTION
                "An entry in the performance control table"
            INDEX { e3PerfCtrlUnit }
            ::= { e3PerfControlTab 1 }

        E3PerfControlEty ::= SEQUENCE {
            e3PerfCtrlUnit              UnitID,
            e3PerfCtrlClearPerf         INTEGER
        }

        e3PerfCtrlUnit  OBJECT-TYPE
            SYNTAX  UnitID
            ACCESS  read-only
            STATUS  mandatory
            DESCRIPTION
            "unit 1 to 4."
            ::= { e3PerfControlEty 1 }

        e3PerfCtrlClearPerf  OBJECT-TYPE
            SYNTAX  INTEGER {
                    none(0),
                    clear-all-port(1),
                    clear-port1(2),
                    clear-port2(3),
                    clear-port3(4)
                }
            ACCESS  read-write
            STATUS  mandatory
            DESCRIPTION
                "Clear performance data"
            ::= { e3PerfControlEty 2 }

--
-- E3 SNCP/UPSR APS Table
--

        e3SncpApsTab  OBJECT-TYPE
            SYNTAX  SEQUENCE OF  E3SncpApsEty
            ACCESS  not-accessible
            STATUS  mandatory
            DESCRIPTION
                "E3 SNCP/UPSR APS table "
            ::= { e3-card 5 }

        e3SncpApsEty  OBJECT-TYPE
            SYNTAX  E3SncpApsEty
            ACCESS  not-accessible
            STATUS  mandatory
            DESCRIPTION
                "E3 SNCP/UPSR APS entry"
            INDEX { e3SncpUnit , e3SncpPort , e3SncpChannel }
            ::= { e3SncpApsTab 1 }

        E3SncpApsEty ::= SEQUENCE {
            e3SncpUnit                  UnitID,
            e3SncpPort                  PortID,
            e3SncpChannel               ChannelNum,
            e3SncpCurrentPathSlot       XcSlot,
            e3SncpCurrentPathPort       PortID,
            e3SncpPrimaryPathSlot       XcSlot,
            e3SncpPrimaryPathPort       PortID,
            e3SncpPPType                XcType,
            e3SncpCmd                   SncpUserCmd
        }

        e3SncpUnit  OBJECT-TYPE
            SYNTAX  UnitID
            ACCESS  read-only
            STATUS  mandatory
            DESCRIPTION
            "unit 1 to 4."
            ::= { e3SncpApsEty 1 }

        e3SncpPort  OBJECT-TYPE
            SYNTAX  PortID
            ACCESS  read-only
            STATUS  mandatory
            DESCRIPTION
                "PORT #1~#3"
            ::= { e3SncpApsEty 2 }

        e3SncpChannel  OBJECT-TYPE
            SYNTAX  ChannelNum
            ACCESS  read-only
            STATUS  mandatory
            DESCRIPTION
                "CHANNEL #1~#28"
            ::= { e3SncpApsEty 3 }

        e3SncpCurrentPathSlot  OBJECT-TYPE
            SYNTAX  XcSlot
            ACCESS  read-only
            STATUS  mandatory
            DESCRIPTION
                "SNCP/UPSR current path"
            ::= { e3SncpApsEty 4 }

        e3SncpCurrentPathPort  OBJECT-TYPE
            SYNTAX  PortID
            ACCESS  read-only
            STATUS  mandatory
            DESCRIPTION
                "SNCP/UPSR current path"
            ::= { e3SncpApsEty 5 }

        e3SncpPrimaryPathSlot  OBJECT-TYPE
            SYNTAX  XcSlot
            ACCESS  read-only
            STATUS  mandatory
            DESCRIPTION
                "SNCP/UPSR primary path"
            ::= { e3SncpApsEty 6 }

        e3SncpPrimaryPathPort  OBJECT-TYPE
            SYNTAX  PortID
            ACCESS  read-only
            STATUS  mandatory
            DESCRIPTION
                "SNCP/UPSR primary path"
            ::= { e3SncpApsEty 7 }

        e3SncpPPType  OBJECT-TYPE
            SYNTAX  XcType
            ACCESS  read-only
            STATUS  mandatory
            DESCRIPTION
                "SNCP/UPSR path protection type"
            ::= { e3SncpApsEty 8 }

        e3SncpCmd  OBJECT-TYPE
            SYNTAX  SncpUserCmd
            ACCESS  read-write
            STATUS  mandatory
            DESCRIPTION
                "SNCP/UPSR APS command"
            ::= { e3SncpApsEty 9 }

--
-- E3 LED Status Table
--

        e3LedStatusTab OBJECT-TYPE
            SYNTAX  SEQUENCE OF E3LedStatusEty
            ACCESS  not-accessible
            STATUS  mandatory
            DESCRIPTION
                "Led Status"
            ::= { e3-card 6 }

        e3LedStatusEty  OBJECT-TYPE
            SYNTAX  E3LedStatusEty
            ACCESS  not-accessible
            STATUS  mandatory
            DESCRIPTION
                "An entry in the led status table"
            INDEX { e3LedStsUnit }
            ::= { e3LedStatusTab 1 }

        E3LedStatusEty ::= SEQUENCE {
            e3LedStsUnit                UnitID,
            e3LedStsActiveLED           LedStatusType,
            e3LedStsTestLED             LedStatusType,
            e3LedStsAlarmLED            LedStatusType,
            e3LedStsPort1LOSLED         LedStatusType,
            e3LedStsPort2LOSLED         LedStatusType,
            e3LedStsPort3LOSLED         LedStatusType
        }

        e3LedStsUnit  OBJECT-TYPE
            SYNTAX  UnitID
            ACCESS  read-only
            STATUS  mandatory
            DESCRIPTION
            "unit 1 to 4."
            ::= { e3LedStatusEty 1 }

        e3LedStsActiveLED  OBJECT-TYPE
            SYNTAX  LedStatusType
            ACCESS  read-only
            STATUS  mandatory
            DESCRIPTION
                "Active Led Status"
            ::= { e3LedStatusEty 2 }

        e3LedStsTestLED  OBJECT-TYPE
            SYNTAX  LedStatusType
            ACCESS  read-only
            STATUS  mandatory
            DESCRIPTION
                "Test Led Status"
            ::= { e3LedStatusEty 3 }

        e3LedStsAlarmLED  OBJECT-TYPE
            SYNTAX  LedStatusType
            ACCESS  read-only
            STATUS  mandatory
            DESCRIPTION
                "Alarm Led Status"
            ::= { e3LedStatusEty 4 }

        e3LedStsPort1LOSLED  OBJECT-TYPE
            SYNTAX  LedStatusType
            ACCESS  read-only
            STATUS  mandatory
            DESCRIPTION
                "E3 Port 1 LOS Led Status"
            ::= { e3LedStatusEty 5 }

        e3LedStsPort2LOSLED  OBJECT-TYPE
            SYNTAX  LedStatusType
            ACCESS  read-only
            STATUS  mandatory
            DESCRIPTION
                "E3 Port 2 LOS Led Status"
            ::= { e3LedStatusEty 6 }

        e3LedStsPort3LOSLED  OBJECT-TYPE
            SYNTAX  LedStatusType
            ACCESS  read-only
            STATUS  mandatory
            DESCRIPTION
                "E3 Port 3 LOS Led Status"
            ::= { e3LedStatusEty 7 }

--
-- E3 Command Control Table
--

        e3CommandControlTab  OBJECT-TYPE
            SYNTAX  SEQUENCE OF E3CommandControlEty
            ACCESS  not-accessible
            STATUS  mandatory
            DESCRIPTION
                "Command control"
            ::= { e3-card 7 }

        e3CommandControlEty  OBJECT-TYPE
            SYNTAX  E3CommandControlEty
            ACCESS  not-accessible
            STATUS  mandatory
            DESCRIPTION
                "An entry in the command control table"
            INDEX { e3CmdCtrlUnit }
            ::= { e3CommandControlTab 1 }

        E3CommandControlEty ::= SEQUENCE {
            e3CmdCtrlUnit               UnitID,
            e3CmdCtrlUnitReset          INTEGER,
            e3CmdCtrlUnitLoadDefault    INTEGER
        }

        e3CmdCtrlUnit  OBJECT-TYPE
            SYNTAX  UnitID
            ACCESS  read-only
            STATUS  mandatory
            DESCRIPTION
            "unit 1 to 4."
            ::= { e3CommandControlEty 1 }

        e3CmdCtrlUnitReset  OBJECT-TYPE
            SYNTAX  INTEGER {
                    warm(1),
                    cold(2)
                }
            ACCESS  read-write
            STATUS  mandatory
            DESCRIPTION
                "Unit reset"
            ::= { e3CommandControlEty 2 }

        e3CmdCtrlUnitLoadDefault  OBJECT-TYPE
            SYNTAX  INTEGER {
                    load-default(1)
                }
            ACCESS  read-write
            STATUS  mandatory
            DESCRIPTION
                "Unit load default"
            ::= { e3CommandControlEty 3 }

--
--  E3 XC Display Table
--
        e3XcDisplayTab  OBJECT-TYPE
            SYNTAX  SEQUENCE OF  E3XcDisplayEty
            ACCESS  not-accessible
            STATUS  mandatory
            DESCRIPTION
                "E3 xc display table "
            ::= { e3-card 8 }

        e3XcDisplayEty  OBJECT-TYPE
            SYNTAX  E3XcDisplayEty
            ACCESS  not-accessible
            STATUS  mandatory
            DESCRIPTION
                "E3 xc display entry"
            INDEX { e3XcDispMapIndex ,
                    e3XcDispUnitIndex ,
                    e3XcDispPortIndex ,
                    e3XcDispChannelIndex }
            ::= { e3XcDisplayTab 1 }

        E3XcDisplayEty ::= SEQUENCE {
            e3XcDispMapIndex            XcMap,
            e3XcDispUnitIndex           UnitID,
            e3XcDispPortIndex           PortID,
            e3XcDispChannelIndex        ChannelNum,
            e3XcDispSrcSlotType         NewXcModel,
            e3XcDispSrcSlot             XcSlot,
            e3XcDispSrcPort             PortID,
            e3XcDispSrcChannel          ChannelNum,
            e3XcDispSrcAug1Sts3Path     Aug1Sts3Num,
            e3XcDispSrcVc3Sts1Path      Vc3Sts1Num,
            e3XcDispSrcVc1xVtxPath      Vc1xVtxNum,
            e3XcDispXcGranularity       INTEGER,
            e3XcDispXcType              XcType
        }

        e3XcDispMapIndex  OBJECT-TYPE
            SYNTAX  XcMap
            ACCESS  read-only
            STATUS  mandatory
            DESCRIPTION
                "xc map index"
            ::= { e3XcDisplayEty 1 }

        e3XcDispUnitIndex  OBJECT-TYPE
            SYNTAX  UnitID
            ACCESS  read-only
            STATUS  mandatory
            DESCRIPTION
            "unit 1 to 4."
            ::= { e3XcDisplayEty 2 }

        e3XcDispPortIndex  OBJECT-TYPE
            SYNTAX  PortID
            ACCESS  read-only
            STATUS  mandatory
            DESCRIPTION
                "PORT index"
            ::= { e3XcDisplayEty 3 }

        e3XcDispChannelIndex  OBJECT-TYPE
            SYNTAX  ChannelNum
            ACCESS  read-only
            STATUS  mandatory
            DESCRIPTION
                "CHANNEL index"
            ::= { e3XcDisplayEty 4 }

        e3XcDispSrcSlotType  OBJECT-TYPE
            SYNTAX  NewXcModel
            ACCESS  read-only
            STATUS  mandatory
            DESCRIPTION
                " Xc src Unit Type"
            ::= { e3XcDisplayEty 5 }

        e3XcDispSrcSlot  OBJECT-TYPE
            SYNTAX  XcSlot
            ACCESS  read-only
            STATUS  mandatory
            DESCRIPTION
                "Xc src Unit "
            ::= { e3XcDisplayEty 6 }

        e3XcDispSrcPort  OBJECT-TYPE
            SYNTAX  PortID
            ACCESS  read-only
            STATUS  mandatory
            DESCRIPTION
                "Xc src port "
            ::= { e3XcDisplayEty 7 }

        e3XcDispSrcChannel  OBJECT-TYPE
            SYNTAX  ChannelNum
            ACCESS  read-only
            STATUS  mandatory
            DESCRIPTION
                "Xc src channel "
            ::= { e3XcDisplayEty 8 }

        e3XcDispSrcAug1Sts3Path  OBJECT-TYPE
            SYNTAX  Aug1Sts3Num
            ACCESS  read-only
            STATUS  mandatory
            DESCRIPTION
                "Xc src AUG1/STS3 path"
            ::= { e3XcDisplayEty 9 }

        e3XcDispSrcVc3Sts1Path  OBJECT-TYPE
            SYNTAX  Vc3Sts1Num
            ACCESS  read-only
            STATUS  mandatory
            DESCRIPTION
                "Xc src VC3/STS1 path"
            ::= { e3XcDisplayEty 10 }

        e3XcDispSrcVc1xVtxPath  OBJECT-TYPE
            SYNTAX  Vc1xVtxNum
            ACCESS  read-only
            STATUS  mandatory
            DESCRIPTION
                "Xc src VC1x/VTx path"
            ::= { e3XcDisplayEty 11 }

        e3XcDispXcGranularity  OBJECT-TYPE
            SYNTAX  INTEGER {
                    tu3(2),
                    au3-sts1(3),
                    tu11-vt15(4),
                    tu12-vt2(5),
                    vc4-sts3c(6),
                    not-available(100)
                }
            ACCESS  read-only
            STATUS  mandatory
            DESCRIPTION
                "Xc granularity"
            ::= { e3XcDisplayEty 12 }

        e3XcDispXcType  OBJECT-TYPE
            SYNTAX  XcType
            ACCESS  read-only
            STATUS  mandatory
            DESCRIPTION
                "Xc type"
            ::= { e3XcDisplayEty 13 }
--2011-3-18 elvis below
--
--  New E3 XC Display Table
--
        new-e3XcDisplayTab  OBJECT-TYPE
            SYNTAX  SEQUENCE OF  NewE3XcDisplayEty
            ACCESS  not-accessible
            STATUS  mandatory
            DESCRIPTION
                "E3 xc display table "
            ::= { e3-card 9 }

        new-e3XcDisplayEty  OBJECT-TYPE
            SYNTAX  NewE3XcDisplayEty
            ACCESS  not-accessible
            STATUS  mandatory
            DESCRIPTION
                "E3 xc display entry"
            INDEX { new-e3XcDispMapIndex ,
                    new-e3XcDispUnitIndex ,
                    new-e3XcDispPortIndex ,
                    new-e3XcDispChannelIndex }
            ::= { new-e3XcDisplayTab 1 }

        NewE3XcDisplayEty ::= SEQUENCE {
            new-e3XcDispMapIndex        XcMap,
            new-e3XcDispUnitIndex       UnitID,
            new-e3XcDispPortIndex       PortID,
            new-e3XcDispChannelIndex    ChannelNum,
            new-e3XcDispPriSlotType     NewXcModel,
            new-e3XcDispPriSlot         XcSlot,
            new-e3XcDispPriPort         PortID,
            new-e3XcDispPriChannel      ChannelNum,
            new-e3XcDispPriAug1Sts3Path Aug1Sts3Num,
            new-e3XcDispPriVc3Sts1Path  Vc3Sts1Num,
            new-e3XcDispPriVc1xVtxPath  Vc1xVtxNum,
            new-e3XcDispXcGranularity   INTEGER,
            new-e3XcDispXcType          XcType,
            new-e3XcDispSecSlotType     NewXcModel,
            new-e3XcDispSecSlot         XcSlot,
            new-e3XcDispSecPort         PortID,
            new-e3XcDispSecChannel      ChannelNum,
            new-e3XcDispSecAug1Sts3Path Aug1Sts3Num,
            new-e3XcDispSecVc3Sts1Path  Vc3Sts1Num,
            new-e3XcDispSecVc1xVtxPath  Vc1xVtxNum
        }

        new-e3XcDispMapIndex  OBJECT-TYPE
            SYNTAX  XcMap
            ACCESS  read-only
            STATUS  mandatory
            DESCRIPTION
                "xc map index"
            ::= { new-e3XcDisplayEty 1 }

        new-e3XcDispUnitIndex  OBJECT-TYPE
            SYNTAX  UnitID
            ACCESS  read-only
            STATUS  mandatory
            DESCRIPTION
                "unit 1 to 8, total 8 units."
            ::= { new-e3XcDisplayEty 2 }

        new-e3XcDispPortIndex  OBJECT-TYPE
            SYNTAX  PortID
            ACCESS  read-only
            STATUS  mandatory
            DESCRIPTION
                "PORT index"
            ::= { new-e3XcDisplayEty 3 }

        new-e3XcDispChannelIndex  OBJECT-TYPE
            SYNTAX  ChannelNum
            ACCESS  read-only
            STATUS  mandatory
            DESCRIPTION
                "CHANNEL index"
            ::= { new-e3XcDisplayEty 4 }

        new-e3XcDispPriSlotType  OBJECT-TYPE
            SYNTAX  NewXcModel
            ACCESS  read-only
            STATUS  mandatory
            DESCRIPTION
                " Xc Primary Unit Type"
            ::= { new-e3XcDisplayEty 5 }

        new-e3XcDispPriSlot  OBJECT-TYPE
            SYNTAX  XcSlot
            ACCESS  read-only
            STATUS  mandatory
            DESCRIPTION
                "Xc Primary Unit "
            ::= { new-e3XcDisplayEty 6 }

        new-e3XcDispPriPort  OBJECT-TYPE
            SYNTAX  PortID
            ACCESS  read-only
            STATUS  mandatory
            DESCRIPTION
                "Xc Primary port "
            ::= { new-e3XcDisplayEty 7 }

        new-e3XcDispPriChannel  OBJECT-TYPE
            SYNTAX  ChannelNum
            ACCESS  read-only
            STATUS  mandatory
            DESCRIPTION
                "Xc Primary channel "
            ::= { new-e3XcDisplayEty 8 }

        new-e3XcDispPriAug1Sts3Path  OBJECT-TYPE
            SYNTAX  Aug1Sts3Num
            ACCESS  read-only
            STATUS  mandatory
            DESCRIPTION
                "Xc Primary AUG1/STS3 path"
            ::= { new-e3XcDisplayEty 9 }

        new-e3XcDispPriVc3Sts1Path  OBJECT-TYPE
            SYNTAX  Vc3Sts1Num
            ACCESS  read-only
            STATUS  mandatory
            DESCRIPTION
                "Xc Primary VC3/STS1 path"
            ::= { new-e3XcDisplayEty 10 }

        new-e3XcDispPriVc1xVtxPath  OBJECT-TYPE
            SYNTAX  Vc1xVtxNum
            ACCESS  read-only
            STATUS  mandatory
            DESCRIPTION
                "Xc Primary VC1x/VTx path"
            ::= { new-e3XcDisplayEty 11 }

        new-e3XcDispXcGranularity  OBJECT-TYPE
            SYNTAX  INTEGER {
                    tu3(2),
                    au3-sts1(3),
                    tu11-vt15(4),
                    tu12-vt2(5),
                    vc4-sts3c(6),
                    not-available(100)
                }
            ACCESS  read-only
            STATUS  mandatory
            DESCRIPTION
                "Xc granularity"
            ::= { new-e3XcDisplayEty 12 }

        new-e3XcDispXcType  OBJECT-TYPE
            SYNTAX  XcType
            ACCESS  read-only
            STATUS  mandatory
            DESCRIPTION
                "Xc type"
            ::= { new-e3XcDisplayEty 13 }

        new-e3XcDispSecSlotType  OBJECT-TYPE
            SYNTAX  NewXcModel
            ACCESS  read-only
            STATUS  mandatory
            DESCRIPTION
                " Xc Secondary Unit Type"
            ::= { new-e3XcDisplayEty 14 }

        new-e3XcDispSecSlot  OBJECT-TYPE
            SYNTAX  XcSlot
            ACCESS  read-only
            STATUS  mandatory
            DESCRIPTION
                "Xc Secondary Unit "
            ::= { new-e3XcDisplayEty 15 }

        new-e3XcDispSecPort  OBJECT-TYPE
            SYNTAX  PortID
            ACCESS  read-only
            STATUS  mandatory
            DESCRIPTION
                "Xc Secondary port "
            ::= { new-e3XcDisplayEty 16 }

        new-e3XcDispSecChannel  OBJECT-TYPE
            SYNTAX  ChannelNum
            ACCESS  read-only
            STATUS  mandatory
            DESCRIPTION
                "Xc Secondary channel "
            ::= { new-e3XcDisplayEty 17 }

        new-e3XcDispSecAug1Sts3Path  OBJECT-TYPE
            SYNTAX  Aug1Sts3Num
            ACCESS  read-only
            STATUS  mandatory
            DESCRIPTION
                "Xc Secondary AUG1/STS3 path"
            ::= { new-e3XcDisplayEty 18 }

        new-e3XcDispSecVc3Sts1Path  OBJECT-TYPE
            SYNTAX  Vc3Sts1Num
            ACCESS  read-only
            STATUS  mandatory
            DESCRIPTION
                "Xc Secondary VC3/STS1 path"
            ::= { new-e3XcDisplayEty 19 }

        new-e3XcDispSecVc1xVtxPath  OBJECT-TYPE
            SYNTAX  Vc1xVtxNum
            ACCESS  read-only
            STATUS  mandatory
            DESCRIPTION
                "Xc Secondary VC1x/VTx path"
            ::= { new-e3XcDisplayEty 20 }

--
-- New E3 SNCP/UPSR APS Table
--

        new-e3SncpApsTab  OBJECT-TYPE
            SYNTAX  SEQUENCE OF  NewE3SncpApsEty
            ACCESS  not-accessible
            STATUS  mandatory
            DESCRIPTION
                "E3 SNCP/UPSR APS table "
            ::= { e3-card 10 }

        new-e3SncpApsEty  OBJECT-TYPE
            SYNTAX  NewE3SncpApsEty
            ACCESS  not-accessible
            STATUS  mandatory
            DESCRIPTION
                "E3 SNCP/UPSR APS entry"
            INDEX { new-e3SncpUnit , new-e3SncpPort , new-e3SncpChannel }
            ::= { new-e3SncpApsTab 1 }

        NewE3SncpApsEty ::= SEQUENCE {
            new-e3SncpUnit              UnitID,
            new-e3SncpPort              PortID,
            new-e3SncpChannel           ChannelNum,
            new-e3SncpCurrSlot          XcSlot,
            new-e3SncpCurrPort          PortID,
            new-e3SncpCurrChannel       ChannelNum,
            new-e3SncpCurrAug1Sts3Path  Aug1Sts3Num,
            new-e3SncpCurrVc3Sts1Path   Vc3Sts1Num,
            new-e3SncpCurrVc1xVtxPath   Vc1xVtxNum,
            new-e3SncpPPType            XcType,
            new-e3SncpCmd               SncpUserCmd,
            new-e3SncpRevertive         INTEGER
        }

        new-e3SncpUnit  OBJECT-TYPE
            SYNTAX  UnitID
            ACCESS  read-only
            STATUS  mandatory
            DESCRIPTION
                "unit 1 to 8, total 8 units."
            ::= { new-e3SncpApsEty 1 }

        new-e3SncpPort  OBJECT-TYPE
            SYNTAX  PortID
            ACCESS  read-only
            STATUS  mandatory
            DESCRIPTION
                "PORT #1~#3"
            ::= { new-e3SncpApsEty 2 }

        new-e3SncpChannel  OBJECT-TYPE
            SYNTAX  ChannelNum
            ACCESS  read-only
            STATUS  mandatory
            DESCRIPTION
                "CHANNEL #1~#28"
            ::= { new-e3SncpApsEty 3 }

        new-e3SncpCurrSlot  OBJECT-TYPE
            SYNTAX  XcSlot
            ACCESS  read-only
            STATUS  mandatory
            DESCRIPTION
                "SNCP/UPSR current slot"
            ::= { new-e3SncpApsEty 4 }

        new-e3SncpCurrPort  OBJECT-TYPE
            SYNTAX  PortID
            ACCESS  read-only
            STATUS  mandatory
            DESCRIPTION
                "SNCP/UPSR current port"
            ::= { new-e3SncpApsEty 5 }

        new-e3SncpCurrChannel  OBJECT-TYPE
            SYNTAX  ChannelNum
            ACCESS  read-only
            STATUS  mandatory
            DESCRIPTION
                "SNCP/UPSR current channel"
            ::= { new-e3SncpApsEty 6 }

        new-e3SncpCurrAug1Sts3Path  OBJECT-TYPE
            SYNTAX  Aug1Sts3Num
            ACCESS  read-only
            STATUS  mandatory
            DESCRIPTION
                "SNCP/UPSR current Aug1/Sts3"
            ::= { new-e3SncpApsEty 7 }

        new-e3SncpCurrVc3Sts1Path  OBJECT-TYPE
            SYNTAX  Vc3Sts1Num
            ACCESS  read-only
            STATUS  mandatory
            DESCRIPTION
                "SNCP/UPSR current Vc3/Sts1"
            ::= { new-e3SncpApsEty 8 }

        new-e3SncpCurrVc1xVtxPath  OBJECT-TYPE
            SYNTAX  Vc1xVtxNum
            ACCESS  read-only
            STATUS  mandatory
            DESCRIPTION
                "SNCP/UPSR current Vc1x/Vtx"
            ::= { new-e3SncpApsEty 9 }

        new-e3SncpPPType  OBJECT-TYPE
            SYNTAX  XcType
            ACCESS  read-only
            STATUS  mandatory
            DESCRIPTION
                "SNCP/UPSR path protection type"
            ::= { new-e3SncpApsEty 10 }

        new-e3SncpCmd  OBJECT-TYPE
            SYNTAX  SncpUserCmd
            ACCESS  read-write
            STATUS  mandatory
            DESCRIPTION
                "SNCP/UPSR APS command"
            ::= { new-e3SncpApsEty 11 }

        new-e3SncpRevertive  OBJECT-TYPE
            SYNTAX  INTEGER {
                    non-revertive(1),
                    revertive(2)
                }
            ACCESS  read-write
            STATUS  mandatory
            DESCRIPTION
                "SNCP/UPSR revertive or non-revertive"
            ::= { new-e3SncpApsEty 12 }

        e3TotalCard   OBJECT-TYPE
            SYNTAX  INTEGER
            ACCESS  read-only
            STATUS  mandatory
            DESCRIPTION
                "Total cards of E3"
            ::= { e3-card 100 }


--2011-3-18 elvis above
--======================================================================--
--======================================================================--
--  t3-card MIB
--======================================================================--
--======================================================================--
--
--  T3 Config
--

    t3Config           OBJECT IDENTIFIER ::= { t3-card 1 }


--
--  T3 Channel Line Interface Setup Table
--

        t3ChLineIntfSetupTab  OBJECT-TYPE
            SYNTAX  SEQUENCE OF T3ChLineIntfSetupEty
            ACCESS  not-accessible
            STATUS  mandatory
            DESCRIPTION
                "Channel line interface setup table"
            ::= { t3Config 1 }

        t3ChLineIntfSetupEty  OBJECT-TYPE
            SYNTAX  T3ChLineIntfSetupEty
            ACCESS  not-accessible
            STATUS  mandatory
            DESCRIPTION
                "An entry in the channel line interface setup table"
            INDEX { t3ChLineIntfUnit ,
                    t3ChLineIntfPort }
            ::= { t3ChLineIntfSetupTab 1 }

        T3ChLineIntfSetupEty ::= SEQUENCE {
            t3ChLineIntfUnit            UnitID,
            t3ChLineIntfPort            PortID,
            t3ChLineIntfCoding          INTEGER,
            t3ChLineIntfType            INTEGER,
            t3ChLineIntfLength          INTEGER
        }

        t3ChLineIntfUnit  OBJECT-TYPE
            SYNTAX  UnitID
            ACCESS  read-only
            STATUS  mandatory
            DESCRIPTION
            "unit 1 to 4."
            ::= { t3ChLineIntfSetupEty 1 }

        t3ChLineIntfPort  OBJECT-TYPE
            SYNTAX  PortID
            ACCESS  read-only
            STATUS  mandatory
            DESCRIPTION
                "T3 Port 1 to 3"
            ::= { t3ChLineIntfSetupEty 2 }

        t3ChLineIntfCoding  OBJECT-TYPE
            SYNTAX  INTEGER{
                    b3zs(1)
                }
            ACCESS  read-only
            STATUS  mandatory
            DESCRIPTION
                "T3 line coding mode"
            ::= { t3ChLineIntfSetupEty 3 }

        t3ChLineIntfType  OBJECT-TYPE
            SYNTAX  INTEGER{
                    unframe(1),
                    c-bit(2),
                    m13-t1(3),
                    m13-e1(4),
                    c-bit-t1(5),
                    c-bit-e1(6)
                }
            ACCESS  read-write
            STATUS  mandatory
            DESCRIPTION
                "T3 line type"
            ::= { t3ChLineIntfSetupEty 4 }

        t3ChLineIntfLength  OBJECT-TYPE
            SYNTAX  INTEGER{
                    ft0-225(1),
                    ft225-450(2)
                }
            ACCESS  read-write
            STATUS  mandatory
            DESCRIPTION
                "T3 Transmit Length"
            ::= { t3ChLineIntfSetupEty 5 }


--
--  T3 Trace Message & Signal Label Setup Table
--
    t3OverheadSetup           OBJECT IDENTIFIER ::= { t3Config 2 }

--
-- T3 High Order Trace Message & Signal Label Setup Table
--

        t3HoSTSOverheadSetupTab  OBJECT-TYPE
            SYNTAX  SEQUENCE OF T3HoSTSOverheadSetupEty
            ACCESS  not-accessible
            STATUS  mandatory
            DESCRIPTION
                "High order Trace message & Signal label setup table"
            ::= { t3OverheadSetup 1 }

        t3HoSTSOverheadSetupEty  OBJECT-TYPE
            SYNTAX  T3HoSTSOverheadSetupEty
            ACCESS  not-accessible
            STATUS  mandatory
            DESCRIPTION
                "An entry in the trace message & signal label setup table"
            INDEX { t3HoSTSOverheadUnit ,
                    t3HoSTSOverheadPort }
            ::= { t3HoSTSOverheadSetupTab 1 }

        T3HoSTSOverheadSetupEty ::= SEQUENCE {
            t3HoSTSOverheadUnit         UnitID,
            t3HoSTSOverheadPort         PortID,
            t3HoSTSOverheadLength       MsgLen,
            t3HoSTSOverheadExpMsg       DisplayString(SIZE(0..64)),
            t3HoSTSOverheadTxMsg        DisplayString(SIZE(0..64)),
            t3HoSTSOverheadRxMsg        DisplayString(SIZE(0..64)),
            t3HoSTSOverheadEPSL         INTEGER,
            t3HoSTSOverheadExpMsg1B     INTEGER(0..255),
            t3HoSTSOverheadTxMsg1B      INTEGER(0..255),
            t3HoSTSOverheadRxMsg1B      INTEGER(0..255),
            t3HoSTSOverheadTxPSL        INTEGER,
            t3HoSTSOverheadRxPSL        INTEGER
        }

        t3HoSTSOverheadUnit  OBJECT-TYPE
            SYNTAX  UnitID
            ACCESS  read-only
            STATUS  mandatory
            DESCRIPTION
            "unit 1 to 4."
            ::= { t3HoSTSOverheadSetupEty 1 }

        t3HoSTSOverheadPort  OBJECT-TYPE
            SYNTAX  PortID
            ACCESS  read-only
            STATUS  mandatory
            DESCRIPTION
                "T3 Port 1 to 3"
            ::= { t3HoSTSOverheadSetupEty 2 }

        t3HoSTSOverheadLength  OBJECT-TYPE
            SYNTAX  MsgLen
            ACCESS  read-write
            STATUS  mandatory
            DESCRIPTION
                "message length"
            ::= { t3HoSTSOverheadSetupEty 3 }

        t3HoSTSOverheadExpMsg OBJECT-TYPE
            SYNTAX  DisplayString (SIZE(0..64))
            ACCESS  read-write
            STATUS  mandatory
            DESCRIPTION
                "The expected message"
            ::= { t3HoSTSOverheadSetupEty 4 }

        t3HoSTSOverheadTxMsg OBJECT-TYPE
            SYNTAX  DisplayString (SIZE(0..64))
            ACCESS  read-write
            STATUS  mandatory
            DESCRIPTION
                "The tx message"
            ::= { t3HoSTSOverheadSetupEty 5 }

        t3HoSTSOverheadRxMsg OBJECT-TYPE
            SYNTAX  DisplayString (SIZE(0..64))
            ACCESS  read-only
            STATUS  mandatory
            DESCRIPTION
                "The rx message"
            ::= { t3HoSTSOverheadSetupEty 6 }

        t3HoSTSOverheadEPSL  OBJECT-TYPE
            SYNTAX  INTEGER(0..255)
            ACCESS  read-write
            STATUS  mandatory
            DESCRIPTION
                "The expected Path Signal Label"
            ::= { t3HoSTSOverheadSetupEty 7 }

        t3HoSTSOverheadExpMsg1B OBJECT-TYPE
            SYNTAX  INTEGER(0..255)
            ACCESS  read-write
            STATUS  mandatory
            DESCRIPTION
                "The expected message (1byte)"
            ::= { t3HoSTSOverheadSetupEty 8 }

        t3HoSTSOverheadTxMsg1B OBJECT-TYPE
            SYNTAX  INTEGER(0..255)
            ACCESS  read-write
            STATUS  mandatory
            DESCRIPTION
                "The tx message (1byte)"
            ::= { t3HoSTSOverheadSetupEty 9 }

        t3HoSTSOverheadRxMsg1B OBJECT-TYPE
            SYNTAX  INTEGER(0..255)
            ACCESS  read-only
            STATUS  mandatory
            DESCRIPTION
                "The rx message (1byte)"
            ::= { t3HoSTSOverheadSetupEty 10 }

        t3HoSTSOverheadTxPSL  OBJECT-TYPE
            SYNTAX  INTEGER(0..255)
            ACCESS  read-write
            STATUS  mandatory
            DESCRIPTION
                "The Tx Path Signal Label"
            ::= { t3HoSTSOverheadSetupEty 11 }

        t3HoSTSOverheadRxPSL  OBJECT-TYPE
            SYNTAX  INTEGER(0..255)
            ACCESS  read-only
            STATUS  mandatory
            DESCRIPTION
                "The Rx Path Signal Label"
            ::= { t3HoSTSOverheadSetupEty 12 }

--
-- T3 Low Order Trace Message & Signal Label Setup Table
--

        t3LoVTOverheadSetupTab  OBJECT-TYPE
            SYNTAX  SEQUENCE OF T3LoVTOverheadSetupEty
            ACCESS  not-accessible
            STATUS  mandatory
            DESCRIPTION
                "Low Order Trace message & Signal label setup table"
            ::= { t3OverheadSetup 2 }

        t3LoVTOverheadSetupEty  OBJECT-TYPE
            SYNTAX  T3LoVTOverheadSetupEty
            ACCESS  not-accessible
            STATUS  mandatory
            DESCRIPTION
                "An entry in the trace message & signal label setup table"
            INDEX { t3LoVTOverheadUnit ,
                    t3LoVTOverheadPort ,
                    t3LoVTOverheadChannel }
            ::= { t3LoVTOverheadSetupTab 1 }

        T3LoVTOverheadSetupEty ::= SEQUENCE {
            t3LoVTOverheadUnit          UnitID,
            t3LoVTOverheadPort          PortID,
            t3LoVTOverheadChannel       ChannelNum,
            t3LoVTOverheadLength        INTEGER,
            t3LoVTOverheadExpMsg        DisplayString(SIZE(0..64)),
            t3LoVTOverheadTxMsg         DisplayString(SIZE(0..64)),
            t3LoVTOverheadRxMsg         DisplayString(SIZE(0..64)),
            t3LoVTOverheadEPSL          INTEGER,
            t3LoVTOverheadTxPSL         INTEGER,
            t3LoVTOverheadRxPSL         INTEGER
        }

        t3LoVTOverheadUnit  OBJECT-TYPE
            SYNTAX  UnitID
            ACCESS  read-only
            STATUS  mandatory
            DESCRIPTION
            "unit 1 to 4."
            ::= { t3LoVTOverheadSetupEty 1 }

        t3LoVTOverheadPort  OBJECT-TYPE
            SYNTAX  PortID
            ACCESS  read-only
            STATUS  mandatory
            DESCRIPTION
                "T3 Port 1 to 3"
            ::= { t3LoVTOverheadSetupEty 2 }

        t3LoVTOverheadChannel  OBJECT-TYPE
            SYNTAX  ChannelNum
            ACCESS  read-only
            STATUS  mandatory
            DESCRIPTION
                "T3 Channel 1 to 28"
            ::= { t3LoVTOverheadSetupEty 3 }

        t3LoVTOverheadLength  OBJECT-TYPE
            SYNTAX  INTEGER{
                    null(1),
                    len-16-BYTE-space(2),
                    len-16-BYTE-null(4)
                }
            ACCESS  read-write
            STATUS  mandatory
            DESCRIPTION
                "message length"
            ::= { t3LoVTOverheadSetupEty 4 }

        t3LoVTOverheadExpMsg OBJECT-TYPE
            SYNTAX  DisplayString (SIZE(0..64))
            ACCESS  read-write
            STATUS  mandatory
            DESCRIPTION
                "The expected message"
            ::= { t3LoVTOverheadSetupEty 5 }

        t3LoVTOverheadTxMsg OBJECT-TYPE
            SYNTAX  DisplayString (SIZE(0..64))
            ACCESS  read-write
            STATUS  mandatory
            DESCRIPTION
                "The tx message"
            ::= { t3LoVTOverheadSetupEty 6 }

        t3LoVTOverheadRxMsg OBJECT-TYPE
            SYNTAX  DisplayString (SIZE(0..64))
            ACCESS  read-only
            STATUS  mandatory
            DESCRIPTION
                "The rx message"
            ::= { t3LoVTOverheadSetupEty 7 }

        t3LoVTOverheadEPSL  OBJECT-TYPE
            SYNTAX  INTEGER(0..255)
            ACCESS  read-write
            STATUS  mandatory
            DESCRIPTION
                "The expected Path Signal Label"
            ::= { t3LoVTOverheadSetupEty 8 }

        t3LoVTOverheadTxPSL  OBJECT-TYPE
            SYNTAX  INTEGER(0..255)
            ACCESS  read-write
            STATUS  mandatory
            DESCRIPTION
                "The Tx Path Signal Label"
            ::= { t3LoVTOverheadSetupEty 9 }

        t3LoVTOverheadRxPSL  OBJECT-TYPE
            SYNTAX  INTEGER(0..255)
            ACCESS  read-only
            STATUS  mandatory
            DESCRIPTION
                "The Rx Path Signal Label"
            ::= { t3LoVTOverheadSetupEty 10 }

--
--  T3 Customer Information Setup Table
--

        t3CustomerInfoSetupTab  OBJECT-TYPE
            SYNTAX  SEQUENCE OF T3CustomerInfoSetupEty
            ACCESS  not-accessible
            STATUS  mandatory
            DESCRIPTION
                "Customer information setup table"
            ::= { t3Config 3 }

        t3CustomerInfoSetupEty  OBJECT-TYPE
            SYNTAX  T3CustomerInfoSetupEty
            ACCESS  not-accessible
            STATUS  mandatory
            DESCRIPTION
                "An entry in the customer information setup table"
            INDEX { t3CustomerInfoUnit ,
                    t3CustomerInfoPort }
            ::= { t3CustomerInfoSetupTab 1 }

        T3CustomerInfoSetupEty ::= SEQUENCE {
            t3CustomerInfoUnit          UnitID,
            t3CustomerInfoPort          PortID,
            t3CustomerInfoString        DisplayString(SIZE(0..32))
        }

        t3CustomerInfoUnit  OBJECT-TYPE
            SYNTAX  UnitID
            ACCESS  read-only
            STATUS  mandatory
            DESCRIPTION
            "unit 1 to 4."
            ::= { t3CustomerInfoSetupEty 1 }

        t3CustomerInfoPort  OBJECT-TYPE
            SYNTAX  PortID
            ACCESS  read-only
            STATUS  mandatory
            DESCRIPTION
                "T3 Port 1 to 3"
            ::= { t3CustomerInfoSetupEty 2 }

        t3CustomerInfoString OBJECT-TYPE
            SYNTAX  DisplayString (SIZE(0..32))
            ACCESS  read-write
            STATUS  mandatory
            DESCRIPTION
                "Customer information"
            ::= { t3CustomerInfoSetupEty 3 }

--
-- T3 TPSG Protection Setup Table
--
        t3TPSGProtectSetupTab  OBJECT-TYPE
            SYNTAX  SEQUENCE OF T3TPSGProtectSetupEty
            ACCESS  not-accessible
            STATUS  mandatory
            DESCRIPTION
                "TPSG protection setup table"
            ::= { t3Config 4 }

        t3TPSGProtectSetupEty  OBJECT-TYPE
            SYNTAX  T3TPSGProtectSetupEty
            ACCESS  not-accessible
            STATUS  mandatory
            DESCRIPTION
                "An entry in the TPSG protection setup table"
            INDEX { t3TPSGProtectUnit }
            ::= { t3TPSGProtectSetupTab 1 }

        T3TPSGProtectSetupEty ::= SEQUENCE {
            t3TPSGProtectUnit           UnitID,
            t3TPSGProtectActive         INTEGER,
            t3TPSGProtectStatus         INTEGER,
            t3TPSGProtectType           INTEGER,
            t3TPSGProtectMode           INTEGER
        }

        t3TPSGProtectUnit  OBJECT-TYPE
            SYNTAX  UnitID
            ACCESS  read-only
            STATUS  mandatory
            DESCRIPTION
            "unit 1 to 4."
            ::= { t3TPSGProtectSetupEty 1 }

        t3TPSGProtectActive  OBJECT-TYPE
            SYNTAX  INTEGER{
                    none(0),
                    standby(1),
                    working(2)
                }
            ACCESS  read-only
            STATUS  mandatory
            DESCRIPTION
                "TPSG active working/standby"
            ::= { t3TPSGProtectSetupEty 2 }

        t3TPSGProtectStatus  OBJECT-TYPE
            SYNTAX  INTEGER{
                    sync-failed(1),
                    sync-ok(2),
                    start-sync(3),
                    during-sync(4),
                    update-failed(5),
                    unsync(6)
                }
            ACCESS  read-only
            STATUS  mandatory
            DESCRIPTION
                "TPSG Status"
            ::= { t3TPSGProtectSetupEty 3 }

        t3TPSGProtectType  OBJECT-TYPE
            SYNTAX  INTEGER{
                    port-circuit-protection(3),
                    line-1-plus-1(4)
                }
            ACCESS  read-write
            STATUS  mandatory
            DESCRIPTION
                "TPSG protection type"
            ::= { t3TPSGProtectSetupEty 4 }

        t3TPSGProtectMode  OBJECT-TYPE
            SYNTAX  INTEGER{
                    non-revertible(1),
                    revertible(2)
                }
            ACCESS  read-write
            STATUS  mandatory
            DESCRIPTION
                "TPSG protection mode"
            ::= { t3TPSGProtectSetupEty 5 }


--
--  T3 Mapping Mode Setup Table
--

        t3MappingModeSetupTab  OBJECT-TYPE
            SYNTAX  SEQUENCE OF T3MappingModeSetupEty
            ACCESS  not-accessible
            STATUS  mandatory
            DESCRIPTION
                "AU3/TU3 mapping mode setup table"
            ::= { t3Config 5 }

        t3MappingModeSetupEty  OBJECT-TYPE
            SYNTAX  T3MappingModeSetupEty
            ACCESS  not-accessible
            STATUS  mandatory
            DESCRIPTION
                "An entry in the AU3/TU3 mapping mode setup table"
            INDEX { t3MappingModeUnit }
            ::= { t3MappingModeSetupTab 1 }

        T3MappingModeSetupEty ::= SEQUENCE {
            t3MappingModeUnit           UnitID,
            t3MappingMode               INTEGER
        }

        t3MappingModeUnit  OBJECT-TYPE
            SYNTAX  UnitID
            ACCESS  read-only
            STATUS  mandatory
            DESCRIPTION
            "unit 1 to 4."
            ::= { t3MappingModeSetupEty 1 }

        t3MappingMode  OBJECT-TYPE
            SYNTAX  INTEGER{
                    au3-sts1(1),
                    au4-tug3(2)
                }
            ACCESS  read-write
            STATUS  mandatory
            DESCRIPTION
                "AU3/TU3 mapping mode"
            ::= { t3MappingModeSetupEty 2 }

--
-- T3 TPSG Protection Switch Table
--
        t3TPSGProtectSwitchTab  OBJECT-TYPE
            SYNTAX  SEQUENCE OF T3TPSGProtectSwitchEty
            ACCESS  not-accessible
            STATUS  mandatory
            DESCRIPTION
                "TPSG protection switch table"
            ::= { t3Config 6 }

        t3TPSGProtectSwitchEty  OBJECT-TYPE
            SYNTAX  T3TPSGProtectSwitchEty
            ACCESS  not-accessible
            STATUS  mandatory
            DESCRIPTION
                "An entry in the TPSG protection switch table"
            INDEX { t3TPSGProSwitchUnit ,
                    t3TPSGProSwitchPort }
            ::= { t3TPSGProtectSwitchTab 1 }

        T3TPSGProtectSwitchEty ::= SEQUENCE {
            t3TPSGProSwitchUnit         UnitID,
            t3TPSGProSwitchPort         PortID,
            t3TPSGProSwitchSide         INTEGER
        }

        t3TPSGProSwitchUnit  OBJECT-TYPE
            SYNTAX  UnitID
            ACCESS  read-only
            STATUS  mandatory
            DESCRIPTION
            "unit 1 to 4."
            ::= { t3TPSGProtectSwitchEty 1 }

        t3TPSGProSwitchPort  OBJECT-TYPE
            SYNTAX  PortID
            ACCESS  read-only
            STATUS  mandatory
            DESCRIPTION
                "T3 Port 1 to 3"
            ::= { t3TPSGProtectSwitchEty 2 }

        t3TPSGProSwitchSide  OBJECT-TYPE
            SYNTAX  INTEGER {
                    left(1),
                    right(2)
                }
            ACCESS  read-write
            STATUS  mandatory
            DESCRIPTION
                "Switch Side(left/right)"
            ::= { t3TPSGProtectSwitchEty 3 }

--
--  T3 Alarm
--

    t3Alarm           OBJECT IDENTIFIER ::= { t3-card 2 }

--
--  T3 Alarm Mask Setup Table
--

    t3AlarmMask       OBJECT IDENTIFIER ::= { t3Alarm 1 }

--
--   High Order Alarm Mask Setup
--

        t3HoSTSAlmMaskSetupTab  OBJECT-TYPE
            SYNTAX  SEQUENCE OF T3HoSTSAlmMaskSetupEty
            ACCESS  not-accessible
            STATUS  mandatory
            DESCRIPTION
                "High Order/STS Alarm mask setup table"
            ::= { t3AlarmMask 1 }

        t3HoSTSAlmMaskSetupEty  OBJECT-TYPE
            SYNTAX  T3HoSTSAlmMaskSetupEty
            ACCESS  not-accessible
            STATUS  mandatory
            DESCRIPTION
                "An entry in the alarm mask setup table"
            INDEX { t3HoSTSAlmMaskUnit ,
                    t3HoSTSAlmMaskPort }
            ::= { t3HoSTSAlmMaskSetupTab 1 }

        T3HoSTSAlmMaskSetupEty ::= SEQUENCE {
            t3HoSTSAlmMaskUnit          UnitID,
            t3HoSTSAlmMaskPort          PortID,
            t3HoSTSAlmMask-LOP          INTEGER,
            t3HoSTSAlmMask-AIS          INTEGER,
            t3HoSTSAlmMask-UNEQ         INTEGER,
            t3HoSTSAlmMask-PLM          INTEGER,
            t3HoSTSAlmMask-TIM          INTEGER,
            t3HoSTSAlmMask-RDI-P        INTEGER,
            t3HoSTSAlmMask-RDI-S        INTEGER,
            t3HoSTSAlmMask-RDI-C        INTEGER,
            t3HoSTSAlmMask-REI          INTEGER,
            t3HoSTSAlmMask-B3-BIP       INTEGER,
            t3HoSTSAlmMask-B3-LOM       INTEGER
        }

        t3HoSTSAlmMaskUnit  OBJECT-TYPE
            SYNTAX  UnitID
            ACCESS  read-only
            STATUS  mandatory
            DESCRIPTION
            "unit 1 to 4."
            ::= { t3HoSTSAlmMaskSetupEty 1 }

        t3HoSTSAlmMaskPort  OBJECT-TYPE
            SYNTAX  PortID
            ACCESS  read-only
            STATUS  mandatory
            DESCRIPTION
                "T3 Port 1 to 3"
            ::= { t3HoSTSAlmMaskSetupEty 2 }

        t3HoSTSAlmMask-LOP  OBJECT-TYPE
            SYNTAX  INTEGER{
                    disable(1),
                    enable(2)
                }
            ACCESS  read-write
            STATUS  mandatory
            DESCRIPTION
                "au-lop alarm"
            ::= { t3HoSTSAlmMaskSetupEty 3 }

        t3HoSTSAlmMask-AIS  OBJECT-TYPE
            SYNTAX  INTEGER{
                    disable(1),
                    enable(2)
                }
            ACCESS  read-write
            STATUS  mandatory
            DESCRIPTION
                "au-ais alarm"
            ::= { t3HoSTSAlmMaskSetupEty 4 }

        t3HoSTSAlmMask-UNEQ  OBJECT-TYPE
            SYNTAX  INTEGER{
                    disable(1),
                    enable(2)
                }
            ACCESS  read-write
            STATUS  mandatory
            DESCRIPTION
                "hp-uneq alarm"
            ::= { t3HoSTSAlmMaskSetupEty 5 }

        t3HoSTSAlmMask-PLM  OBJECT-TYPE
            SYNTAX  INTEGER{
                    disable(1),
                    enable(2)
                }
            ACCESS  read-write
            STATUS  mandatory
            DESCRIPTION
                "hp-plm alarm"
            ::= { t3HoSTSAlmMaskSetupEty 6 }

        t3HoSTSAlmMask-TIM  OBJECT-TYPE
            SYNTAX  INTEGER{
                    disable(1),
                    enable(2)
                }
            ACCESS  read-write
            STATUS  mandatory
            DESCRIPTION
                "hp-tim alarm"
            ::= { t3HoSTSAlmMaskSetupEty 7 }

        t3HoSTSAlmMask-RDI-P  OBJECT-TYPE
            SYNTAX  INTEGER{
                    disable(1),
                    enable(2)
                }
            ACCESS  read-write
            STATUS  mandatory
            DESCRIPTION
                "hp-rdi-p alarm"
            ::= { t3HoSTSAlmMaskSetupEty 8 }

        t3HoSTSAlmMask-RDI-S  OBJECT-TYPE
            SYNTAX  INTEGER{
                    disable(1),
                    enable(2)
                }
            ACCESS  read-write
            STATUS  mandatory
            DESCRIPTION
                "hp-rdi-s alarm"
            ::= { t3HoSTSAlmMaskSetupEty 9 }

        t3HoSTSAlmMask-RDI-C  OBJECT-TYPE
            SYNTAX  INTEGER{
                    disable(1),
                    enable(2)
                }
            ACCESS  read-write
            STATUS  mandatory
            DESCRIPTION
                "hp-rdi-c alarm"
            ::= { t3HoSTSAlmMaskSetupEty 10 }

        t3HoSTSAlmMask-REI  OBJECT-TYPE
            SYNTAX  INTEGER{
                    disable(1),
                    enable(2)
                }
            ACCESS  read-write
            STATUS  mandatory
            DESCRIPTION
                "hp-rei alarm"
            ::= { t3HoSTSAlmMaskSetupEty 11 }

        t3HoSTSAlmMask-B3-BIP  OBJECT-TYPE
            SYNTAX  INTEGER{
                    disable(1),
                    enable(2)
                }
            ACCESS  read-write
            STATUS  mandatory
            DESCRIPTION
                "hp-bip alarm"
            ::= { t3HoSTSAlmMaskSetupEty 12 }

        t3HoSTSAlmMask-B3-LOM  OBJECT-TYPE
            SYNTAX  INTEGER{
                    disable(1),
                    enable(2)
                }
            ACCESS  read-write
            STATUS  mandatory
            DESCRIPTION
                "hp-lom alarm"
            ::= { t3HoSTSAlmMaskSetupEty 13 }

--
--   Low Order Alarm Mask Setup
--

        t3LoVTAlmMaskSetupTab  OBJECT-TYPE
            SYNTAX  SEQUENCE OF T3LoVTAlmMaskSetupEty
            ACCESS  not-accessible
            STATUS  mandatory
            DESCRIPTION
                "Low Order/VT Alarm mask setup table"
            ::= { t3AlarmMask 2 }

        t3LoVTAlmMaskSetupEty  OBJECT-TYPE
            SYNTAX  T3LoVTAlmMaskSetupEty
            ACCESS  not-accessible
            STATUS  mandatory
            DESCRIPTION
                "An entry in the alarm mask setup table"
            INDEX { t3LoVTAlmMaskUnit ,
                    t3LoVTAlmMaskPort ,
                    t3LoVTAlmMaskChannel }
            ::= { t3LoVTAlmMaskSetupTab 1 }

        T3LoVTAlmMaskSetupEty ::= SEQUENCE {
            t3LoVTAlmMaskUnit           UnitID,
            t3LoVTAlmMaskPort           PortID,
            t3LoVTAlmMaskChannel        ChannelNum,
            t3LoVTAlmMask-LOP           INTEGER,
            t3LoVTAlmMask-AIS           INTEGER,
            t3LoVTAlmMask-UNEQ          INTEGER,
            t3LoVTAlmMask-PLM           INTEGER,
            t3LoVTAlmMask-TIM           INTEGER,
            t3LoVTAlmMask-RDI-P         INTEGER,
            t3LoVTAlmMask-RDI-S         INTEGER,
            t3LoVTAlmMask-RDI-C         INTEGER,
            t3LoVTAlmMask-V5-REI        INTEGER,
            t3LoVTAlmMask-V5-BIP        INTEGER
        }

        t3LoVTAlmMaskUnit  OBJECT-TYPE
            SYNTAX  UnitID
            ACCESS  read-only
            STATUS  mandatory
            DESCRIPTION
            "unit 1 to 4."
            ::= { t3LoVTAlmMaskSetupEty 1 }

        t3LoVTAlmMaskPort  OBJECT-TYPE
            SYNTAX  PortID
            ACCESS  read-only
            STATUS  mandatory
            DESCRIPTION
                "T3 Port 1 to 3"
            ::= { t3LoVTAlmMaskSetupEty 2 }

        t3LoVTAlmMaskChannel  OBJECT-TYPE
            SYNTAX  ChannelNum
            ACCESS  read-only
            STATUS  mandatory
            DESCRIPTION
                "T3 Channel 1 to 28"
            ::= { t3LoVTAlmMaskSetupEty 3 }

        t3LoVTAlmMask-LOP  OBJECT-TYPE
            SYNTAX  INTEGER{
                    disable(1),
                    enable(2)
                }
            ACCESS  read-write
            STATUS  mandatory
            DESCRIPTION
                "tu-lop alarm"
            ::= { t3LoVTAlmMaskSetupEty 4 }

        t3LoVTAlmMask-AIS  OBJECT-TYPE
            SYNTAX  INTEGER{
                    disable(1),
                    enable(2)
                }
            ACCESS  read-write
            STATUS  mandatory
            DESCRIPTION
                "tu-ais alarm"
            ::= { t3LoVTAlmMaskSetupEty 5 }

        t3LoVTAlmMask-UNEQ  OBJECT-TYPE
            SYNTAX  INTEGER{
                    disable(1),
                    enable(2)
                }
            ACCESS  read-write
            STATUS  mandatory
            DESCRIPTION
                "lp-uneq alarm"
            ::= { t3LoVTAlmMaskSetupEty 6 }

        t3LoVTAlmMask-PLM  OBJECT-TYPE
            SYNTAX  INTEGER{
                    disable(1),
                    enable(2)
                }
            ACCESS  read-write
            STATUS  mandatory
            DESCRIPTION
                "lp-plm alarm"
            ::= { t3LoVTAlmMaskSetupEty 7 }

        t3LoVTAlmMask-TIM  OBJECT-TYPE
            SYNTAX  INTEGER{
                    disable(1),
                    enable(2)
                }
            ACCESS  read-write
            STATUS  mandatory
            DESCRIPTION
                "lp-tim alarm"
            ::= { t3LoVTAlmMaskSetupEty 8 }

        t3LoVTAlmMask-RDI-P  OBJECT-TYPE
            SYNTAX  INTEGER{
                    disable(1),
                    enable(2)
                }
            ACCESS  read-write
            STATUS  mandatory
            DESCRIPTION
                "lp-rdi-p alarm"
            ::= { t3LoVTAlmMaskSetupEty 9 }

        t3LoVTAlmMask-RDI-S  OBJECT-TYPE
            SYNTAX  INTEGER{
                    disable(1),
                    enable(2)
                }
            ACCESS  read-write
            STATUS  mandatory
            DESCRIPTION
                "lp-rdi-s alarm"
            ::= { t3LoVTAlmMaskSetupEty 10 }

        t3LoVTAlmMask-RDI-C  OBJECT-TYPE
            SYNTAX  INTEGER{
                    disable(1),
                    enable(2)
                }
            ACCESS  read-write
            STATUS  mandatory
            DESCRIPTION
                "lp-rdi-c alarm"
            ::= { t3LoVTAlmMaskSetupEty 11 }

        t3LoVTAlmMask-V5-REI  OBJECT-TYPE
            SYNTAX  INTEGER{
                    disable(1),
                    enable(2)
                }
            ACCESS  read-write
            STATUS  mandatory
            DESCRIPTION
                "lp-rei alarm"
            ::= { t3LoVTAlmMaskSetupEty 12 }

        t3LoVTAlmMask-V5-BIP  OBJECT-TYPE
            SYNTAX  INTEGER{
                    disable(1),
                    enable(2)
                }
            ACCESS  read-write
            STATUS  mandatory
            DESCRIPTION
                "lp-bip alarm"
            ::= { t3LoVTAlmMaskSetupEty 13 }

--
--   Line Alarm Mask Setup
--

        t3LineAlmMaskSetupTab  OBJECT-TYPE
            SYNTAX  SEQUENCE OF T3LineAlmMaskSetupEty
            ACCESS  not-accessible
            STATUS  mandatory
            DESCRIPTION
                "Line Alarm mask setup table"
            ::= { t3AlarmMask 3 }

        t3LineAlmMaskSetupEty  OBJECT-TYPE
            SYNTAX  T3LineAlmMaskSetupEty
            ACCESS  not-accessible
            STATUS  mandatory
            DESCRIPTION
                "An entry in the alarm mask setup table"
            INDEX { t3LineAlmMaskUnit ,
                    t3LineAlmMaskPort }
            ::= { t3LineAlmMaskSetupTab 1 }

        T3LineAlmMaskSetupEty ::= SEQUENCE {
            t3LineAlmMaskUnit           UnitID,
            t3LineAlmMaskPort           PortID,
            t3LineAlmMask-LOS           INTEGER,
            t3LineAlmMask-AIS           INTEGER,
            t3LineAlmMask-UAS           INTEGER,
            t3LineAlmMask-YELL          INTEGER,
            t3LineAlmMask-LOF           INTEGER,
            t3LineAlmMask-IDLE          INTEGER,
            t3LineAlmMask-P-C-BITS      INTEGER
        }

        t3LineAlmMaskUnit  OBJECT-TYPE
            SYNTAX  UnitID
            ACCESS  read-only
            STATUS  mandatory
            DESCRIPTION
            "unit 1 to 4."
            ::= { t3LineAlmMaskSetupEty 1 }

        t3LineAlmMaskPort  OBJECT-TYPE
            SYNTAX  PortID
            ACCESS  read-only
            STATUS  mandatory
            DESCRIPTION
                "T3 Port 1 to 3"
            ::= { t3LineAlmMaskSetupEty 2 }

        t3LineAlmMask-LOS  OBJECT-TYPE
            SYNTAX  INTEGER{
                    disable(1),
                    enable(2)
                }
            ACCESS  read-write
            STATUS  mandatory
            DESCRIPTION
                "line-los alarm"
            ::= { t3LineAlmMaskSetupEty 3 }

        t3LineAlmMask-AIS  OBJECT-TYPE
            SYNTAX  INTEGER{
                    disable(1),
                    enable(2)
                }
            ACCESS  read-write
            STATUS  mandatory
            DESCRIPTION
                "line-ais alarm"
            ::= { t3LineAlmMaskSetupEty 4 }

        t3LineAlmMask-UAS  OBJECT-TYPE
            SYNTAX  INTEGER{
                    disable(1),
                    enable(2)
                }
            ACCESS  read-write
            STATUS  mandatory
            DESCRIPTION
                "line-uas alarm"
            ::= { t3LineAlmMaskSetupEty 5 }

        t3LineAlmMask-YELL  OBJECT-TYPE
            SYNTAX  INTEGER{
                    disable(1),
                    enable(2)
                }
            ACCESS  read-write
            STATUS  mandatory
            DESCRIPTION
                "line-yell alarm"
            ::= { t3LineAlmMaskSetupEty 6 }

        t3LineAlmMask-LOF  OBJECT-TYPE
            SYNTAX  INTEGER{
                    disable(1),
                    enable(2)
                }
            ACCESS  read-write
            STATUS  mandatory
            DESCRIPTION
                "line-lof alarm"
            ::= { t3LineAlmMaskSetupEty 7 }

        t3LineAlmMask-IDLE  OBJECT-TYPE
            SYNTAX  INTEGER{
                    disable(1),
                    enable(2)
                }
            ACCESS  read-write
            STATUS  mandatory
            DESCRIPTION
                "line-idle alarm"
            ::= { t3LineAlmMaskSetupEty 8 }

        t3LineAlmMask-P-C-BITS  OBJECT-TYPE
            SYNTAX  INTEGER{
                    disable(1),
                    enable(2)
                }
            ACCESS  read-write
            STATUS  mandatory
            DESCRIPTION
                "line DS3 alarm, P-Bits for M13 frame, and C-Bits for C-Bits Parity frame"
            ::= { t3LineAlmMaskSetupEty 9 }


--
--   M13 Alarm Mask Setup
--

        t3M13AlmMaskSetupTab  OBJECT-TYPE
            SYNTAX  SEQUENCE OF T3M13AlmMaskSetupEty
            ACCESS  not-accessible
            STATUS  mandatory
            DESCRIPTION
                "M13 Alarm mask setup table"
            ::= { t3AlarmMask 4 }

        t3M13AlmMaskSetupEty  OBJECT-TYPE
            SYNTAX  T3M13AlmMaskSetupEty
            ACCESS  not-accessible
            STATUS  mandatory
            DESCRIPTION
                "An entry in the alarm mask setup table"
            INDEX { t3M13AlmMaskUnit ,
                    t3M13AlmMaskPort ,
                    t3M13AlmMaskChannel }
            ::= { t3M13AlmMaskSetupTab 1 }

        T3M13AlmMaskSetupEty ::= SEQUENCE {
            t3M13AlmMaskUnit            UnitID,
            t3M13AlmMaskPort            PortID,
            t3M13AlmMaskChannel         ChannelNum,
            t3M13AlmMask-AIS            INTEGER
        }

        t3M13AlmMaskUnit  OBJECT-TYPE
            SYNTAX  UnitID
            ACCESS  read-only
            STATUS  mandatory
            DESCRIPTION
            "unit 1 to 4."
            ::= { t3M13AlmMaskSetupEty 1 }

        t3M13AlmMaskPort  OBJECT-TYPE
            SYNTAX  PortID
            ACCESS  read-only
            STATUS  mandatory
            DESCRIPTION
                "T3 Port 1 to 3"
            ::= { t3M13AlmMaskSetupEty 2 }

        t3M13AlmMaskChannel  OBJECT-TYPE
            SYNTAX  ChannelNum
            ACCESS  read-only
            STATUS  mandatory
            DESCRIPTION
                "T3 Channel 1 to 28"
            ::= { t3M13AlmMaskSetupEty 3 }

        t3M13AlmMask-AIS  OBJECT-TYPE
            SYNTAX  INTEGER{
                    disable(1),
                    enable(2)
                }
            ACCESS  read-write
            STATUS  mandatory
            DESCRIPTION
                "M13-ais alarm"
            ::= { t3M13AlmMaskSetupEty 4 }


--
--  T3 Alarm Relay Setup Table
--

    t3AlarmRelay       OBJECT IDENTIFIER ::= { t3Alarm 2 }


--
--   High Order Alarm Relay Setup
--

        t3HoSTSAlmRelaySetupTab  OBJECT-TYPE
            SYNTAX  SEQUENCE OF T3HoSTSAlmRelaySetupEty
            ACCESS  not-accessible
            STATUS  mandatory
            DESCRIPTION
                "High Order/STS Alarm relay setup table"
            ::= { t3AlarmRelay 1 }

        t3HoSTSAlmRelaySetupEty  OBJECT-TYPE
            SYNTAX  T3HoSTSAlmRelaySetupEty
            ACCESS  not-accessible
            STATUS  mandatory
            DESCRIPTION
                "An entry in the alarm relay setup table"
            INDEX { t3HoSTSAlmRelayUnit ,
                    t3HoSTSAlmRelayPort }
            ::= { t3HoSTSAlmRelaySetupTab 1 }

        T3HoSTSAlmRelaySetupEty ::= SEQUENCE {
            t3HoSTSAlmRelayUnit         UnitID,
            t3HoSTSAlmRelayPort         PortID,
            t3HoSTSAlmRelay-LOP         INTEGER,
            t3HoSTSAlmRelay-AIS         INTEGER,
            t3HoSTSAlmRelay-UNEQ        INTEGER,
            t3HoSTSAlmRelay-PLM         INTEGER,
            t3HoSTSAlmRelay-TIM         INTEGER,
            t3HoSTSAlmRelay-RDI-P       INTEGER,
            t3HoSTSAlmRelay-RDI-S       INTEGER,
            t3HoSTSAlmRelay-RDI-C       INTEGER,
            t3HoSTSAlmRelay-REI         INTEGER,
            t3HoSTSAlmRelay-B3-BIP      INTEGER,
            t3HoSTSAlmRelay-B3-LOM      INTEGER
        }

        t3HoSTSAlmRelayUnit  OBJECT-TYPE
            SYNTAX  UnitID
            ACCESS  read-only
            STATUS  mandatory
            DESCRIPTION
            "unit 1 to 4."
            ::= { t3HoSTSAlmRelaySetupEty 1 }

        t3HoSTSAlmRelayPort  OBJECT-TYPE
            SYNTAX  PortID
            ACCESS  read-only
            STATUS  mandatory
            DESCRIPTION
                "T3 Port 1 to 3"
            ::= { t3HoSTSAlmRelaySetupEty 2 }

        t3HoSTSAlmRelay-LOP  OBJECT-TYPE
            SYNTAX  INTEGER{
                    disable(1),
                    enable(2)
                }
            ACCESS  read-write
            STATUS  mandatory
            DESCRIPTION
                "au-lop alarm"
            ::= { t3HoSTSAlmRelaySetupEty 3 }

        t3HoSTSAlmRelay-AIS  OBJECT-TYPE
            SYNTAX  INTEGER{
                    disable(1),
                    enable(2)
                }
            ACCESS  read-write
            STATUS  mandatory
            DESCRIPTION
                "au-ais alarm"
            ::= { t3HoSTSAlmRelaySetupEty 4 }

        t3HoSTSAlmRelay-UNEQ  OBJECT-TYPE
            SYNTAX  INTEGER{
                    disable(1),
                    enable(2)
                }
            ACCESS  read-write
            STATUS  mandatory
            DESCRIPTION
                "hp-uneq alarm"
            ::= { t3HoSTSAlmRelaySetupEty 5 }

        t3HoSTSAlmRelay-PLM  OBJECT-TYPE
            SYNTAX  INTEGER{
                    disable(1),
                    enable(2)
                }
            ACCESS  read-write
            STATUS  mandatory
            DESCRIPTION
                "hp-plm alarm"
            ::= { t3HoSTSAlmRelaySetupEty 6 }

        t3HoSTSAlmRelay-TIM  OBJECT-TYPE
            SYNTAX  INTEGER{
                    disable(1),
                    enable(2)
                }
            ACCESS  read-write
            STATUS  mandatory
            DESCRIPTION
                "hp-tim alarm"
            ::= { t3HoSTSAlmRelaySetupEty 7 }

        t3HoSTSAlmRelay-RDI-P  OBJECT-TYPE
            SYNTAX  INTEGER{
                    disable(1),
                    enable(2)
                }
            ACCESS  read-write
            STATUS  mandatory
            DESCRIPTION
                "hp-rdi-p alarm"
            ::= { t3HoSTSAlmRelaySetupEty 8 }

        t3HoSTSAlmRelay-RDI-S  OBJECT-TYPE
            SYNTAX  INTEGER{
                    disable(1),
                    enable(2)
                }
            ACCESS  read-write
            STATUS  mandatory
            DESCRIPTION
                "hp-rdi-s alarm"
            ::= { t3HoSTSAlmRelaySetupEty 9 }

        t3HoSTSAlmRelay-RDI-C  OBJECT-TYPE
            SYNTAX  INTEGER{
                    disable(1),
                    enable(2)
                }
            ACCESS  read-write
            STATUS  mandatory
            DESCRIPTION
                "hp-rdi-c alarm"
            ::= { t3HoSTSAlmRelaySetupEty 10 }

        t3HoSTSAlmRelay-REI  OBJECT-TYPE
            SYNTAX  INTEGER{
                    disable(1),
                    enable(2)
                }
            ACCESS  read-write
            STATUS  mandatory
            DESCRIPTION
                "hp-rei alarm"
            ::= { t3HoSTSAlmRelaySetupEty 11 }

        t3HoSTSAlmRelay-B3-BIP  OBJECT-TYPE
            SYNTAX  INTEGER{
                    disable(1),
                    enable(2)
                }
            ACCESS  read-write
            STATUS  mandatory
            DESCRIPTION
                "hp-bip alarm"
            ::= { t3HoSTSAlmRelaySetupEty 12 }

        t3HoSTSAlmRelay-B3-LOM  OBJECT-TYPE
            SYNTAX  INTEGER{
                    disable(1),
                    enable(2)
                }
            ACCESS  read-write
            STATUS  mandatory
            DESCRIPTION
                "hp-lom alarm"
            ::= { t3HoSTSAlmRelaySetupEty 13 }

--
--   Low Order Alarm Relay Setup
--

        t3LoVTAlmRelaySetupTab  OBJECT-TYPE
            SYNTAX  SEQUENCE OF T3LoVTAlmRelaySetupEty
            ACCESS  not-accessible
            STATUS  mandatory
            DESCRIPTION
                "Low Order/VT Alarm relay setup table"
            ::= { t3AlarmRelay 2 }

        t3LoVTAlmRelaySetupEty  OBJECT-TYPE
            SYNTAX  T3LoVTAlmRelaySetupEty
            ACCESS  not-accessible
            STATUS  mandatory
            DESCRIPTION
                "An entry in the alarm relay setup table"
            INDEX { t3LoVTAlmRelayUnit ,
                    t3LoVTAlmRelayPort ,
                    t3LoVTAlmRelayChannel }
            ::= { t3LoVTAlmRelaySetupTab 1 }

        T3LoVTAlmRelaySetupEty ::= SEQUENCE {
            t3LoVTAlmRelayUnit          UnitID,
            t3LoVTAlmRelayPort          PortID,
            t3LoVTAlmRelayChannel       ChannelNum,
            t3LoVTAlmRelay-LOP          INTEGER,
            t3LoVTAlmRelay-AIS          INTEGER,
            t3LoVTAlmRelay-UNEQ         INTEGER,
            t3LoVTAlmRelay-PLM          INTEGER,
            t3LoVTAlmRelay-TIM          INTEGER,
            t3LoVTAlmRelay-RDI-P        INTEGER,
            t3LoVTAlmRelay-RDI-S        INTEGER,
            t3LoVTAlmRelay-RDI-C        INTEGER,
            t3LoVTAlmRelay-V5-REI       INTEGER,
            t3LoVTAlmRelay-V5-BIP       INTEGER
        }

        t3LoVTAlmRelayUnit  OBJECT-TYPE
            SYNTAX  UnitID
            ACCESS  read-only
            STATUS  mandatory
            DESCRIPTION
            "unit 1 to 4."
            ::= { t3LoVTAlmRelaySetupEty 1 }

        t3LoVTAlmRelayPort  OBJECT-TYPE
            SYNTAX  PortID
            ACCESS  read-only
            STATUS  mandatory
            DESCRIPTION
                "T3 Port 1 to 3"
            ::= { t3LoVTAlmRelaySetupEty 2 }

        t3LoVTAlmRelayChannel  OBJECT-TYPE
            SYNTAX  ChannelNum
            ACCESS  read-only
            STATUS  mandatory
            DESCRIPTION
                "T3 Channel 1 to 28"
            ::= { t3LoVTAlmRelaySetupEty 3 }

        t3LoVTAlmRelay-LOP  OBJECT-TYPE
            SYNTAX  INTEGER{
                    disable(1),
                    enable(2)
                }
            ACCESS  read-write
            STATUS  mandatory
            DESCRIPTION
                "tu-lop alarm"
            ::= { t3LoVTAlmRelaySetupEty 4 }

        t3LoVTAlmRelay-AIS  OBJECT-TYPE
            SYNTAX  INTEGER{
                    disable(1),
                    enable(2)
                }
            ACCESS  read-write
            STATUS  mandatory
            DESCRIPTION
                "tu-ais alarm"
            ::= { t3LoVTAlmRelaySetupEty 5 }

        t3LoVTAlmRelay-UNEQ  OBJECT-TYPE
            SYNTAX  INTEGER{
                    disable(1),
                    enable(2)
                }
            ACCESS  read-write
            STATUS  mandatory
            DESCRIPTION
                "lp-uneq alarm"
            ::= { t3LoVTAlmRelaySetupEty 6 }

        t3LoVTAlmRelay-PLM  OBJECT-TYPE
            SYNTAX  INTEGER{
                    disable(1),
                    enable(2)
                }
            ACCESS  read-write
            STATUS  mandatory
            DESCRIPTION
                "lp-plm alarm"
            ::= { t3LoVTAlmRelaySetupEty 7 }

        t3LoVTAlmRelay-TIM  OBJECT-TYPE
            SYNTAX  INTEGER{
                    disable(1),
                    enable(2)
                }
            ACCESS  read-write
            STATUS  mandatory
            DESCRIPTION
                "lp-tim alarm"
            ::= { t3LoVTAlmRelaySetupEty 8 }

        t3LoVTAlmRelay-RDI-P  OBJECT-TYPE
            SYNTAX  INTEGER{
                    disable(1),
                    enable(2)
                }
            ACCESS  read-write
            STATUS  mandatory
            DESCRIPTION
                "lp-rdi-p alarm"
            ::= { t3LoVTAlmRelaySetupEty 9 }

        t3LoVTAlmRelay-RDI-S  OBJECT-TYPE
            SYNTAX  INTEGER{
                    disable(1),
                    enable(2)
                }
            ACCESS  read-write
            STATUS  mandatory
            DESCRIPTION
                "lp-rdi-s alarm"
            ::= { t3LoVTAlmRelaySetupEty 10 }

        t3LoVTAlmRelay-RDI-C  OBJECT-TYPE
            SYNTAX  INTEGER{
                    disable(1),
                    enable(2)
                }
            ACCESS  read-write
            STATUS  mandatory
            DESCRIPTION
                "lp-rdi-c alarm"
            ::= { t3LoVTAlmRelaySetupEty 11 }

        t3LoVTAlmRelay-V5-REI  OBJECT-TYPE
            SYNTAX  INTEGER{
                    disable(1),
                    enable(2)
                }
            ACCESS  read-write
            STATUS  mandatory
            DESCRIPTION
                "lp-rei alarm"
            ::= { t3LoVTAlmRelaySetupEty 12 }

        t3LoVTAlmRelay-V5-BIP  OBJECT-TYPE
            SYNTAX  INTEGER{
                    disable(1),
                    enable(2)
                }
            ACCESS  read-write
            STATUS  mandatory
            DESCRIPTION
                "lp-bip alarm"
            ::= { t3LoVTAlmRelaySetupEty 13 }

--
--   Line Alarm Relay Setup
--

        t3LineAlmRelaySetupTab  OBJECT-TYPE
            SYNTAX  SEQUENCE OF T3LineAlmRelaySetupEty
            ACCESS  not-accessible
            STATUS  mandatory
            DESCRIPTION
                "Line Alarm relay setup table"
            ::= { t3AlarmRelay 3 }

        t3LineAlmRelaySetupEty  OBJECT-TYPE
            SYNTAX  T3LineAlmRelaySetupEty
            ACCESS  not-accessible
            STATUS  mandatory
            DESCRIPTION
                "An entry in the alarm relay setup table"
            INDEX { t3LineAlmRelayUnit ,
                    t3LineAlmRelayPort }
            ::= { t3LineAlmRelaySetupTab 1 }

        T3LineAlmRelaySetupEty ::= SEQUENCE {
            t3LineAlmRelayUnit          UnitID,
            t3LineAlmRelayPort          PortID,
            t3LineAlmRelay-LOS          INTEGER,
            t3LineAlmRelay-AIS          INTEGER,
            t3LineAlmRelay-UAS          INTEGER,
            t3LineAlmRelay-YELL         INTEGER,
            t3LineAlmRelay-LOF          INTEGER,
            t3LineAlmRelay-IDLE         INTEGER,
            t3LineAlmRelay-P-C-BITS     INTEGER
        }

        t3LineAlmRelayUnit  OBJECT-TYPE
            SYNTAX  UnitID
            ACCESS  read-only
            STATUS  mandatory
            DESCRIPTION
            "unit 1 to 4."
            ::= { t3LineAlmRelaySetupEty 1 }

        t3LineAlmRelayPort  OBJECT-TYPE
            SYNTAX  PortID
            ACCESS  read-only
            STATUS  mandatory
            DESCRIPTION
                "T3 Port 1 to 3"
            ::= { t3LineAlmRelaySetupEty 2 }

        t3LineAlmRelay-LOS  OBJECT-TYPE
            SYNTAX  INTEGER{
                    disable(1),
                    enable(2)
                }
            ACCESS  read-write
            STATUS  mandatory
            DESCRIPTION
                "line-los alarm"
            ::= { t3LineAlmRelaySetupEty 3 }

        t3LineAlmRelay-AIS  OBJECT-TYPE
            SYNTAX  INTEGER{
                    disable(1),
                    enable(2)
                }
            ACCESS  read-write
            STATUS  mandatory
            DESCRIPTION
                "line-ais alarm"
            ::= { t3LineAlmRelaySetupEty 4 }

        t3LineAlmRelay-UAS  OBJECT-TYPE
            SYNTAX  INTEGER{
                    disable(1),
                    enable(2)
                }
            ACCESS  read-write
            STATUS  mandatory
            DESCRIPTION
                "line-uas alarm"
            ::= { t3LineAlmRelaySetupEty 5 }

        t3LineAlmRelay-YELL  OBJECT-TYPE
            SYNTAX  INTEGER{
                    disable(1),
                    enable(2)
                }
            ACCESS  read-write
            STATUS  mandatory
            DESCRIPTION
                "line-yell alarm"
            ::= { t3LineAlmRelaySetupEty 6 }

        t3LineAlmRelay-LOF  OBJECT-TYPE
            SYNTAX  INTEGER{
                    disable(1),
                    enable(2)
                }
            ACCESS  read-write
            STATUS  mandatory
            DESCRIPTION
                "line-lof alarm"
            ::= { t3LineAlmRelaySetupEty 7 }

        t3LineAlmRelay-IDLE  OBJECT-TYPE
            SYNTAX  INTEGER{
                    disable(1),
                    enable(2)
                }
            ACCESS  read-write
            STATUS  mandatory
            DESCRIPTION
                "line-idle alarm"
            ::= { t3LineAlmRelaySetupEty 8 }

        t3LineAlmRelay-P-C-BITS  OBJECT-TYPE
            SYNTAX  INTEGER{
                    disable(1),
                    enable(2)
                }
            ACCESS  read-write
            STATUS  mandatory
            DESCRIPTION
                "line DS3 alarm, P-Bits for M13 frame, and C-Bits for C-Bit Parity frame"
            ::= { t3LineAlmRelaySetupEty 9 }

--
--   M13 Alarm Relay Setup
--

        t3M13AlmRelaySetupTab  OBJECT-TYPE
            SYNTAX  SEQUENCE OF T3M13AlmRelaySetupEty
            ACCESS  not-accessible
            STATUS  mandatory
            DESCRIPTION
                "M13 Alarm relay setup table"
            ::= { t3AlarmRelay 4 }

        t3M13AlmRelaySetupEty  OBJECT-TYPE
            SYNTAX  T3M13AlmRelaySetupEty
            ACCESS  not-accessible
            STATUS  mandatory
            DESCRIPTION
                "An entry in the alarm relay setup table"
            INDEX { t3M13AlmRelayUnit ,
                    t3M13AlmRelayPort ,
                    t3M13AlmRelayChannel }
            ::= { t3M13AlmRelaySetupTab 1 }

        T3M13AlmRelaySetupEty ::= SEQUENCE {
            t3M13AlmRelayUnit           UnitID,
            t3M13AlmRelayPort           PortID,
            t3M13AlmRelayChannel        ChannelNum,
            t3M13AlmRelay-AIS           INTEGER
        }

        t3M13AlmRelayUnit  OBJECT-TYPE
            SYNTAX  UnitID
            ACCESS  read-only
            STATUS  mandatory
            DESCRIPTION
            "unit 1 to 4."
            ::= { t3M13AlmRelaySetupEty 1 }

        t3M13AlmRelayPort  OBJECT-TYPE
            SYNTAX  PortID
            ACCESS  read-only
            STATUS  mandatory
            DESCRIPTION
                "T3 Port 1 to 3"
            ::= { t3M13AlmRelaySetupEty 2 }

        t3M13AlmRelayChannel  OBJECT-TYPE
            SYNTAX  ChannelNum
            ACCESS  read-only
            STATUS  mandatory
            DESCRIPTION
                "T3 Channel 1 to 28"
            ::= { t3M13AlmRelaySetupEty 3 }

        t3M13AlmRelay-AIS  OBJECT-TYPE
            SYNTAX  INTEGER{
                    disable(1),
                    enable(2)
                }
            ACCESS  read-write
            STATUS  mandatory
            DESCRIPTION
                "M13-ais alarm"
            ::= { t3M13AlmRelaySetupEty 4 }

--
--  T3 Alarm Severity Setup Table
--

        t3AlmSeveritySetupTab  OBJECT-TYPE
            SYNTAX  SEQUENCE OF T3AlmSeveritySetupEty
            ACCESS  not-accessible
            STATUS  mandatory
            DESCRIPTION
                "Alarm severity setup table"
            ::= { t3Alarm 3 }

        t3AlmSeveritySetupEty  OBJECT-TYPE
            SYNTAX  T3AlmSeveritySetupEty
            ACCESS  not-accessible
            STATUS  mandatory
            DESCRIPTION
                "An entry in the alarm severity setup table"
            INDEX { t3AlmSvrityUnit }
            ::= { t3AlmSeveritySetupTab 1 }

        T3AlmSeveritySetupEty ::= SEQUENCE {
            t3AlmSvrityUnit             UnitID,
            t3AlmSvrityHoSTS-LOP        Severity,
            t3AlmSvrityHoSTS-AIS        Severity,
            t3AlmSvrityHoSTS-UNEQ       Severity,
            t3AlmSvrityHoSTS-PLM        Severity,
            t3AlmSvrityHoSTS-TIM        Severity,
            t3AlmSvrityHoSTS-RDI-P      Severity,
            t3AlmSvrityHoSTS-RDI-S      Severity,
            t3AlmSvrityHoSTS-RDI-C      Severity,
            t3AlmSvrityHoSTS-B3-REI     Severity,
            t3AlmSvrityHoSTS-B3-BIP     Severity,
            t3AlmSvrityHoSTS-LOM        Severity,
            t3AlmSvrityLoVT-LOP         Severity,
            t3AlmSvrityLoVT-AIS         Severity,
            t3AlmSvrityLoVT-UNEQ        Severity,
            t3AlmSvrityLoVT-PLM         Severity,
            t3AlmSvrityLoVT-TIM         Severity,
            t3AlmSvrityLoVT-RDI-P       Severity,
            t3AlmSvrityLoVT-RDI-S       Severity,
            t3AlmSvrityLoVT-RDI-C       Severity,
            t3AlmSvrityLoVT-V5-REI      Severity,
            t3AlmSvrityLoVT-V5-BIP      Severity,
            t3AlmSvrityLine-LOS         Severity,
            t3AlmSvrityLine-AIS         Severity,
            t3AlmSvrityLine-UAS         Severity,
            t3AlmSvrityLine-YELL        Severity,
            t3AlmSvrityLine-LOF         Severity,
            t3AlmSvrityLine-IDLE        Severity,
            t3AlmSvrityLine-P-C-BITS    Severity,
            t3AlmSvrityM13T1E1-AIS      Severity
        }

        t3AlmSvrityUnit  OBJECT-TYPE
            SYNTAX  UnitID
            ACCESS  read-only
            STATUS  mandatory
            DESCRIPTION
            "unit 1 to 4."
            ::= { t3AlmSeveritySetupEty 1 }

        t3AlmSvrityHoSTS-LOP  OBJECT-TYPE
            SYNTAX  Severity
            ACCESS  read-write
            STATUS  mandatory
            DESCRIPTION
                "au-lop alarm severity type"
            ::= { t3AlmSeveritySetupEty 2 }

        t3AlmSvrityHoSTS-AIS  OBJECT-TYPE
            SYNTAX  Severity
            ACCESS  read-write
            STATUS  mandatory
            DESCRIPTION
                "au-ais alarm severity type"
            ::= { t3AlmSeveritySetupEty 3 }

        t3AlmSvrityHoSTS-UNEQ  OBJECT-TYPE
            SYNTAX  Severity
            ACCESS  read-write
            STATUS  mandatory
            DESCRIPTION
                "hp-uneq alarm severity type"
            ::= { t3AlmSeveritySetupEty 4 }

        t3AlmSvrityHoSTS-PLM  OBJECT-TYPE
            SYNTAX  Severity
            ACCESS  read-write
            STATUS  mandatory
            DESCRIPTION
                "hp-plm alarm severity type"
            ::= { t3AlmSeveritySetupEty 5 }

        t3AlmSvrityHoSTS-TIM  OBJECT-TYPE
            SYNTAX  Severity
            ACCESS  read-write
            STATUS  mandatory
            DESCRIPTION
                "hp-tim alarm severity type"
            ::= { t3AlmSeveritySetupEty 6 }

        t3AlmSvrityHoSTS-RDI-P  OBJECT-TYPE
            SYNTAX  Severity
            ACCESS  read-write
            STATUS  mandatory
            DESCRIPTION
                "hp-rdi-p alarm severity type"
            ::= { t3AlmSeveritySetupEty 7 }

        t3AlmSvrityHoSTS-RDI-S  OBJECT-TYPE
            SYNTAX  Severity
            ACCESS  read-write
            STATUS  mandatory
            DESCRIPTION
                "hp-rdi-s alarm severity type"
            ::= { t3AlmSeveritySetupEty 8 }

        t3AlmSvrityHoSTS-RDI-C  OBJECT-TYPE
            SYNTAX  Severity
            ACCESS  read-write
            STATUS  mandatory
            DESCRIPTION
                "hp-rdi-c alarm severity type"
            ::= { t3AlmSeveritySetupEty 9 }

        t3AlmSvrityHoSTS-B3-REI  OBJECT-TYPE
            SYNTAX  Severity
            ACCESS  read-write
            STATUS  mandatory
            DESCRIPTION
                "hp-rei alarm severity type"
            ::= { t3AlmSeveritySetupEty 10 }

        t3AlmSvrityHoSTS-B3-BIP  OBJECT-TYPE
            SYNTAX  Severity
            ACCESS  read-write
            STATUS  mandatory
            DESCRIPTION
                "hp-bip alarm severity type"
            ::= { t3AlmSeveritySetupEty 11 }

        t3AlmSvrityHoSTS-LOM  OBJECT-TYPE
            SYNTAX  Severity
            ACCESS  read-write
            STATUS  mandatory
            DESCRIPTION
                "hp-lom alarm severity type"
            ::= { t3AlmSeveritySetupEty 12 }

        t3AlmSvrityLoVT-LOP  OBJECT-TYPE
            SYNTAX  Severity
            ACCESS  read-write
            STATUS  mandatory
            DESCRIPTION
                "tu-lop alarm severity type"
            ::= { t3AlmSeveritySetupEty 13 }

        t3AlmSvrityLoVT-AIS  OBJECT-TYPE
            SYNTAX  Severity
            ACCESS  read-write
            STATUS  mandatory
            DESCRIPTION
                "tu-ais alarm severity type"
            ::= { t3AlmSeveritySetupEty 14 }

        t3AlmSvrityLoVT-UNEQ  OBJECT-TYPE
            SYNTAX  Severity
            ACCESS  read-write
            STATUS  mandatory
            DESCRIPTION
                "lp-uneq alarm severity type"
            ::= { t3AlmSeveritySetupEty 15 }

        t3AlmSvrityLoVT-PLM  OBJECT-TYPE
            SYNTAX  Severity
            ACCESS  read-write
            STATUS  mandatory
            DESCRIPTION
                "lp-plm alarm severity type"
            ::= { t3AlmSeveritySetupEty 16 }

        t3AlmSvrityLoVT-TIM  OBJECT-TYPE
            SYNTAX  Severity
            ACCESS  read-write
            STATUS  mandatory
            DESCRIPTION
                "lp-tim alarm severity type"
            ::= { t3AlmSeveritySetupEty 17 }

        t3AlmSvrityLoVT-RDI-P  OBJECT-TYPE
            SYNTAX  Severity
            ACCESS  read-write
            STATUS  mandatory
            DESCRIPTION
                "lp-rdi-p alarm severity type"
            ::= { t3AlmSeveritySetupEty 18 }

        t3AlmSvrityLoVT-RDI-S  OBJECT-TYPE
            SYNTAX  Severity
            ACCESS  read-write
            STATUS  mandatory
            DESCRIPTION
                "lp-rdi-s alarm severity type"
            ::= { t3AlmSeveritySetupEty 19 }

        t3AlmSvrityLoVT-RDI-C  OBJECT-TYPE
            SYNTAX  Severity
            ACCESS  read-write
            STATUS  mandatory
            DESCRIPTION
                "lp-rdi-c alarm severity type"
            ::= { t3AlmSeveritySetupEty 20 }

        t3AlmSvrityLoVT-V5-REI  OBJECT-TYPE
            SYNTAX  Severity
            ACCESS  read-write
            STATUS  mandatory
            DESCRIPTION
                "lp-rei alarm severity type"
            ::= { t3AlmSeveritySetupEty 21 }

        t3AlmSvrityLoVT-V5-BIP  OBJECT-TYPE
            SYNTAX  Severity
            ACCESS  read-write
            STATUS  mandatory
            DESCRIPTION
                "lp-bip alarm severity type"
            ::= { t3AlmSeveritySetupEty 22 }

        t3AlmSvrityLine-LOS  OBJECT-TYPE
            SYNTAX  Severity
            ACCESS  read-write
            STATUS  mandatory
            DESCRIPTION
                "line-los alarm severity type"
            ::= { t3AlmSeveritySetupEty 23 }

        t3AlmSvrityLine-AIS  OBJECT-TYPE
            SYNTAX  Severity
            ACCESS  read-write
            STATUS  mandatory
            DESCRIPTION
                "line-ais alarm severity type"
            ::= { t3AlmSeveritySetupEty 24 }

        t3AlmSvrityLine-UAS  OBJECT-TYPE
            SYNTAX  Severity
            ACCESS  read-write
            STATUS  mandatory
            DESCRIPTION
                "line-uas alarm severity type"
            ::= { t3AlmSeveritySetupEty 25 }

        t3AlmSvrityLine-YELL  OBJECT-TYPE
            SYNTAX  Severity
            ACCESS  read-write
            STATUS  mandatory
            DESCRIPTION
                "line-yell alarm severity type"
            ::= { t3AlmSeveritySetupEty 26 }

        t3AlmSvrityLine-LOF  OBJECT-TYPE
            SYNTAX  Severity
            ACCESS  read-write
            STATUS  mandatory
            DESCRIPTION
                "line-lof alarm severity type"
            ::= { t3AlmSeveritySetupEty 27 }

        t3AlmSvrityLine-IDLE  OBJECT-TYPE
            SYNTAX  Severity
            ACCESS  read-write
            STATUS  mandatory
            DESCRIPTION
                "line-idle alarm severity type"
            ::= { t3AlmSeveritySetupEty 28 }

        t3AlmSvrityLine-P-C-BITS  OBJECT-TYPE
            SYNTAX  Severity
            ACCESS  read-write
            STATUS  mandatory
            DESCRIPTION
                "line DS3 alarm severity type, P-Bits for M13 frame, and C-Bits for C-Bit Parity frame"
            ::= { t3AlmSeveritySetupEty 29 }

        t3AlmSvrityM13T1E1-AIS  OBJECT-TYPE
            SYNTAX  Severity
            ACCESS  read-write
            STATUS  mandatory
            DESCRIPTION
                "M13-T1/E1 alarm severity type"
            ::= { t3AlmSeveritySetupEty 30 }

--
--  T3 Insert AIS Alarm Setup Table
--

        t3InsertAisAlmSetupTab  OBJECT-TYPE
            SYNTAX  SEQUENCE OF T3InsertAisAlmSetupEty
            ACCESS  not-accessible
            STATUS  mandatory
            DESCRIPTION
                "Insert AIS alarm setup table"
            ::= { t3Alarm 4 }

        t3InsertAisAlmSetupEty  OBJECT-TYPE
            SYNTAX  T3InsertAisAlmSetupEty
            ACCESS  not-accessible
            STATUS  mandatory
            DESCRIPTION
                "An entry in the insert AIS alarm setup table"
            INDEX { t3InstUnit }
            ::= { t3InsertAisAlmSetupTab 1 }

        T3InsertAisAlmSetupEty ::= SEQUENCE {
            t3InstUnit                  UnitID,
            t3InstAuLop-LopPToAis       INTEGER,
            t3InstAuAis-AisPToAis       INTEGER,
            t3InstHpUneq-UneqPToAis     INTEGER,
            t3InstHpTim-TimPToAis       INTEGER,
            t3InstHpLom-LomToAis        INTEGER,
            t3InstHpPlm-PlmPToAis       INTEGER,
            t3InstTuAis-AisVToAis       INTEGER,
            t3InstTuLop-LopVToAis       INTEGER,
            t3InstLpUneq-UneqVToAis     INTEGER,
            t3InstLpTim-TimVToAis       INTEGER,
            t3InstLpPlm-PlmVToAis       INTEGER
        }

        t3InstUnit  OBJECT-TYPE
            SYNTAX  UnitID
            ACCESS  read-only
            STATUS  mandatory
            DESCRIPTION
            "unit 1 to 4."
            ::= { t3InsertAisAlmSetupEty 1 }

        t3InstAuLop-LopPToAis OBJECT-TYPE
            SYNTAX  INTEGER {
                    disable(1),
                    enable(2)
                }
            ACCESS  read-write
            STATUS  mandatory
            DESCRIPTION
                "au-lop to ais"
            ::= { t3InsertAisAlmSetupEty 2 }

        t3InstAuAis-AisPToAis OBJECT-TYPE
            SYNTAX  INTEGER {
                    disable(1),
                    enable(2)
                }
            ACCESS  read-write
            STATUS  mandatory
            DESCRIPTION
                "au-ais to ais"
            ::= { t3InsertAisAlmSetupEty 3 }

        t3InstHpUneq-UneqPToAis OBJECT-TYPE
            SYNTAX  INTEGER {
                    disable(1),
                    enable(2)
                }
            ACCESS  read-write
            STATUS  mandatory
            DESCRIPTION
                "hp-uneq to ais"
            ::= { t3InsertAisAlmSetupEty 4 }

        t3InstHpTim-TimPToAis OBJECT-TYPE
            SYNTAX  INTEGER {
                    disable(1),
                    enable(2)
                }
            ACCESS  read-write
            STATUS  mandatory
            DESCRIPTION
                "hp-tim to ais"
            ::= { t3InsertAisAlmSetupEty 5 }

        t3InstHpLom-LomToAis OBJECT-TYPE
            SYNTAX  INTEGER {
                    disable(1),
                    enable(2)
                }
            ACCESS  read-write
            STATUS  mandatory
            DESCRIPTION
                "hp-lom to ais"
            ::= { t3InsertAisAlmSetupEty 6 }

        t3InstHpPlm-PlmPToAis OBJECT-TYPE
            SYNTAX  INTEGER {
                    disable(1),
                    enable(2)
                }
            ACCESS  read-write
            STATUS  mandatory
            DESCRIPTION
                "hp-plm to ais"
            ::= { t3InsertAisAlmSetupEty 7 }

        t3InstTuAis-AisVToAis OBJECT-TYPE
            SYNTAX  INTEGER {
                    disable(1),
                    enable(2)
                }
            ACCESS  read-write
            STATUS  mandatory
            DESCRIPTION
                "tu-ais to ais"
            ::= { t3InsertAisAlmSetupEty 8 }

        t3InstTuLop-LopVToAis OBJECT-TYPE
            SYNTAX  INTEGER {
                    disable(1),
                    enable(2)
                }
            ACCESS  read-write
            STATUS  mandatory
            DESCRIPTION
                "tu-lop to ais"
            ::= { t3InsertAisAlmSetupEty 9 }

        t3InstLpUneq-UneqVToAis OBJECT-TYPE
            SYNTAX  INTEGER {
                    disable(1),
                    enable(2)
                }
            ACCESS  read-write
            STATUS  mandatory
            DESCRIPTION
                "lp-uneq to ais"
            ::= { t3InsertAisAlmSetupEty 10 }

        t3InstLpTim-TimVToAis OBJECT-TYPE
            SYNTAX  INTEGER {
                    disable(1),
                    enable(2)
                }
            ACCESS  read-write
            STATUS  mandatory
            DESCRIPTION
                "lp-tim to ais"
            ::= { t3InsertAisAlmSetupEty 11 }

        t3InstLpPlm-PlmVToAis OBJECT-TYPE
            SYNTAX  INTEGER {
                    disable(1),
                    enable(2)
                }
            ACCESS  read-write
            STATUS  mandatory
            DESCRIPTION
                "lp-plm to ais"
            ::= { t3InsertAisAlmSetupEty 12 }

--
--  T3 Current Alarm Status Table
--

    t3CurrAlmStatus       OBJECT IDENTIFIER ::= { t3Alarm 5 }

--
--   High Order Current Alarm Status
--

        t3HoSTSCurAlmStatusTab  OBJECT-TYPE
            SYNTAX  SEQUENCE OF T3HoSTSCurAlmStatusEty
            ACCESS  not-accessible
            STATUS  mandatory
            DESCRIPTION
                "High Order/STS current alarm status table"
            ::= { t3CurrAlmStatus 1 }

        t3HoSTSCurAlmStatusEty  OBJECT-TYPE
            SYNTAX  T3HoSTSCurAlmStatusEty
            ACCESS  not-accessible
            STATUS  mandatory
            DESCRIPTION
                "An entry in the alarm mask setup table"
            INDEX { t3HoSTSCurAlmUnit ,
                    t3HoSTSCurAlmPort }
            ::= { t3HoSTSCurAlmStatusTab 1 }

        T3HoSTSCurAlmStatusEty ::= SEQUENCE {
            t3HoSTSCurAlmUnit           UnitID,
            t3HoSTSCurAlmPort           PortID,
            t3HoSTSCurAlm-LOP           AlmStatus,
            t3HoSTSCurAlm-AIS           AlmStatus,
            t3HoSTSCurAlm-UNEQ          AlmStatus,
            t3HoSTSCurAlm-PLM           AlmStatus,
            t3HoSTSCurAlm-TIM           AlmStatus,
            t3HoSTSCurAlm-RDI-P         AlmStatus,
            t3HoSTSCurAlm-RDI-S         AlmStatus,
            t3HoSTSCurAlm-RDI-C         AlmStatus,
            t3HoSTSCurAlm-REI           AlmStatus,
            t3HoSTSCurAlm-B3-BIP        AlmStatus,
            t3HoSTSCurAlm-B3-LOM        AlmStatus
        }

        t3HoSTSCurAlmUnit  OBJECT-TYPE
            SYNTAX  UnitID
            ACCESS  read-only
            STATUS  mandatory
            DESCRIPTION
            "unit 1 to 4."
            ::= { t3HoSTSCurAlmStatusEty 1 }

        t3HoSTSCurAlmPort  OBJECT-TYPE
            SYNTAX  PortID
            ACCESS  read-only
            STATUS  mandatory
            DESCRIPTION
                "T3 Port 1 to 3"
            ::= { t3HoSTSCurAlmStatusEty 2 }

        t3HoSTSCurAlm-LOP  OBJECT-TYPE
            SYNTAX  AlmStatus
            ACCESS  read-only
            STATUS  mandatory
            DESCRIPTION
                "au-lop alarm status"
            ::= { t3HoSTSCurAlmStatusEty 3 }

        t3HoSTSCurAlm-AIS  OBJECT-TYPE
            SYNTAX  AlmStatus
            ACCESS  read-only
            STATUS  mandatory
            DESCRIPTION
                "au-ais alarm status"
            ::= { t3HoSTSCurAlmStatusEty 4 }

        t3HoSTSCurAlm-UNEQ  OBJECT-TYPE
            SYNTAX  AlmStatus
            ACCESS  read-only
            STATUS  mandatory
            DESCRIPTION
                "hp-uneq alarm status"
            ::= { t3HoSTSCurAlmStatusEty 5 }

        t3HoSTSCurAlm-PLM  OBJECT-TYPE
            SYNTAX  AlmStatus
            ACCESS  read-only
            STATUS  mandatory
            DESCRIPTION
                "hp-plm alarm status"
            ::= { t3HoSTSCurAlmStatusEty 6 }

        t3HoSTSCurAlm-TIM  OBJECT-TYPE
            SYNTAX  AlmStatus
            ACCESS  read-only
            STATUS  mandatory
            DESCRIPTION
                "hp-tim alarm status"
            ::= { t3HoSTSCurAlmStatusEty 7 }

        t3HoSTSCurAlm-RDI-P  OBJECT-TYPE
            SYNTAX  AlmStatus
            ACCESS  read-only
            STATUS  mandatory
            DESCRIPTION
                "hp-rdi-p alarm status"
            ::= { t3HoSTSCurAlmStatusEty 8 }

        t3HoSTSCurAlm-RDI-S  OBJECT-TYPE
            SYNTAX  AlmStatus
            ACCESS  read-only
            STATUS  mandatory
            DESCRIPTION
                "hp-rdi-s alarm status"
            ::= { t3HoSTSCurAlmStatusEty 9 }

        t3HoSTSCurAlm-RDI-C  OBJECT-TYPE
            SYNTAX  AlmStatus
            ACCESS  read-only
            STATUS  mandatory
            DESCRIPTION
                "hp-rdi-c alarm status"
            ::= { t3HoSTSCurAlmStatusEty 10 }

        t3HoSTSCurAlm-REI  OBJECT-TYPE
            SYNTAX  AlmStatus
            ACCESS  read-only
            STATUS  mandatory
            DESCRIPTION
                "hp-rei alarm status"
            ::= { t3HoSTSCurAlmStatusEty 11 }

        t3HoSTSCurAlm-B3-BIP  OBJECT-TYPE
            SYNTAX  AlmStatus
            ACCESS  read-only
            STATUS  mandatory
            DESCRIPTION
                "hp-bip alarm status"
            ::= { t3HoSTSCurAlmStatusEty 12 }

        t3HoSTSCurAlm-B3-LOM  OBJECT-TYPE
            SYNTAX  AlmStatus
            ACCESS  read-only
            STATUS  mandatory
            DESCRIPTION
                "hp-lom alarm status"
            ::= { t3HoSTSCurAlmStatusEty 13 }

--
--   Low Order Current Alarm Status
--

        t3LoVTCurAlmStatusTab  OBJECT-TYPE
            SYNTAX  SEQUENCE OF T3LoVTCurAlmStatusEty
            ACCESS  not-accessible
            STATUS  mandatory
            DESCRIPTION
                "Low Order/VT Alarm mask setup table"
            ::= { t3CurrAlmStatus 2 }

        t3LoVTCurAlmStatusEty  OBJECT-TYPE
            SYNTAX  T3LoVTCurAlmStatusEty
            ACCESS  not-accessible
            STATUS  mandatory
            DESCRIPTION
                "An entry in the alarm mask setup table"
            INDEX { t3LoVTCurAlmUnit ,
                    t3LoVTCurAlmPort ,
                    t3LoVTCurAlmChannel }
            ::= { t3LoVTCurAlmStatusTab 1 }

        T3LoVTCurAlmStatusEty ::= SEQUENCE {
            t3LoVTCurAlmUnit            UnitID,
            t3LoVTCurAlmPort            PortID,
            t3LoVTCurAlmChannel         ChannelNum,
            t3LoVTCurAlm-LOP            AlmStatus,
            t3LoVTCurAlm-AIS            AlmStatus,
            t3LoVTCurAlm-UNEQ           AlmStatus,
            t3LoVTCurAlm-PLM            AlmStatus,
            t3LoVTCurAlm-TIM            AlmStatus,
            t3LoVTCurAlm-RDI-P          AlmStatus,
            t3LoVTCurAlm-RDI-S          AlmStatus,
            t3LoVTCurAlm-RDI-C          AlmStatus,
            t3LoVTCurAlm-V5-REI         AlmStatus,
            t3LoVTCurAlm-V5-BIP         AlmStatus
        }

        t3LoVTCurAlmUnit  OBJECT-TYPE
            SYNTAX  UnitID
            ACCESS  read-only
            STATUS  mandatory
            DESCRIPTION
            "unit 1 to 4."
            ::= { t3LoVTCurAlmStatusEty 1 }

        t3LoVTCurAlmPort  OBJECT-TYPE
            SYNTAX  PortID
            ACCESS  read-only
            STATUS  mandatory
            DESCRIPTION
                "T3 Port 1 to 3"
            ::= { t3LoVTCurAlmStatusEty 2 }

        t3LoVTCurAlmChannel  OBJECT-TYPE
            SYNTAX  ChannelNum
            ACCESS  read-only
            STATUS  mandatory
            DESCRIPTION
                "T3 Channel 1 to 28"
            ::= { t3LoVTCurAlmStatusEty 3 }

        t3LoVTCurAlm-LOP  OBJECT-TYPE
            SYNTAX  AlmStatus
            ACCESS  read-only
            STATUS  mandatory
            DESCRIPTION
                "tu-lop alarm status"
            ::= { t3LoVTCurAlmStatusEty 4 }

        t3LoVTCurAlm-AIS  OBJECT-TYPE
            SYNTAX  AlmStatus
            ACCESS  read-only
            STATUS  mandatory
            DESCRIPTION
                "tu-ais alarm status"
            ::= { t3LoVTCurAlmStatusEty 5 }

        t3LoVTCurAlm-UNEQ  OBJECT-TYPE
            SYNTAX  AlmStatus
            ACCESS  read-only
            STATUS  mandatory
            DESCRIPTION
                "lp-uneq alarm status"
            ::= { t3LoVTCurAlmStatusEty 6 }

        t3LoVTCurAlm-PLM  OBJECT-TYPE
            SYNTAX  AlmStatus
            ACCESS  read-only
            STATUS  mandatory
            DESCRIPTION
                "lp-plm alarm status"
            ::= { t3LoVTCurAlmStatusEty 7 }

        t3LoVTCurAlm-TIM  OBJECT-TYPE
            SYNTAX  AlmStatus
            ACCESS  read-only
            STATUS  mandatory
            DESCRIPTION
                "lp-tim alarm status"
            ::= { t3LoVTCurAlmStatusEty 8 }

        t3LoVTCurAlm-RDI-P  OBJECT-TYPE
            SYNTAX  AlmStatus
            ACCESS  read-only
            STATUS  mandatory
            DESCRIPTION
                "lp-rdi-p alarm status"
            ::= { t3LoVTCurAlmStatusEty 9 }

        t3LoVTCurAlm-RDI-S  OBJECT-TYPE
            SYNTAX  AlmStatus
            ACCESS  read-only
            STATUS  mandatory
            DESCRIPTION
                "lp-rdi-s alarm status"
            ::= { t3LoVTCurAlmStatusEty 10 }

        t3LoVTCurAlm-RDI-C  OBJECT-TYPE
            SYNTAX  AlmStatus
            ACCESS  read-only
            STATUS  mandatory
            DESCRIPTION
                "lp-rdi-c alarm status"
            ::= { t3LoVTCurAlmStatusEty 11 }

        t3LoVTCurAlm-V5-REI  OBJECT-TYPE
            SYNTAX  AlmStatus
            ACCESS  read-only
            STATUS  mandatory
            DESCRIPTION
                "lp-rei alarm status"
            ::= { t3LoVTCurAlmStatusEty 12 }

        t3LoVTCurAlm-V5-BIP  OBJECT-TYPE
            SYNTAX  AlmStatus
            ACCESS  read-only
            STATUS  mandatory
            DESCRIPTION
                "lp-bip alarm status"
            ::= { t3LoVTCurAlmStatusEty 13 }

--
--   Line Alarm Current Alarm Status
--

        t3LineCurAlmStatusTab  OBJECT-TYPE
            SYNTAX  SEQUENCE OF T3LineCurAlmStatusEty
            ACCESS  not-accessible
            STATUS  mandatory
            DESCRIPTION
                "Line Alarm mask setup table"
            ::= { t3CurrAlmStatus 3 }

        t3LineCurAlmStatusEty  OBJECT-TYPE
            SYNTAX  T3LineCurAlmStatusEty
            ACCESS  not-accessible
            STATUS  mandatory
            DESCRIPTION
                "An entry in the alarm mask setup table"
            INDEX { t3LineCurAlmUnit ,
                    t3LineCurAlmPort }
            ::= { t3LineCurAlmStatusTab 1 }

        T3LineCurAlmStatusEty ::= SEQUENCE {
            t3LineCurAlmUnit            UnitID,
            t3LineCurAlmPort            PortID,
            t3LineCurAlm-LOS            AlmStatus,
            t3LineCurAlm-AIS            AlmStatus,
            t3LineCurAlm-UAS            AlmStatus,
            t3LineCurAlm-YELL           AlmStatus,
            t3LineCurAlm-LOF            AlmStatus,
            t3LineCurAlm-IDLE           AlmStatus,
            t3LineCurAlm-P-BITS         AlmStatus,
            t3LineCurAlm-C-BITS         AlmStatus
        }

        t3LineCurAlmUnit  OBJECT-TYPE
            SYNTAX  UnitID
            ACCESS  read-only
            STATUS  mandatory
            DESCRIPTION
            "unit 1 to 4."
            ::= { t3LineCurAlmStatusEty 1 }

        t3LineCurAlmPort  OBJECT-TYPE
            SYNTAX  PortID
            ACCESS  read-only
            STATUS  mandatory
            DESCRIPTION
                "T3 Port 1 to 3"
            ::= { t3LineCurAlmStatusEty 2 }

        t3LineCurAlm-LOS  OBJECT-TYPE
            SYNTAX  AlmStatus
            ACCESS  read-only
            STATUS  mandatory
            DESCRIPTION
                "line-los alarm status"
            ::= { t3LineCurAlmStatusEty 3 }

        t3LineCurAlm-AIS  OBJECT-TYPE
            SYNTAX  AlmStatus
            ACCESS  read-only
            STATUS  mandatory
            DESCRIPTION
                "line-ais alarm status"
            ::= { t3LineCurAlmStatusEty 4 }

        t3LineCurAlm-UAS  OBJECT-TYPE
            SYNTAX  AlmStatus
            ACCESS  read-only
            STATUS  mandatory
            DESCRIPTION
                "line-uas alarm status"
            ::= { t3LineCurAlmStatusEty 5 }

        t3LineCurAlm-YELL  OBJECT-TYPE
            SYNTAX  AlmStatus
            ACCESS  read-only
            STATUS  mandatory
            DESCRIPTION
                "line-yell alarm status"
            ::= { t3LineCurAlmStatusEty 6 }

        t3LineCurAlm-LOF  OBJECT-TYPE
            SYNTAX  AlmStatus
            ACCESS  read-only
            STATUS  mandatory
            DESCRIPTION
                "line-lof alarm status"
            ::= { t3LineCurAlmStatusEty 7 }

        t3LineCurAlm-IDLE  OBJECT-TYPE
            SYNTAX  AlmStatus
            ACCESS  read-only
            STATUS  mandatory
            DESCRIPTION
                "line-idle alarm status"
            ::= { t3LineCurAlmStatusEty 8 }

        t3LineCurAlm-P-BITS  OBJECT-TYPE
            SYNTAX  AlmStatus
            ACCESS  read-only
            STATUS  mandatory
            DESCRIPTION
                "line-p-bits alarm status"
            ::= { t3LineCurAlmStatusEty 9 }

        t3LineCurAlm-C-BITS  OBJECT-TYPE
            SYNTAX  AlmStatus
            ACCESS  read-only
            STATUS  mandatory
            DESCRIPTION
                "line-p-bits alarm status"
            ::= { t3LineCurAlmStatusEty 10 }

--
--   M13 Current Alarm Status
--

        t3M13CurAlmStatusTab  OBJECT-TYPE
            SYNTAX  SEQUENCE OF T3M13CurAlmStatusEty
            ACCESS  not-accessible
            STATUS  mandatory
            DESCRIPTION
                "M13 Alarm mask setup table"
            ::= { t3CurrAlmStatus 4 }

        t3M13CurAlmStatusEty  OBJECT-TYPE
            SYNTAX  T3M13CurAlmStatusEty
            ACCESS  not-accessible
            STATUS  mandatory
            DESCRIPTION
                "An entry in the alarm mask setup table"
            INDEX { t3M13CurAlmUnit ,
                    t3M13CurAlmPort ,
                    t3M13CurAlmChannel }
            ::= { t3M13CurAlmStatusTab 1 }

        T3M13CurAlmStatusEty ::= SEQUENCE {
            t3M13CurAlmUnit             UnitID,
            t3M13CurAlmPort             PortID,
            t3M13CurAlmChannel          ChannelNum,
            t3M13CurAlm-AIS             AlmStatus
        }

        t3M13CurAlmUnit  OBJECT-TYPE
            SYNTAX  UnitID
            ACCESS  read-only
            STATUS  mandatory
            DESCRIPTION
            "unit 1 to 4."
            ::= { t3M13CurAlmStatusEty 1 }

        t3M13CurAlmPort  OBJECT-TYPE
            SYNTAX  PortID
            ACCESS  read-only
            STATUS  mandatory
            DESCRIPTION
                "T3 Port 1 to 3"
            ::= { t3M13CurAlmStatusEty 2 }

        t3M13CurAlmChannel  OBJECT-TYPE
            SYNTAX  ChannelNum
            ACCESS  read-only
            STATUS  mandatory
            DESCRIPTION
                "T3 Channel 1 to 28"
            ::= { t3M13CurAlmStatusEty 3 }

        t3M13CurAlm-AIS  OBJECT-TYPE
            SYNTAX  AlmStatus
            ACCESS  read-only
            STATUS  mandatory
            DESCRIPTION
                "tu-ais alarm status"
            ::= { t3M13CurAlmStatusEty 4 }

--
--  T3 Current Active Alarm Summary Table
--
        t3CurrActAlmSummaryTab  OBJECT-TYPE
            SYNTAX  SEQUENCE OF T3CurrActAlmSummaryEty
            ACCESS  not-accessible
            STATUS  mandatory
            DESCRIPTION
                "T3 Current Active Alarm Summary Table."
            ::= { t3Alarm 6 }

        t3CurrActAlmSummaryEty  OBJECT-TYPE
            SYNTAX  T3CurrActAlmSummaryEty
            ACCESS  not-accessible
            STATUS  mandatory
            DESCRIPTION
                "t3 current active alarm summary entry"
            INDEX { t3AlmSumUnit ,
                    t3AlmSumIndex }
            ::= { t3CurrActAlmSummaryTab 1 }

        T3CurrActAlmSummaryEty ::= SEQUENCE {
            t3AlmSumUnit                UnitID,
            t3AlmSumIndex               INTEGER,
            t3AlmSumString              DisplayString (SIZE(0..255)),
            t3AlmSumUnitNum             CardID,
            t3AlmSumCardModel           CardModel,
            t3AlmSumPortNum             PortID,
            t3AlmSumChannel             ChannelNum,
            t3AlmSumAlmNum              AlarmNum,
            t3AlmSumStatus              AlmStatus,
            t3AlmSumSeverity            Severity
        }

        t3AlmSumUnit  OBJECT-TYPE
            SYNTAX  UnitID
            ACCESS  read-only
            STATUS  mandatory
            DESCRIPTION
            "unit 1 to 4."
            ::= { t3CurrActAlmSummaryEty 1 }

        t3AlmSumIndex  OBJECT-TYPE
            SYNTAX  INTEGER
            ACCESS  read-only
            STATUS  mandatory
            DESCRIPTION
                "Select Alarm Summary Index"
            ::= { t3CurrActAlmSummaryEty 2 }

        t3AlmSumString  OBJECT-TYPE
            SYNTAX  DisplayString (SIZE (0..255))
            ACCESS  read-only
            STATUS  mandatory
            DESCRIPTION
                "Alarm Summary String"
            ::= { t3CurrActAlmSummaryEty 3 }

        t3AlmSumUnitNum  OBJECT-TYPE
            SYNTAX  CardID
            ACCESS  read-only
            STATUS  mandatory
            DESCRIPTION
            "Xcu or Unit 1~4,11~16"
            ::= { t3CurrActAlmSummaryEty 4 }

        t3AlmSumCardModel  OBJECT-TYPE
            SYNTAX  CardModel
            ACCESS  read-only
            STATUS  mandatory
            DESCRIPTION
                "Card Model"
            ::= { t3CurrActAlmSummaryEty 5 }

        t3AlmSumPortNum  OBJECT-TYPE
            SYNTAX  PortID
            ACCESS  read-only
            STATUS  mandatory
            DESCRIPTION
                "Port number(1..3)"
            ::= { t3CurrActAlmSummaryEty 6 }

        t3AlmSumChannel  OBJECT-TYPE
            SYNTAX  ChannelNum
            ACCESS  read-only
            STATUS  mandatory
            DESCRIPTION
                "Channel number(1..28)"
            ::= { t3CurrActAlmSummaryEty 7 }

        t3AlmSumAlmNum  OBJECT-TYPE
            SYNTAX  AlarmNum
            ACCESS  read-only
            STATUS  mandatory
            DESCRIPTION
                "Alarm Num"
            ::= { t3CurrActAlmSummaryEty 8 }

        t3AlmSumStatus  OBJECT-TYPE
            SYNTAX  AlmStatus
            ACCESS  read-only
            STATUS  mandatory
            DESCRIPTION
                "The Status of Alarm"
            ::= { t3CurrActAlmSummaryEty 9 }

        t3AlmSumSeverity  OBJECT-TYPE
            SYNTAX  Severity
            ACCESS  read-only
            STATUS  mandatory
            DESCRIPTION
                "Alarm Severity"
            ::= { t3CurrActAlmSummaryEty 10 }

--
--  T3 Loopback & Diagnostics
--

    t3LoopbackAndDiagnostics           OBJECT IDENTIFIER ::= { t3-card 3 }

--
--  T3 Loopback Setup Table
--

        t3LoopbackSetupTab  OBJECT-TYPE
            SYNTAX  SEQUENCE OF T3LoopbackSetupEty
            ACCESS  not-accessible
            STATUS  mandatory
            DESCRIPTION
                "Loopback setup table"
            ::= { t3LoopbackAndDiagnostics 1 }

        t3LoopbackSetupEty  OBJECT-TYPE
            SYNTAX  T3LoopbackSetupEty
            ACCESS  not-accessible
            STATUS  mandatory
            DESCRIPTION
                "An entry in the loopback setup table"
            INDEX { t3LoopbackUnit ,
                    t3LoopbackPort }
            ::= { t3LoopbackSetupTab 1 }

        T3LoopbackSetupEty ::= SEQUENCE {
            t3LoopbackUnit              UnitID,
            t3LoopbackPort              PortID,
            t3LoopbackLoopbackType      INTEGER
        }

        t3LoopbackUnit  OBJECT-TYPE
            SYNTAX  UnitID
            ACCESS  read-only
            STATUS  mandatory
            DESCRIPTION
            "unit 1 to 4."
            ::= { t3LoopbackSetupEty 1 }

        t3LoopbackPort  OBJECT-TYPE
            SYNTAX  PortID
            ACCESS  read-only
            STATUS  mandatory
            DESCRIPTION
                "T3 Port 1 to 3"
            ::= { t3LoopbackSetupEty 2 }

        t3LoopbackLoopbackType  OBJECT-TYPE
            SYNTAX  INTEGER{
                    off(1),
                    local(2),
                    line(3)
                }
            ACCESS  read-write
            STATUS  mandatory
            DESCRIPTION
                "Loopback type"
            ::= { t3LoopbackSetupEty 3 }


--
--  T3 Diagnostics Setup Table
--

        t3DiagnosticsSetupTab  OBJECT-TYPE
            SYNTAX  SEQUENCE OF T3DiagnosticsSetupEty
            ACCESS  not-accessible
            STATUS  mandatory
            DESCRIPTION
                "Diagnostics setup table"
            ::= { t3LoopbackAndDiagnostics 2 }

        t3DiagnosticsSetupEty  OBJECT-TYPE
            SYNTAX  T3DiagnosticsSetupEty
            ACCESS  not-accessible
            STATUS  mandatory
            DESCRIPTION
                "An entry in the diagnostics setup table"
            INDEX { t3DiagUnit ,
                    t3DiagPort }
            ::= { t3DiagnosticsSetupTab 1 }

        T3DiagnosticsSetupEty ::= SEQUENCE {
            t3DiagUnit                  UnitID,
            t3DiagPort                  PortID,
            t3DiagBertDirection         INTEGER,
            t3DiagBertPattern           INTEGER,
            t3DiagBertAction            INTEGER,
            t3DiagBertStatus            INTEGER,
            t3DiagElapseSecond          INTEGER,
            t3DiagBitError              INTEGER,
            t3DiagErrorSecond           INTEGER,
            t3DiagSevereErrorSecond     INTEGER
        }

        t3DiagUnit  OBJECT-TYPE
            SYNTAX  UnitID
            ACCESS  read-only
            STATUS  mandatory
            DESCRIPTION
            "unit 1 to 4."
            ::= { t3DiagnosticsSetupEty 1 }

        t3DiagPort  OBJECT-TYPE
            SYNTAX  PortID
            ACCESS  read-only
            STATUS  mandatory
            DESCRIPTION
                "T3 Port 1 to 3"
            ::= { t3DiagnosticsSetupEty 2 }

        t3DiagBertDirection  OBJECT-TYPE
            SYNTAX  INTEGER{
                    optical-site(1),
                    line-site(2)
                }
            ACCESS  read-write
            STATUS  mandatory
            DESCRIPTION
                "BERT test direction"
            ::= { t3DiagnosticsSetupEty 3 }

        t3DiagBertPattern  OBJECT-TYPE
            SYNTAX  INTEGER{
                    off(1),
                    patt-2exp11-1(2),
                    patt-2exp15-1(3),
                    patt-2exp20-1(4),
                    patt-2exp23-1(5)
                }
            ACCESS  read-write
            STATUS  mandatory
            DESCRIPTION
                "BERT test pattern"
            ::= { t3DiagnosticsSetupEty 4 }

        t3DiagBertAction  OBJECT-TYPE
            SYNTAX  INTEGER{
                    none(0),
                    reset(1),
                    insert-error(2)
                }
            ACCESS  read-write
            STATUS  mandatory
            DESCRIPTION
                "BERT test action"
            ::= { t3DiagnosticsSetupEty 5 }

        t3DiagBertStatus  OBJECT-TYPE
            SYNTAX  INTEGER{
                    unsync(1),
                    sync(2)
                }
            ACCESS  read-only
            STATUS  mandatory
            DESCRIPTION
                "BERT status"
            ::= { t3DiagnosticsSetupEty 6 }

        t3DiagElapseSecond  OBJECT-TYPE
            SYNTAX  INTEGER
            ACCESS  read-only
            STATUS  mandatory
            DESCRIPTION
                "BERT elapsed time(s)"
            ::= { t3DiagnosticsSetupEty 7 }

        t3DiagBitError  OBJECT-TYPE
            SYNTAX  INTEGER
            ACCESS  read-only
            STATUS  mandatory
            DESCRIPTION
                "BERT Bit Error"
            ::= { t3DiagnosticsSetupEty 8 }

        t3DiagErrorSecond  OBJECT-TYPE
            SYNTAX  INTEGER
            ACCESS  read-only
            STATUS  mandatory
            DESCRIPTION
                "BERT Error Seconds"
            ::= { t3DiagnosticsSetupEty 9 }

        t3DiagSevereErrorSecond  OBJECT-TYPE
            SYNTAX  INTEGER
            ACCESS  read-only
            STATUS  mandatory
            DESCRIPTION
                "BERT SES"
            ::= { t3DiagnosticsSetupEty 10 }

--
--  T3 M13 Loopback Setup Table
--

        t3M13LoopbackSetupTab  OBJECT-TYPE
            SYNTAX  SEQUENCE OF T3M13LoopbackSetupEty
            ACCESS  not-accessible
            STATUS  mandatory
            DESCRIPTION
                "M13 Loopback setup table"
            ::= { t3LoopbackAndDiagnostics 3 }

        t3M13LoopbackSetupEty  OBJECT-TYPE
            SYNTAX  T3M13LoopbackSetupEty
            ACCESS  not-accessible
            STATUS  mandatory
            DESCRIPTION
                "An entry in the M13 loopback setup table"
            INDEX { t3M13LoopbackUnit ,
                    t3M13LoopbackPort ,
                    t3M13LoopbackChannel }
            ::= { t3M13LoopbackSetupTab 1 }

        T3M13LoopbackSetupEty ::= SEQUENCE {
            t3M13LoopbackUnit           UnitID,
            t3M13LoopbackPort           PortID,
            t3M13LoopbackChannel        ChannelNum,
            t3M13LoopbackLbType         INTEGER
        }

        t3M13LoopbackUnit  OBJECT-TYPE
            SYNTAX  UnitID
            ACCESS  read-only
            STATUS  mandatory
            DESCRIPTION
            "unit 1 to 4."
            ::= { t3M13LoopbackSetupEty 1 }

        t3M13LoopbackPort  OBJECT-TYPE
            SYNTAX  PortID
            ACCESS  read-only
            STATUS  mandatory
            DESCRIPTION
                "T3 Port 1 to 3"
            ::= { t3M13LoopbackSetupEty 2 }

        t3M13LoopbackChannel  OBJECT-TYPE
            SYNTAX  ChannelNum
            ACCESS  read-only
            STATUS  mandatory
            DESCRIPTION
                "T3 Channel 1 to 28"
            ::= { t3M13LoopbackSetupEty 3 }

        t3M13LoopbackLbType  OBJECT-TYPE
            SYNTAX  INTEGER{
                    off(1),
                    local(2),
                    line(3)
                }
            ACCESS  read-write
            STATUS  mandatory
            DESCRIPTION
                "Loopback type"
            ::= { t3M13LoopbackSetupEty 4 }


--
--  T3 M13 Diagnostics Setup Table
--

        t3M13DiagnosticsSetupTab  OBJECT-TYPE
            SYNTAX  SEQUENCE OF T3M13DiagnosticsSetupEty
            ACCESS  not-accessible
            STATUS  mandatory
            DESCRIPTION
                "M13 Diagnostics setup table"
            ::= { t3LoopbackAndDiagnostics 4 }

        t3M13DiagnosticsSetupEty  OBJECT-TYPE
            SYNTAX  T3M13DiagnosticsSetupEty
            ACCESS  not-accessible
            STATUS  mandatory
            DESCRIPTION
                "An entry in the M13 diagnostics setup table"
            INDEX { t3M13DiagUnit ,
                    t3M13DiagPort ,
                    t3M13DiagChannel }
            ::= { t3M13DiagnosticsSetupTab 1 }

        T3M13DiagnosticsSetupEty ::= SEQUENCE {
            t3M13DiagUnit               UnitID,
            t3M13DiagPort               PortID,
            t3M13DiagChannel            ChannelNum,
            t3M13DiagBertDirection      INTEGER,
            t3M13DiagBertPattern        INTEGER,
            t3M13DiagBertAction         INTEGER,
            t3M13DiagBertStatus         INTEGER,
            t3M13DiagElapseSecond       INTEGER,
            t3M13DiagBitError           INTEGER,
            t3M13DiagErrorSecond        INTEGER,
            t3M13DiagSevereErrorSec     INTEGER
        }

        t3M13DiagUnit  OBJECT-TYPE
            SYNTAX  UnitID
            ACCESS  read-only
            STATUS  mandatory
            DESCRIPTION
            "unit 1 to 4."
            ::= { t3M13DiagnosticsSetupEty 1 }

        t3M13DiagPort  OBJECT-TYPE
            SYNTAX  PortID
            ACCESS  read-only
            STATUS  mandatory
            DESCRIPTION
                "T3 Port 1 to 3"
            ::= { t3M13DiagnosticsSetupEty 2 }

        t3M13DiagChannel  OBJECT-TYPE
            SYNTAX  ChannelNum
            ACCESS  read-only
            STATUS  mandatory
            DESCRIPTION
                "T3 Channel 1 to 28"
            ::= { t3M13DiagnosticsSetupEty 3 }

        t3M13DiagBertDirection  OBJECT-TYPE
            SYNTAX  INTEGER{
                    optical-site(1),
                    line-site(2)
                }
            ACCESS  read-write
            STATUS  mandatory
            DESCRIPTION
                "BERT test direction"
            ::= { t3M13DiagnosticsSetupEty 4 }

        t3M13DiagBertPattern  OBJECT-TYPE
            SYNTAX  INTEGER{
                    off(1),
                    patt-2exp11-1(2),
                    patt-2exp15-1(3),
--                         patt-2exp20-1(4),
                    patt-2exp23-1(5)
                }
            ACCESS  read-write
            STATUS  mandatory
            DESCRIPTION
                "BERT test pattern"
            ::= { t3M13DiagnosticsSetupEty 5 }

        t3M13DiagBertAction  OBJECT-TYPE
            SYNTAX  INTEGER{
                    none(0),
                    reset(1),
                    insert-error(2)
                }
            ACCESS  read-write
            STATUS  mandatory
            DESCRIPTION
                "BERT test action"
            ::= { t3M13DiagnosticsSetupEty 6 }

        t3M13DiagBertStatus  OBJECT-TYPE
            SYNTAX  INTEGER{
                    unsync(1),
                    sync(2)
                }
            ACCESS  read-only
            STATUS  mandatory
            DESCRIPTION
                "BERT status"
            ::= { t3M13DiagnosticsSetupEty 7 }

        t3M13DiagElapseSecond  OBJECT-TYPE
            SYNTAX  INTEGER
            ACCESS  read-only
            STATUS  mandatory
            DESCRIPTION
                "BERT elapsed time(s)"
            ::= { t3M13DiagnosticsSetupEty 8 }

        t3M13DiagBitError  OBJECT-TYPE
            SYNTAX  INTEGER
            ACCESS  read-only
            STATUS  mandatory
            DESCRIPTION
                "BERT Bit Error"
            ::= { t3M13DiagnosticsSetupEty 9 }

        t3M13DiagErrorSecond  OBJECT-TYPE
            SYNTAX  INTEGER
            ACCESS  read-only
            STATUS  mandatory
            DESCRIPTION
                "BERT Error Seconds"
            ::= { t3M13DiagnosticsSetupEty 10 }

        t3M13DiagSevereErrorSec  OBJECT-TYPE
            SYNTAX  INTEGER
            ACCESS  read-only
            STATUS  mandatory
            DESCRIPTION
                "BERT SES"
            ::= { t3M13DiagnosticsSetupEty 11 }

--
--  T3 M13 Remote Loopback Setup Table
--

        t3M13RemoteLbSetupTab  OBJECT-TYPE
            SYNTAX  SEQUENCE OF T3M13RemoteLbSetupEty
            ACCESS  not-accessible
            STATUS  mandatory
            DESCRIPTION
                "M13 Remote Loopback setup table"
            ::= { t3LoopbackAndDiagnostics 5 }

        t3M13RemoteLbSetupEty  OBJECT-TYPE
            SYNTAX  T3M13RemoteLbSetupEty
            ACCESS  not-accessible
            STATUS  mandatory
            DESCRIPTION
                "An entry in the M13 remote loopback setup table"
            INDEX { t3M13RemoteLbUnit ,
                    t3M13RemoteLbPort ,
                    t3M13RemoteLbChannel }
            ::= { t3M13RemoteLbSetupTab 1 }

        T3M13RemoteLbSetupEty ::= SEQUENCE {
            t3M13RemoteLbUnit           UnitID,
            t3M13RemoteLbPort           PortID,
            t3M13RemoteLbChannel        ChannelNum,
            t3M13RemoteLbLbType         INTEGER
        }

        t3M13RemoteLbUnit  OBJECT-TYPE
            SYNTAX  UnitID
            ACCESS  read-only
            STATUS  mandatory
            DESCRIPTION
            "unit 1 to 4."
            ::= { t3M13RemoteLbSetupEty 1 }

        t3M13RemoteLbPort  OBJECT-TYPE
            SYNTAX  PortID
            ACCESS  read-only
            STATUS  mandatory
            DESCRIPTION
                "T3 Port 1 to 3"
            ::= { t3M13RemoteLbSetupEty 2 }

        t3M13RemoteLbChannel  OBJECT-TYPE
            SYNTAX  ChannelNum
            ACCESS  read-only
            STATUS  mandatory
            DESCRIPTION
                "T3 Channel 1 to 28"
            ::= { t3M13RemoteLbSetupEty 3 }

        t3M13RemoteLbLbType  OBJECT-TYPE
            SYNTAX  INTEGER{
                    off(1),
                    active(2)
                }
            ACCESS  read-write
            STATUS  mandatory
            DESCRIPTION
                "Remote RemoteLb type"
            ::= { t3M13RemoteLbSetupEty 4 }

--
--  T3 Performance
--

    t3Performance           OBJECT IDENTIFIER ::= { t3-card 4 }

--
--  T3 Performance Report
--

    t3PerformanceReport           OBJECT IDENTIFIER ::= { t3Performance 1 }

--
--  T3 Performance Report HoPath/STSPath Current Table
--

        t3HoPath-STSPathCurrTab  OBJECT-TYPE
            SYNTAX  SEQUENCE OF T3HoPath-STSPathCurrEty
            ACCESS  not-accessible
            STATUS  mandatory
            DESCRIPTION
                "Performance report current"
            ::= { t3PerformanceReport 1 }

        t3HoPath-STSPathCurrEty  OBJECT-TYPE
            SYNTAX  T3HoPath-STSPathCurrEty
            ACCESS  not-accessible
            STATUS  mandatory
            DESCRIPTION
                "An entry in the performance report current table"
            INDEX { t3HoSTSCurrUnit ,
                    t3HoSTSCurrPort ,
                    t3HoSTSCurrAnomalyType }
            ::= { t3HoPath-STSPathCurrTab 1 }

        T3HoPath-STSPathCurrEty ::= SEQUENCE {
            t3HoSTSCurrUnit             UnitID,
            t3HoSTSCurrPort             PortID,
            t3HoSTSCurrAnomalyType      HoPathPerfAnomalyType,
            t3HoSTSCurrEB-Count         INTEGER,
            t3HoSTSCurrBBE-Count        INTEGER,
            t3HoSTSCurrES-Count         INTEGER,
            t3HoSTSCurrUAS-Count        INTEGER,
            t3HoSTSCurrBES-Count        INTEGER,
            t3HoSTSCurrSES-Count        INTEGER,
            t3HoSTSCurr15MinTimeElaps   INTEGER,
            t3HoSTSCurr24hrValid15Min   INTEGER,
            t3HoSTSCurrDayValid15Min    INTEGER,
            t3HoSTSCurr7DayValidDays    INTEGER
        }

        t3HoSTSCurrUnit  OBJECT-TYPE
            SYNTAX  UnitID
            ACCESS  read-only
            STATUS  mandatory
            DESCRIPTION
            "unit 1 to 4."
            ::= { t3HoPath-STSPathCurrEty 1 }

        t3HoSTSCurrPort  OBJECT-TYPE
            SYNTAX  PortID
            ACCESS  read-only
            STATUS  mandatory
            DESCRIPTION
                "T3 Port 1 to 3"
            ::= { t3HoPath-STSPathCurrEty 2 }

        t3HoSTSCurrAnomalyType  OBJECT-TYPE
            SYNTAX  HoPathPerfAnomalyType
            ACCESS  read-only
            STATUS  mandatory
            DESCRIPTION
                "Performance report HoPath/STSPath Anomaly Type"
            ::= { t3HoPath-STSPathCurrEty 3 }

        t3HoSTSCurrEB-Count  OBJECT-TYPE
            SYNTAX  INTEGER
            ACCESS  read-only
            STATUS  mandatory
            DESCRIPTION
                "Current Error Block"
            ::= { t3HoPath-STSPathCurrEty 4 }

        t3HoSTSCurrBBE-Count  OBJECT-TYPE
            SYNTAX  INTEGER
            ACCESS  read-only
            STATUS  mandatory
            DESCRIPTION
                "Current Background Block Error"
            ::= { t3HoPath-STSPathCurrEty 5 }

        t3HoSTSCurrES-Count  OBJECT-TYPE
            SYNTAX  INTEGER
            ACCESS  read-only
            STATUS  mandatory
            DESCRIPTION
                "Error Second"
            ::= { t3HoPath-STSPathCurrEty 6 }

        t3HoSTSCurrUAS-Count  OBJECT-TYPE
            SYNTAX  INTEGER
            ACCESS  read-only
            STATUS  mandatory
            DESCRIPTION
                "Unavailable Second"
            ::= { t3HoPath-STSPathCurrEty 7 }

        t3HoSTSCurrBES-Count  OBJECT-TYPE
            SYNTAX  INTEGER
            ACCESS  read-only
            STATUS  mandatory
            DESCRIPTION
                "Background Error Second"
            ::= { t3HoPath-STSPathCurrEty 8 }

        t3HoSTSCurrSES-Count  OBJECT-TYPE
            SYNTAX  INTEGER
            ACCESS  read-only
            STATUS  mandatory
            DESCRIPTION
                "Severly Error Second"
            ::= { t3HoPath-STSPathCurrEty 9 }

        t3HoSTSCurr15MinTimeElaps  OBJECT-TYPE
            SYNTAX  INTEGER
            ACCESS  read-only
            STATUS  mandatory
            DESCRIPTION
                "Valid Seconds in Current 15-Min Interval"
            ::= { t3HoPath-STSPathCurrEty 10 }

        t3HoSTSCurr24hrValid15Min  OBJECT-TYPE
            SYNTAX  INTEGER
            ACCESS  read-only
            STATUS  mandatory
            DESCRIPTION
                "Valid 15-Min Intervals in Current 24-Hour Interval"
            ::= { t3HoPath-STSPathCurrEty 11 }

        t3HoSTSCurrDayValid15Min  OBJECT-TYPE
            SYNTAX  INTEGER
            ACCESS  read-only
            STATUS  mandatory
            DESCRIPTION
                "Valid 15-Min Intervals in Current Day"
            ::= { t3HoPath-STSPathCurrEty 12 }

        t3HoSTSCurr7DayValidDays  OBJECT-TYPE
            SYNTAX  INTEGER
            ACCESS  read-only
            STATUS  mandatory
            DESCRIPTION
                "Valid Days in Current Seven Day"
            ::= { t3HoPath-STSPathCurrEty 13 }


--
--  T3 Performance Report HoPath/STSPath Interval Table
--

        t3HoPath-STSPathIntvTab  OBJECT-TYPE
            SYNTAX  SEQUENCE OF T3HoPath-STSPathIntvEty
            ACCESS  not-accessible
            STATUS  mandatory
            DESCRIPTION
                "Performance report Inteval"
            ::= { t3PerformanceReport 2 }

        t3HoPath-STSPathIntvEty  OBJECT-TYPE
            SYNTAX  T3HoPath-STSPathIntvEty
            ACCESS  not-accessible
            STATUS  mandatory
            DESCRIPTION
                "An entry in the performance report interval table"
            INDEX { t3HoSTSIntvUnit ,
                    t3HoSTSIntvPort ,
                    t3HoSTSIntvAnomalyType ,
                    t3HoSTSIntvPeriod }
            ::= { t3HoPath-STSPathIntvTab 1 }

        T3HoPath-STSPathIntvEty ::= SEQUENCE {
            t3HoSTSIntvUnit             UnitID,
            t3HoSTSIntvPort             PortID,
            t3HoSTSIntvAnomalyType      HoPathPerfAnomalyType,
            t3HoSTSIntvPeriod           INTEGER (1..96),
            t3HoSTSIntvEB-Count         INTEGER,
            t3HoSTSIntvBBE-Count        INTEGER,
            t3HoSTSIntvES-Count         INTEGER,
            t3HoSTSIntvUAS-Count        INTEGER,
            t3HoSTSIntvBES-Count        INTEGER,
            t3HoSTSIntvSES-Count        INTEGER
        }

        t3HoSTSIntvUnit  OBJECT-TYPE
            SYNTAX  UnitID
            ACCESS  read-only
            STATUS  mandatory
            DESCRIPTION
            "unit 1 to 4."
            ::= { t3HoPath-STSPathIntvEty 1 }

        t3HoSTSIntvPort  OBJECT-TYPE
            SYNTAX  PortID
            ACCESS  read-only
            STATUS  mandatory
            DESCRIPTION
                "T3 Port 1 to 3"
            ::= { t3HoPath-STSPathIntvEty 2 }

        t3HoSTSIntvAnomalyType  OBJECT-TYPE
            SYNTAX  HoPathPerfAnomalyType
            ACCESS  read-only
            STATUS  mandatory
            DESCRIPTION
                "Performance report HoPath/STSPath Anomaly Type"
            ::= { t3HoPath-STSPathIntvEty 3 }

        t3HoSTSIntvPeriod  OBJECT-TYPE
            SYNTAX  INTEGER (1..96)
            ACCESS  read-only
            STATUS  mandatory
            DESCRIPTION
                "HoPath Interval Period"
            ::= { t3HoPath-STSPathIntvEty 4 }

        t3HoSTSIntvEB-Count  OBJECT-TYPE
            SYNTAX  INTEGER
            ACCESS  read-only
            STATUS  mandatory
            DESCRIPTION
                "Current Error Block"
            ::= { t3HoPath-STSPathIntvEty 5 }

        t3HoSTSIntvBBE-Count  OBJECT-TYPE
            SYNTAX  INTEGER
            ACCESS  read-only
            STATUS  mandatory
            DESCRIPTION
                "Current Background Block Error"
            ::= { t3HoPath-STSPathIntvEty 6 }

        t3HoSTSIntvES-Count  OBJECT-TYPE
            SYNTAX  INTEGER
            ACCESS  read-only
            STATUS  mandatory
            DESCRIPTION
                "Error Second"
            ::= { t3HoPath-STSPathIntvEty 7 }

        t3HoSTSIntvUAS-Count  OBJECT-TYPE
            SYNTAX  INTEGER
            ACCESS  read-only
            STATUS  mandatory
            DESCRIPTION
                "Unavailable Second"
            ::= { t3HoPath-STSPathIntvEty 8 }

        t3HoSTSIntvBES-Count  OBJECT-TYPE
            SYNTAX  INTEGER
            ACCESS  read-only
            STATUS  mandatory
            DESCRIPTION
                "Background Error Second"
            ::= { t3HoPath-STSPathIntvEty 9 }

        t3HoSTSIntvSES-Count  OBJECT-TYPE
            SYNTAX  INTEGER
            ACCESS  read-only
            STATUS  mandatory
            DESCRIPTION
                "Severly Error Second"
            ::= { t3HoPath-STSPathIntvEty 10 }


--
--  T3 Performance Report HoPath/STS-Path Seven Days Table
--

        t3HoPath-STSPath7DaysTab  OBJECT-TYPE
            SYNTAX  SEQUENCE OF T3HoPath-STSPath7DaysEty
            ACCESS  not-accessible
            STATUS  mandatory
            DESCRIPTION
                "Performance report Seven Days"
            ::= { t3PerformanceReport 3 }

        t3HoPath-STSPath7DaysEty  OBJECT-TYPE
            SYNTAX  T3HoPath-STSPath7DaysEty
            ACCESS  not-accessible
            STATUS  mandatory
            DESCRIPTION
                "An entry in the performance report seven days table"
            INDEX { t3HoSTS7DaysUnit ,
                    t3HoSTS7DaysPort ,
                    t3HoSTS7DaysAnomalyType ,
                    t3HoSTS7DaysDayIndex }
            ::= { t3HoPath-STSPath7DaysTab 1 }

        T3HoPath-STSPath7DaysEty ::= SEQUENCE {
            t3HoSTS7DaysUnit            UnitID,
            t3HoSTS7DaysPort            PortID,
            t3HoSTS7DaysAnomalyType     HoPathPerfAnomalyType,
            t3HoSTS7DaysDayIndex        INTEGER (1..7),
            t3HoSTS7DaysDate            DisplayString (SIZE (0..255) ),
            t3HoSTS7DaysEB-Count        INTEGER,
            t3HoSTS7DaysBBE-Count       INTEGER,
            t3HoSTS7DaysES-Count        INTEGER,
            t3HoSTS7DaysUAS-Count       INTEGER,
            t3HoSTS7DaysBES-Count       INTEGER,
            t3HoSTS7DaysSES-Count       INTEGER
        }

        t3HoSTS7DaysUnit  OBJECT-TYPE
            SYNTAX  UnitID
            ACCESS  read-only
            STATUS  mandatory
            DESCRIPTION
            "unit 1 to 4."
            ::= { t3HoPath-STSPath7DaysEty 1 }

        t3HoSTS7DaysPort  OBJECT-TYPE
            SYNTAX  PortID
            ACCESS  read-only
            STATUS  mandatory
            DESCRIPTION
                "T3 Port 1 to 3"
            ::= { t3HoPath-STSPath7DaysEty 2 }

        t3HoSTS7DaysAnomalyType  OBJECT-TYPE
            SYNTAX  HoPathPerfAnomalyType
            ACCESS  read-only
            STATUS  mandatory
            DESCRIPTION
                "Performance report HoPath/STSPath Anomaly Type"
            ::= { t3HoPath-STSPath7DaysEty 3 }

        t3HoSTS7DaysDayIndex  OBJECT-TYPE
            SYNTAX  INTEGER (1..7)
            ACCESS  read-only
            STATUS  mandatory
            DESCRIPTION
                "HoPath Seven Days day index"
            ::= { t3HoPath-STSPath7DaysEty 4 }

        t3HoSTS7DaysDate  OBJECT-TYPE
            SYNTAX  DisplayString (SIZE (0..255) )
            ACCESS  read-only
            STATUS  mandatory
            DESCRIPTION
                "Seven Days Date"
            ::= { t3HoPath-STSPath7DaysEty 5 }

        t3HoSTS7DaysEB-Count  OBJECT-TYPE
            SYNTAX  INTEGER
            ACCESS  read-only
            STATUS  mandatory
            DESCRIPTION
                "Current Error Block"
            ::= { t3HoPath-STSPath7DaysEty 6 }

        t3HoSTS7DaysBBE-Count  OBJECT-TYPE
            SYNTAX  INTEGER
            ACCESS  read-only
            STATUS  mandatory
            DESCRIPTION
                "Current Background Block Error"
            ::= { t3HoPath-STSPath7DaysEty 7 }

        t3HoSTS7DaysES-Count  OBJECT-TYPE
            SYNTAX  INTEGER
            ACCESS  read-only
            STATUS  mandatory
            DESCRIPTION
                "Error Second"
            ::= { t3HoPath-STSPath7DaysEty 8 }

        t3HoSTS7DaysUAS-Count  OBJECT-TYPE
            SYNTAX  INTEGER
            ACCESS  read-only
            STATUS  mandatory
            DESCRIPTION
                "Unavailable Second"
            ::= { t3HoPath-STSPath7DaysEty 9 }

        t3HoSTS7DaysBES-Count  OBJECT-TYPE
            SYNTAX  INTEGER
            ACCESS  read-only
            STATUS  mandatory
            DESCRIPTION
                "Background Error Second"
            ::= { t3HoPath-STSPath7DaysEty 10 }

        t3HoSTS7DaysSES-Count  OBJECT-TYPE
            SYNTAX  INTEGER
            ACCESS  read-only
            STATUS  mandatory
            DESCRIPTION
                "Severly Error Second"
            ::= { t3HoPath-STSPath7DaysEty 11 }


--
--  T3 Performance Report HoPath/STSPath Total Table
--

        t3HoPath-STSPathTotalTab  OBJECT-TYPE
            SYNTAX  SEQUENCE OF T3HoPath-STSPathTotalEty
            ACCESS  not-accessible
            STATUS  mandatory
            DESCRIPTION
                "Performance report Total"
            ::= { t3PerformanceReport 4 }

        t3HoPath-STSPathTotalEty  OBJECT-TYPE
            SYNTAX  T3HoPath-STSPathTotalEty
            ACCESS  not-accessible
            STATUS  mandatory
            DESCRIPTION
                "An entry in the performance report total table"
            INDEX { t3HoSTSTotalUnit ,
                    t3HoSTSTotalPort ,
                    t3HoSTSTotalAnomalyType }
            ::= { t3HoPath-STSPathTotalTab 1 }

        T3HoPath-STSPathTotalEty ::= SEQUENCE {
            t3HoSTSTotalUnit            UnitID,
            t3HoSTSTotalPort            PortID,
            t3HoSTSTotalAnomalyType     HoPathPerfAnomalyType,
            t3HoSTSTotalEB-Count        INTEGER,
            t3HoSTSTotalBBE-Count       INTEGER,
            t3HoSTSTotalES-Count        INTEGER,
            t3HoSTSTotalUAS-Count       INTEGER,
            t3HoSTSTotalBES-Count       INTEGER,
            t3HoSTSTotalSES-Count       INTEGER
        }

        t3HoSTSTotalUnit  OBJECT-TYPE
            SYNTAX  UnitID
            ACCESS  read-only
            STATUS  mandatory
            DESCRIPTION
            "unit 1 to 4."
            ::= { t3HoPath-STSPathTotalEty 1 }

        t3HoSTSTotalPort  OBJECT-TYPE
            SYNTAX  PortID
            ACCESS  read-only
            STATUS  mandatory
            DESCRIPTION
                "T3 Port 1 to 3"
            ::= { t3HoPath-STSPathTotalEty 2 }

        t3HoSTSTotalAnomalyType  OBJECT-TYPE
            SYNTAX  HoPathPerfAnomalyType
            ACCESS  read-only
            STATUS  mandatory
            DESCRIPTION
                "Performance report HoPath/STSPath Anomaly Type"
            ::= { t3HoPath-STSPathTotalEty 3 }

        t3HoSTSTotalEB-Count  OBJECT-TYPE
            SYNTAX  INTEGER
            ACCESS  read-only
            STATUS  mandatory
            DESCRIPTION
                "Current Error Block"
            ::= { t3HoPath-STSPathTotalEty 4 }

        t3HoSTSTotalBBE-Count  OBJECT-TYPE
            SYNTAX  INTEGER
            ACCESS  read-only
            STATUS  mandatory
            DESCRIPTION
                "Current Background Block Error"
            ::= { t3HoPath-STSPathTotalEty 5 }

        t3HoSTSTotalES-Count  OBJECT-TYPE
            SYNTAX  INTEGER
            ACCESS  read-only
            STATUS  mandatory
            DESCRIPTION
                "Error Second"
            ::= { t3HoPath-STSPathTotalEty 6 }

        t3HoSTSTotalUAS-Count  OBJECT-TYPE
            SYNTAX  INTEGER
            ACCESS  read-only
            STATUS  mandatory
            DESCRIPTION
                "Unavailable Second"
            ::= { t3HoPath-STSPathTotalEty 7 }

        t3HoSTSTotalBES-Count  OBJECT-TYPE
            SYNTAX  INTEGER
            ACCESS  read-only
            STATUS  mandatory
            DESCRIPTION
                "Background Error Second"
            ::= { t3HoPath-STSPathTotalEty 8 }

        t3HoSTSTotalSES-Count  OBJECT-TYPE
            SYNTAX  INTEGER
            ACCESS  read-only
            STATUS  mandatory
            DESCRIPTION
                "Severly Error Second"
            ::= { t3HoPath-STSPathTotalEty 9 }

--
--  T3 Performance Report LoPath/VTPath Current Table
--

        t3LoPath-VTPathCurrTab  OBJECT-TYPE
            SYNTAX  SEQUENCE OF T3LoPath-VTPathCurrEty
            ACCESS  not-accessible
            STATUS  mandatory
            DESCRIPTION
                "Performance report current"
            ::= { t3PerformanceReport 5 }

        t3LoPath-VTPathCurrEty  OBJECT-TYPE
            SYNTAX  T3LoPath-VTPathCurrEty
            ACCESS  not-accessible
            STATUS  mandatory
            DESCRIPTION
                "An entry in the performance report current table"
            INDEX { t3LoVTCurrUnit ,
                    t3LoVTCurrPort ,
                    t3LoVTCurrChannel ,
                    t3LoVTCurrAnomalyType }
            ::= { t3LoPath-VTPathCurrTab 1 }

        T3LoPath-VTPathCurrEty ::= SEQUENCE {
            t3LoVTCurrUnit              UnitID,
            t3LoVTCurrPort              PortID,
            t3LoVTCurrChannel           ChannelNum,
            t3LoVTCurrAnomalyType       LoPathPerfAnomalyType,
            t3LoVTCurrEB-Count          INTEGER,
            t3LoVTCurrBBE-Count         INTEGER,
            t3LoVTCurrES-Count          INTEGER,
            t3LoVTCurrUAS-Count         INTEGER,
            t3LoVTCurrBES-Count         INTEGER,
            t3LoVTCurrSES-Count         INTEGER,
            t3LoVTCurr15MinTimeElaps    INTEGER,
            t3LoVTCurr24hrValid15Min    INTEGER,
            t3LoVTCurrDayValid15Min     INTEGER,
            t3LoVTCurr7DayValidDays     INTEGER
        }

        t3LoVTCurrUnit  OBJECT-TYPE
            SYNTAX  UnitID
            ACCESS  read-only
            STATUS  mandatory
            DESCRIPTION
            "unit 1 to 4."
            ::= { t3LoPath-VTPathCurrEty 1 }

        t3LoVTCurrPort  OBJECT-TYPE
            SYNTAX  PortID
            ACCESS  read-only
            STATUS  mandatory
            DESCRIPTION
                "T3 Port 1 to 3"
            ::= { t3LoPath-VTPathCurrEty 2 }

        t3LoVTCurrChannel  OBJECT-TYPE
            SYNTAX  ChannelNum
            ACCESS  read-only
            STATUS  mandatory
            DESCRIPTION
                "T3 Channel 1 to 28"
            ::= { t3LoPath-VTPathCurrEty 3 }

        t3LoVTCurrAnomalyType  OBJECT-TYPE
            SYNTAX  LoPathPerfAnomalyType
            ACCESS  read-only
            STATUS  mandatory
            DESCRIPTION
                "Performance report LoPath/VTPath Anomaly Type"
            ::= { t3LoPath-VTPathCurrEty 4 }

        t3LoVTCurrEB-Count  OBJECT-TYPE
            SYNTAX  INTEGER
            ACCESS  read-only
            STATUS  mandatory
            DESCRIPTION
                "Current Error Block"
            ::= { t3LoPath-VTPathCurrEty 5 }

        t3LoVTCurrBBE-Count  OBJECT-TYPE
            SYNTAX  INTEGER
            ACCESS  read-only
            STATUS  mandatory
            DESCRIPTION
                "Current Background Block Error"
            ::= { t3LoPath-VTPathCurrEty 6 }

        t3LoVTCurrES-Count  OBJECT-TYPE
            SYNTAX  INTEGER
            ACCESS  read-only
            STATUS  mandatory
            DESCRIPTION
                "Error Second"
            ::= { t3LoPath-VTPathCurrEty 7 }

        t3LoVTCurrUAS-Count  OBJECT-TYPE
            SYNTAX  INTEGER
            ACCESS  read-only
            STATUS  mandatory
            DESCRIPTION
                "Unavailable Second"
            ::= { t3LoPath-VTPathCurrEty 8 }

        t3LoVTCurrBES-Count  OBJECT-TYPE
            SYNTAX  INTEGER
            ACCESS  read-only
            STATUS  mandatory
            DESCRIPTION
                "Background Error Second"
            ::= { t3LoPath-VTPathCurrEty 9 }

        t3LoVTCurrSES-Count  OBJECT-TYPE
            SYNTAX  INTEGER
            ACCESS  read-only
            STATUS  mandatory
            DESCRIPTION
                "Severly Error Second"
            ::= { t3LoPath-VTPathCurrEty 10 }

        t3LoVTCurr15MinTimeElaps  OBJECT-TYPE
            SYNTAX  INTEGER
            ACCESS  read-only
            STATUS  mandatory
            DESCRIPTION
                "Valid Seconds in Current 15-Min Interval"
            ::= { t3LoPath-VTPathCurrEty 11 }

        t3LoVTCurr24hrValid15Min  OBJECT-TYPE
            SYNTAX  INTEGER
            ACCESS  read-only
            STATUS  mandatory
            DESCRIPTION
                "Valid 15-Min Intervals in Current 24-Hour Interval"
            ::= { t3LoPath-VTPathCurrEty 12 }

        t3LoVTCurrDayValid15Min  OBJECT-TYPE
            SYNTAX  INTEGER
            ACCESS  read-only
            STATUS  mandatory
            DESCRIPTION
                "Valid 15-Min Intervals in Current Day"
            ::= { t3LoPath-VTPathCurrEty 13 }

        t3LoVTCurr7DayValidDays  OBJECT-TYPE
            SYNTAX  INTEGER
            ACCESS  read-only
            STATUS  mandatory
            DESCRIPTION
                "Valid Days in Current Seven Day"
            ::= { t3LoPath-VTPathCurrEty 14 }


--
--  T3 Performance Report LoPath/VTPath Interval Table
--

        t3LoPath-VTPathIntvTab  OBJECT-TYPE
            SYNTAX  SEQUENCE OF T3LoPath-VTPathIntvEty
            ACCESS  not-accessible
            STATUS  mandatory
            DESCRIPTION
                "Performance report Inteval"
            ::= { t3PerformanceReport 6 }

        t3LoPath-VTPathIntvEty  OBJECT-TYPE
            SYNTAX  T3LoPath-VTPathIntvEty
            ACCESS  not-accessible
            STATUS  mandatory
            DESCRIPTION
                "An entry in the performance report interval table"
            INDEX { t3LoVTIntvUnit ,
                    t3LoVTIntvPort ,
                    t3LoVTIntvChannel ,
                    t3LoVTIntvAnomalyType ,
                    t3LoVTIntvPeriod }
            ::= { t3LoPath-VTPathIntvTab 1 }

        T3LoPath-VTPathIntvEty ::= SEQUENCE {
            t3LoVTIntvUnit              UnitID,
            t3LoVTIntvPort              PortID,
            t3LoVTIntvChannel           ChannelNum,
            t3LoVTIntvAnomalyType       LoPathPerfAnomalyType,
            t3LoVTIntvPeriod            INTEGER (1..96),
            t3LoVTIntvEB-Count          INTEGER,
            t3LoVTIntvBBE-Count         INTEGER,
            t3LoVTIntvES-Count          INTEGER,
            t3LoVTIntvUAS-Count         INTEGER,
            t3LoVTIntvBES-Count         INTEGER,
            t3LoVTIntvSES-Count         INTEGER
        }

        t3LoVTIntvUnit  OBJECT-TYPE
            SYNTAX  UnitID
            ACCESS  read-only
            STATUS  mandatory
            DESCRIPTION
            "unit 1 to 4."
            ::= { t3LoPath-VTPathIntvEty 1 }

        t3LoVTIntvPort  OBJECT-TYPE
            SYNTAX  PortID
            ACCESS  read-only
            STATUS  mandatory
            DESCRIPTION
                "T3 Port 1 to 3"
            ::= { t3LoPath-VTPathIntvEty 2 }

        t3LoVTIntvChannel  OBJECT-TYPE
            SYNTAX  ChannelNum
            ACCESS  read-only
            STATUS  mandatory
            DESCRIPTION
                "T3 Channel 1 to 28"
            ::= { t3LoPath-VTPathIntvEty 3 }

        t3LoVTIntvAnomalyType  OBJECT-TYPE
            SYNTAX  LoPathPerfAnomalyType
            ACCESS  read-only
            STATUS  mandatory
            DESCRIPTION
                "Performance report LoPath/VTPath Anomaly Type"
            ::= { t3LoPath-VTPathIntvEty 4 }

        t3LoVTIntvPeriod  OBJECT-TYPE
            SYNTAX  INTEGER (1..96)
            ACCESS  read-only
            STATUS  mandatory
            DESCRIPTION
                "LoPath Interval Period"
            ::= { t3LoPath-VTPathIntvEty 5 }

        t3LoVTIntvEB-Count  OBJECT-TYPE
            SYNTAX  INTEGER
            ACCESS  read-only
            STATUS  mandatory
            DESCRIPTION
                "Current Error Block"
            ::= { t3LoPath-VTPathIntvEty 6 }

        t3LoVTIntvBBE-Count  OBJECT-TYPE
            SYNTAX  INTEGER
            ACCESS  read-only
            STATUS  mandatory
            DESCRIPTION
                "Current Background Block Error"
            ::= { t3LoPath-VTPathIntvEty 7 }

        t3LoVTIntvES-Count  OBJECT-TYPE
            SYNTAX  INTEGER
            ACCESS  read-only
            STATUS  mandatory
            DESCRIPTION
                "Error Second"
            ::= { t3LoPath-VTPathIntvEty 8 }

        t3LoVTIntvUAS-Count  OBJECT-TYPE
            SYNTAX  INTEGER
            ACCESS  read-only
            STATUS  mandatory
            DESCRIPTION
                "Unavailable Second"
            ::= { t3LoPath-VTPathIntvEty 9 }

        t3LoVTIntvBES-Count  OBJECT-TYPE
            SYNTAX  INTEGER
            ACCESS  read-only
            STATUS  mandatory
            DESCRIPTION
                "Background Error Second"
            ::= { t3LoPath-VTPathIntvEty 10 }

        t3LoVTIntvSES-Count  OBJECT-TYPE
            SYNTAX  INTEGER
            ACCESS  read-only
            STATUS  mandatory
            DESCRIPTION
                "Severly Error Second"
            ::= { t3LoPath-VTPathIntvEty 11 }


--
--  T3 Performance Report LoPath/VT-Path Seven Days Table
--

        t3LoPath-VTPath7DaysTab  OBJECT-TYPE
            SYNTAX  SEQUENCE OF T3LoPath-VTPath7DaysEty
            ACCESS  not-accessible
            STATUS  mandatory
            DESCRIPTION
                "Performance report Seven Days"
            ::= { t3PerformanceReport 7 }

        t3LoPath-VTPath7DaysEty  OBJECT-TYPE
            SYNTAX  T3LoPath-VTPath7DaysEty
            ACCESS  not-accessible
            STATUS  mandatory
            DESCRIPTION
                "An entry in the performance report seven days table"
            INDEX { t3LoVT7DaysUnit ,
                    t3LoVT7DaysPort ,
                    t3LoVT7DaysChannel ,
                    t3LoVT7DaysAnomalyType ,
                    t3LoVT7DaysDayIndex }
            ::= { t3LoPath-VTPath7DaysTab 1 }

        T3LoPath-VTPath7DaysEty ::= SEQUENCE {
            t3LoVT7DaysUnit             UnitID,
            t3LoVT7DaysPort             PortID,
            t3LoVT7DaysChannel          ChannelNum,
            t3LoVT7DaysAnomalyType      LoPathPerfAnomalyType,
            t3LoVT7DaysDayIndex         INTEGER (1..7),
            t3LoVT7DaysDate             DisplayString (SIZE (0..255) ),
            t3LoVT7DaysEB-Count         INTEGER,
            t3LoVT7DaysBBE-Count        INTEGER,
            t3LoVT7DaysES-Count         INTEGER,
            t3LoVT7DaysUAS-Count        INTEGER,
            t3LoVT7DaysBES-Count        INTEGER,
            t3LoVT7DaysSES-Count        INTEGER
        }

        t3LoVT7DaysUnit  OBJECT-TYPE
            SYNTAX  UnitID
            ACCESS  read-only
            STATUS  mandatory
            DESCRIPTION
            "unit 1 to 4."
            ::= { t3LoPath-VTPath7DaysEty 1 }

        t3LoVT7DaysPort  OBJECT-TYPE
            SYNTAX  PortID
            ACCESS  read-only
            STATUS  mandatory
            DESCRIPTION
                "T3 Port 1 to 3"
            ::= { t3LoPath-VTPath7DaysEty 2 }

        t3LoVT7DaysChannel  OBJECT-TYPE
            SYNTAX  ChannelNum
            ACCESS  read-only
            STATUS  mandatory
            DESCRIPTION
                "T3 Channel 1 to 28"
            ::= { t3LoPath-VTPath7DaysEty 3 }

        t3LoVT7DaysAnomalyType  OBJECT-TYPE
            SYNTAX  LoPathPerfAnomalyType
            ACCESS  read-only
            STATUS  mandatory
            DESCRIPTION
                "Performance report LoPath/VTPath Anomaly Type"
            ::= { t3LoPath-VTPath7DaysEty 4 }

        t3LoVT7DaysDayIndex  OBJECT-TYPE
            SYNTAX  INTEGER (1..7)
            ACCESS  read-only
            STATUS  mandatory
            DESCRIPTION
                "LoPath Seven Days day index"
            ::= { t3LoPath-VTPath7DaysEty 5 }

        t3LoVT7DaysDate  OBJECT-TYPE
            SYNTAX  DisplayString (SIZE (0..255) )
            ACCESS  read-only
            STATUS  mandatory
            DESCRIPTION
                "Seven Days Date"
            ::= { t3LoPath-VTPath7DaysEty 6 }

        t3LoVT7DaysEB-Count  OBJECT-TYPE
            SYNTAX  INTEGER
            ACCESS  read-only
            STATUS  mandatory
            DESCRIPTION
                "Current Error Block"
            ::= { t3LoPath-VTPath7DaysEty 7 }

        t3LoVT7DaysBBE-Count  OBJECT-TYPE
            SYNTAX  INTEGER
            ACCESS  read-only
            STATUS  mandatory
            DESCRIPTION
                "Current Background Block Error"
            ::= { t3LoPath-VTPath7DaysEty 8 }

        t3LoVT7DaysES-Count  OBJECT-TYPE
            SYNTAX  INTEGER
            ACCESS  read-only
            STATUS  mandatory
            DESCRIPTION
                "Error Second"
            ::= { t3LoPath-VTPath7DaysEty 9 }

        t3LoVT7DaysUAS-Count  OBJECT-TYPE
            SYNTAX  INTEGER
            ACCESS  read-only
            STATUS  mandatory
            DESCRIPTION
                "Unavailable Second"
            ::= { t3LoPath-VTPath7DaysEty 10 }

        t3LoVT7DaysBES-Count  OBJECT-TYPE
            SYNTAX  INTEGER
            ACCESS  read-only
            STATUS  mandatory
            DESCRIPTION
                "Background Error Second"
            ::= { t3LoPath-VTPath7DaysEty 11 }

        t3LoVT7DaysSES-Count  OBJECT-TYPE
            SYNTAX  INTEGER
            ACCESS  read-only
            STATUS  mandatory
            DESCRIPTION
                "Severly Error Second"
            ::= { t3LoPath-VTPath7DaysEty 12 }


--
--  T3 Performance Report LoPath/VTPath Total Table
--

        t3LoPath-VTPathTotalTab  OBJECT-TYPE
            SYNTAX  SEQUENCE OF T3LoPath-VTPathTotalEty
            ACCESS  not-accessible
            STATUS  mandatory
            DESCRIPTION
                "Performance report Total"
            ::= { t3PerformanceReport 8 }

        t3LoPath-VTPathTotalEty  OBJECT-TYPE
            SYNTAX  T3LoPath-VTPathTotalEty
            ACCESS  not-accessible
            STATUS  mandatory
            DESCRIPTION
                "An entry in the performance report total table"
            INDEX { t3LoVTTotalUnit ,
                    t3LoVTTotalPort ,
                    t3LoVTTotalChannel ,
                    t3LoVTTotalAnomalyType }
            ::= { t3LoPath-VTPathTotalTab 1 }

        T3LoPath-VTPathTotalEty ::= SEQUENCE {
            t3LoVTTotalUnit             UnitID,
            t3LoVTTotalPort             PortID,
            t3LoVTTotalChannel          ChannelNum,
            t3LoVTTotalAnomalyType      LoPathPerfAnomalyType,
            t3LoVTTotalEB-Count         INTEGER,
            t3LoVTTotalBBE-Count        INTEGER,
            t3LoVTTotalES-Count         INTEGER,
            t3LoVTTotalUAS-Count        INTEGER,
            t3LoVTTotalBES-Count        INTEGER,
            t3LoVTTotalSES-Count        INTEGER
        }

        t3LoVTTotalUnit  OBJECT-TYPE
            SYNTAX  UnitID
            ACCESS  read-only
            STATUS  mandatory
            DESCRIPTION
            "unit 1 to 4."
            ::= { t3LoPath-VTPathTotalEty 1 }

        t3LoVTTotalPort  OBJECT-TYPE
            SYNTAX  PortID
            ACCESS  read-only
            STATUS  mandatory
            DESCRIPTION
                "T3 Port 1 to 3"
            ::= { t3LoPath-VTPathTotalEty 2 }

        t3LoVTTotalChannel  OBJECT-TYPE
            SYNTAX  ChannelNum
            ACCESS  read-only
            STATUS  mandatory
            DESCRIPTION
                "T3 Channel 1 to 28"
            ::= { t3LoPath-VTPathTotalEty 3 }

        t3LoVTTotalAnomalyType  OBJECT-TYPE
            SYNTAX  LoPathPerfAnomalyType
            ACCESS  read-only
            STATUS  mandatory
            DESCRIPTION
                "Performance report LoPath/VTPath Anomaly Type"
            ::= { t3LoPath-VTPathTotalEty 4 }

        t3LoVTTotalEB-Count  OBJECT-TYPE
            SYNTAX  INTEGER
            ACCESS  read-only
            STATUS  mandatory
            DESCRIPTION
                "Current Error Block"
            ::= { t3LoPath-VTPathTotalEty 5 }

        t3LoVTTotalBBE-Count  OBJECT-TYPE
            SYNTAX  INTEGER
            ACCESS  read-only
            STATUS  mandatory
            DESCRIPTION
                "Current Background Block Error"
            ::= { t3LoPath-VTPathTotalEty 6 }

        t3LoVTTotalES-Count  OBJECT-TYPE
            SYNTAX  INTEGER
            ACCESS  read-only
            STATUS  mandatory
            DESCRIPTION
                "Error Second"
            ::= { t3LoPath-VTPathTotalEty 7 }

        t3LoVTTotalUAS-Count  OBJECT-TYPE
            SYNTAX  INTEGER
            ACCESS  read-only
            STATUS  mandatory
            DESCRIPTION
                "Unavailable Second"
            ::= { t3LoPath-VTPathTotalEty 8 }

        t3LoVTTotalBES-Count  OBJECT-TYPE
            SYNTAX  INTEGER
            ACCESS  read-only
            STATUS  mandatory
            DESCRIPTION
                "Background Error Second"
            ::= { t3LoPath-VTPathTotalEty 9 }

        t3LoVTTotalSES-Count  OBJECT-TYPE
            SYNTAX  INTEGER
            ACCESS  read-only
            STATUS  mandatory
            DESCRIPTION
                "Severly Error Second"
            ::= { t3LoPath-VTPathTotalEty 10 }

--
--  T3 Performance Report Line Current Table
--

        t3LineCurrTab  OBJECT-TYPE
            SYNTAX  SEQUENCE OF T3LineCurrEty
            ACCESS  not-accessible
            STATUS  mandatory
            DESCRIPTION
                "Performance report current"
            ::= { t3PerformanceReport 9 }

        t3LineCurrEty  OBJECT-TYPE
            SYNTAX  T3LineCurrEty
            ACCESS  not-accessible
            STATUS  mandatory
            DESCRIPTION
                "An entry in the performance report current table"
            INDEX { t3LineCurrUnit ,
                    t3LineCurrPort }
            ::= { t3LineCurrTab 1 }

        T3LineCurrEty ::= SEQUENCE {
            t3LineCurrUnit              UnitID,
            t3LineCurrPort              PortID,
            t3LineCurrES-Count          INTEGER,
            t3LineCurrUAS-Count         INTEGER,
            t3LineCurrBES-Count         INTEGER,
            t3LineCurrSES-Count         INTEGER,
            t3LineCurrBPV-Count         INTEGER,
            t3LineCurr15MinTimeElaps    INTEGER,
            t3LineCurr24hrValid15Min    INTEGER,
            t3LineCurrDayValid15Min     INTEGER,
            t3LineCurr7DayValidDays     INTEGER
        }

        t3LineCurrUnit  OBJECT-TYPE
            SYNTAX  UnitID
            ACCESS  read-only
            STATUS  mandatory
            DESCRIPTION
            "unit 1 to 4."
            ::= { t3LineCurrEty 1 }

        t3LineCurrPort  OBJECT-TYPE
            SYNTAX  PortID
            ACCESS  read-only
            STATUS  mandatory
            DESCRIPTION
                "T3 Port 1 to 3"
            ::= { t3LineCurrEty 2 }


        t3LineCurrES-Count  OBJECT-TYPE
            SYNTAX  INTEGER
            ACCESS  read-only
            STATUS  mandatory
            DESCRIPTION
                "Error Second"
            ::= { t3LineCurrEty 3 }

        t3LineCurrUAS-Count  OBJECT-TYPE
            SYNTAX  INTEGER
            ACCESS  read-only
            STATUS  mandatory
            DESCRIPTION
                "Unavailable Second"
            ::= { t3LineCurrEty 4 }

        t3LineCurrBES-Count  OBJECT-TYPE
            SYNTAX  INTEGER
            ACCESS  read-only
            STATUS  mandatory
            DESCRIPTION
                "Background Error Second"
            ::= { t3LineCurrEty 5 }

        t3LineCurrSES-Count  OBJECT-TYPE
            SYNTAX  INTEGER
            ACCESS  read-only
            STATUS  mandatory
            DESCRIPTION
                "Severly Error Second"
            ::= { t3LineCurrEty 6 }

        t3LineCurrBPV-Count  OBJECT-TYPE
            SYNTAX  INTEGER
            ACCESS  read-only
            STATUS  mandatory
            DESCRIPTION
                "Bipolar Violation"
            ::= { t3LineCurrEty 7 }

        t3LineCurr15MinTimeElaps  OBJECT-TYPE
            SYNTAX  INTEGER
            ACCESS  read-only
            STATUS  mandatory
            DESCRIPTION
                "Valid Seconds in Current 15-Min Interval"
            ::= { t3LineCurrEty 8 }

        t3LineCurr24hrValid15Min  OBJECT-TYPE
            SYNTAX  INTEGER
            ACCESS  read-only
            STATUS  mandatory
            DESCRIPTION
                "Valid 15-Min Intervals in Current 24-Hour Interval"
            ::= { t3LineCurrEty 9 }

        t3LineCurrDayValid15Min  OBJECT-TYPE
            SYNTAX  INTEGER
            ACCESS  read-only
            STATUS  mandatory
            DESCRIPTION
                "Valid 15-Min Intervals in Current Day"
            ::= { t3LineCurrEty 10 }

        t3LineCurr7DayValidDays  OBJECT-TYPE
            SYNTAX  INTEGER
            ACCESS  read-only
            STATUS  mandatory
            DESCRIPTION
                "Valid Days in Current Seven Day"
            ::= { t3LineCurrEty 11 }


--
--  T3 Performance Report Line Interval Table
--

        t3LineIntervalTab  OBJECT-TYPE
            SYNTAX  SEQUENCE OF T3LineIntervalEty
            ACCESS  not-accessible
            STATUS  mandatory
            DESCRIPTION
                "Performance report Inteval"
            ::= { t3PerformanceReport 10 }

        t3LineIntervalEty  OBJECT-TYPE
            SYNTAX  T3LineIntervalEty
            ACCESS  not-accessible
            STATUS  mandatory
            DESCRIPTION
                "An entry in the performance report interval table"
            INDEX { t3LineIntvUnit ,
                    t3LineIntvPort ,
                    t3LineIntvPeriod }
            ::= { t3LineIntervalTab 1 }

        T3LineIntervalEty ::= SEQUENCE {
            t3LineIntvUnit              UnitID,
            t3LineIntvPort              PortID,
            t3LineIntvPeriod            INTEGER (1..96),
            t3LineIntvES-Count          INTEGER,
            t3LineIntvUAS-Count         INTEGER,
            t3LineIntvBES-Count         INTEGER,
            t3LineIntvSES-Count         INTEGER,
            t3LineIntvBPV-Count         INTEGER
        }

        t3LineIntvUnit  OBJECT-TYPE
            SYNTAX  UnitID
            ACCESS  read-only
            STATUS  mandatory
            DESCRIPTION
            "unit 1 to 4."
            ::= { t3LineIntervalEty 1 }

        t3LineIntvPort  OBJECT-TYPE
            SYNTAX  PortID
            ACCESS  read-only
            STATUS  mandatory
            DESCRIPTION
                "T3 Port 1 to 3"
            ::= { t3LineIntervalEty 2 }

        t3LineIntvPeriod  OBJECT-TYPE
            SYNTAX  INTEGER (1..96)
            ACCESS  read-only
            STATUS  mandatory
            DESCRIPTION
                "Line Interval Period"
            ::= { t3LineIntervalEty 3 }

        t3LineIntvES-Count  OBJECT-TYPE
            SYNTAX  INTEGER
            ACCESS  read-only
            STATUS  mandatory
            DESCRIPTION
                "Error Second"
            ::= { t3LineIntervalEty 4 }

        t3LineIntvUAS-Count  OBJECT-TYPE
            SYNTAX  INTEGER
            ACCESS  read-only
            STATUS  mandatory
            DESCRIPTION
                "Unavailable Second"
            ::= { t3LineIntervalEty 5 }

        t3LineIntvBES-Count  OBJECT-TYPE
            SYNTAX  INTEGER
            ACCESS  read-only
            STATUS  mandatory
            DESCRIPTION
                "Background Error Second"
            ::= { t3LineIntervalEty 6 }

        t3LineIntvSES-Count  OBJECT-TYPE
            SYNTAX  INTEGER
            ACCESS  read-only
            STATUS  mandatory
            DESCRIPTION
                "Severly Error Second"
            ::= { t3LineIntervalEty 7 }

        t3LineIntvBPV-Count  OBJECT-TYPE
            SYNTAX  INTEGER
            ACCESS  read-only
            STATUS  mandatory
            DESCRIPTION
                "Bipolar Violation"
            ::= { t3LineIntervalEty 8 }

--
--  T3 Performance Report Line Seven Days Table
--

        t3Line7DaysTab  OBJECT-TYPE
            SYNTAX  SEQUENCE OF T3Line7DaysEty
            ACCESS  not-accessible
            STATUS  mandatory
            DESCRIPTION
                "Performance report seven days"
            ::= { t3PerformanceReport 11 }

        t3Line7DaysEty  OBJECT-TYPE
            SYNTAX  T3Line7DaysEty
            ACCESS  not-accessible
            STATUS  mandatory
            DESCRIPTION
                "An entry in the performance report seven days table"
            INDEX { t3Line7DaysUnit ,
                    t3Line7DaysPort ,
                    t3Line7DaysDayIndex }
            ::= { t3Line7DaysTab 1 }

        T3Line7DaysEty ::= SEQUENCE {
            t3Line7DaysUnit             UnitID,
            t3Line7DaysPort             PortID,
            t3Line7DaysDayIndex         INTEGER (1..7),
            t3Line7DaysDate             DisplayString (SIZE (0..255) ),
            t3Line7DaysES-Count         INTEGER,
            t3Line7DaysUAS-Count        INTEGER,
            t3Line7DaysBES-Count        INTEGER,
            t3Line7DaysSES-Count        INTEGER,
            t3Line7DaysBPV-Count        INTEGER
        }

        t3Line7DaysUnit  OBJECT-TYPE
            SYNTAX  UnitID
            ACCESS  read-only
            STATUS  mandatory
            DESCRIPTION
            "unit 1 to 4."
            ::= { t3Line7DaysEty 1 }

        t3Line7DaysPort  OBJECT-TYPE
            SYNTAX  PortID
            ACCESS  read-only
            STATUS  mandatory
            DESCRIPTION
                "T3 Port 1 to 3"
            ::= { t3Line7DaysEty 2 }

        t3Line7DaysDayIndex  OBJECT-TYPE
            SYNTAX  INTEGER (1..7)
            ACCESS  read-only
            STATUS  mandatory
            DESCRIPTION
                "Line Seven Days day index"
            ::= { t3Line7DaysEty 3 }

        t3Line7DaysDate  OBJECT-TYPE
            SYNTAX  DisplayString (SIZE (0..255) )
            ACCESS  read-only
            STATUS  mandatory
            DESCRIPTION
                "Seven Days Date"
            ::= { t3Line7DaysEty 4 }

        t3Line7DaysES-Count  OBJECT-TYPE
            SYNTAX  INTEGER
            ACCESS  read-only
            STATUS  mandatory
            DESCRIPTION
                "Error Second"
            ::= { t3Line7DaysEty 5 }

        t3Line7DaysUAS-Count  OBJECT-TYPE
            SYNTAX  INTEGER
            ACCESS  read-only
            STATUS  mandatory
            DESCRIPTION
                "Unavailable Second"
            ::= { t3Line7DaysEty 6 }

        t3Line7DaysBES-Count  OBJECT-TYPE
            SYNTAX  INTEGER
            ACCESS  read-only
            STATUS  mandatory
            DESCRIPTION
                "Background Error Second"
            ::= { t3Line7DaysEty 7 }

        t3Line7DaysSES-Count  OBJECT-TYPE
            SYNTAX  INTEGER
            ACCESS  read-only
            STATUS  mandatory
            DESCRIPTION
                "Severly Error Second"
            ::= { t3Line7DaysEty 8 }

        t3Line7DaysBPV-Count  OBJECT-TYPE
            SYNTAX  INTEGER
            ACCESS  read-only
            STATUS  mandatory
            DESCRIPTION
                "Bipolar Violation"
            ::= { t3Line7DaysEty 9 }


--
--  T3 Performance Report Line Total Table
--

        t3LineTotalTab  OBJECT-TYPE
            SYNTAX  SEQUENCE OF T3LineTotalEty
            ACCESS  not-accessible
            STATUS  mandatory
            DESCRIPTION
                "Performance report Total"
            ::= { t3PerformanceReport 12 }

        t3LineTotalEty  OBJECT-TYPE
            SYNTAX  T3LineTotalEty
            ACCESS  not-accessible
            STATUS  mandatory
            DESCRIPTION
                "An entry in the performance report total table"
            INDEX { t3LineTotalUnit ,
                    t3LineTotalPort }
            ::= { t3LineTotalTab 1 }

        T3LineTotalEty ::= SEQUENCE {
            t3LineTotalUnit             UnitID,
            t3LineTotalPort             PortID,
            t3LineTotalES-Count         INTEGER,
            t3LineTotalUAS-Count        INTEGER,
            t3LineTotalBES-Count        INTEGER,
            t3LineTotalSES-Count        INTEGER,
            t3LineTotalBPV-Count        INTEGER
        }

        t3LineTotalUnit  OBJECT-TYPE
            SYNTAX  UnitID
            ACCESS  read-only
            STATUS  mandatory
            DESCRIPTION
            "unit 1 to 4."
            ::= { t3LineTotalEty 1 }

        t3LineTotalPort  OBJECT-TYPE
            SYNTAX  PortID
            ACCESS  read-only
            STATUS  mandatory
            DESCRIPTION
                "T3 Port 1 to 3"
            ::= { t3LineTotalEty 2 }

        t3LineTotalES-Count  OBJECT-TYPE
            SYNTAX  INTEGER
            ACCESS  read-only
            STATUS  mandatory
            DESCRIPTION
                "Error Second"
            ::= { t3LineTotalEty 3 }

        t3LineTotalUAS-Count  OBJECT-TYPE
            SYNTAX  INTEGER
            ACCESS  read-only
            STATUS  mandatory
            DESCRIPTION
                "Unavailable Second"
            ::= { t3LineTotalEty 4 }

        t3LineTotalBES-Count  OBJECT-TYPE
            SYNTAX  INTEGER
            ACCESS  read-only
            STATUS  mandatory
            DESCRIPTION
                "Background Error Second"
            ::= { t3LineTotalEty 5 }

        t3LineTotalSES-Count  OBJECT-TYPE
            SYNTAX  INTEGER
            ACCESS  read-only
            STATUS  mandatory
            DESCRIPTION
                "Severly Error Second"
            ::= { t3LineTotalEty 6 }

        t3LineTotalBPV-Count  OBJECT-TYPE
            SYNTAX  INTEGER
            ACCESS  read-only
            STATUS  mandatory
            DESCRIPTION
                "Bipolar Violation"
            ::= { t3LineTotalEty 7 }

--
--  T3 Performance Report Line P-Bits Current Table
--

        t3PBitsCurrTab  OBJECT-TYPE
            SYNTAX  SEQUENCE OF T3PBitsCurrEty
            ACCESS  not-accessible
            STATUS  mandatory
            DESCRIPTION
                "Performance report current"
            ::= { t3PerformanceReport 13 }

        t3PBitsCurrEty  OBJECT-TYPE
            SYNTAX  T3PBitsCurrEty
            ACCESS  not-accessible
            STATUS  mandatory
            DESCRIPTION
                "An entry in the performance report current table"
            INDEX { t3PBitsCurrUnit ,
                    t3PBitsCurrPort }
            ::= { t3PBitsCurrTab 1 }

        T3PBitsCurrEty ::= SEQUENCE {
            t3PBitsCurrUnit             UnitID,
            t3PBitsCurrPort             PortID,
            t3PBitsCurrES-Count         INTEGER,
            t3PBitsCurrUAS-Count        INTEGER,
            t3PBitsCurrBES-Count        INTEGER,
            t3PBitsCurrSES-Count        INTEGER,
            t3PBitsCurrCV-Count         INTEGER,
            t3PBitsCurr15MinTimeElaps   INTEGER,
            t3PBitsCurr24hrValid15Min   INTEGER,
            t3PBitsCurrDayValid15Min    INTEGER,
            t3PBitsCurr7DayValidDays    INTEGER
        }

        t3PBitsCurrUnit  OBJECT-TYPE
            SYNTAX  UnitID
            ACCESS  read-only
            STATUS  mandatory
            DESCRIPTION
            "unit 1 to 4."
            ::= { t3PBitsCurrEty 1 }

        t3PBitsCurrPort  OBJECT-TYPE
            SYNTAX  PortID
            ACCESS  read-only
            STATUS  mandatory
            DESCRIPTION
                "T3 Port 1 to 3"
            ::= { t3PBitsCurrEty 2 }


        t3PBitsCurrES-Count  OBJECT-TYPE
            SYNTAX  INTEGER
            ACCESS  read-only
            STATUS  mandatory
            DESCRIPTION
                "Error Second"
            ::= { t3PBitsCurrEty 3 }

        t3PBitsCurrUAS-Count  OBJECT-TYPE
            SYNTAX  INTEGER
            ACCESS  read-only
            STATUS  mandatory
            DESCRIPTION
                "Unavailable Second"
            ::= { t3PBitsCurrEty 4 }

        t3PBitsCurrBES-Count  OBJECT-TYPE
            SYNTAX  INTEGER
            ACCESS  read-only
            STATUS  mandatory
            DESCRIPTION
                "Background Error Second"
            ::= { t3PBitsCurrEty 5 }

        t3PBitsCurrSES-Count  OBJECT-TYPE
            SYNTAX  INTEGER
            ACCESS  read-only
            STATUS  mandatory
            DESCRIPTION
                "Severly Error Second"
            ::= { t3PBitsCurrEty 6 }

        t3PBitsCurrCV-Count  OBJECT-TYPE
            SYNTAX  INTEGER
            ACCESS  read-only
            STATUS  mandatory
            DESCRIPTION
                "Code Violation"
            ::= { t3PBitsCurrEty 7 }

        t3PBitsCurr15MinTimeElaps  OBJECT-TYPE
            SYNTAX  INTEGER
            ACCESS  read-only
            STATUS  mandatory
            DESCRIPTION
                "Valid Seconds in Current 15-Min Interval"
            ::= { t3PBitsCurrEty 8 }

        t3PBitsCurr24hrValid15Min  OBJECT-TYPE
            SYNTAX  INTEGER
            ACCESS  read-only
            STATUS  mandatory
            DESCRIPTION
                "Valid 15-Min Intervals in Current 24-Hour Interval"
            ::= { t3PBitsCurrEty 9 }

        t3PBitsCurrDayValid15Min  OBJECT-TYPE
            SYNTAX  INTEGER
            ACCESS  read-only
            STATUS  mandatory
            DESCRIPTION
                "Valid 15-Min Intervals in Current Day"
            ::= { t3PBitsCurrEty 10 }

        t3PBitsCurr7DayValidDays  OBJECT-TYPE
            SYNTAX  INTEGER
            ACCESS  read-only
            STATUS  mandatory
            DESCRIPTION
                "Valid Days in Current Seven Day"
            ::= { t3PBitsCurrEty 11 }


--
--  T3 Performance Report Line P-Bits Interval Table
--

        t3PBitsIntervalTab  OBJECT-TYPE
            SYNTAX  SEQUENCE OF T3PBitsIntervalEty
            ACCESS  not-accessible
            STATUS  mandatory
            DESCRIPTION
                "Performance report Inteval"
            ::= { t3PerformanceReport 14 }

        t3PBitsIntervalEty  OBJECT-TYPE
            SYNTAX  T3PBitsIntervalEty
            ACCESS  not-accessible
            STATUS  mandatory
            DESCRIPTION
                "An entry in the performance report interval table"
            INDEX { t3PBitsIntvUnit ,
                    t3PBitsIntvPort ,
                    t3PBitsIntvPeriod }
            ::= { t3PBitsIntervalTab 1 }

        T3PBitsIntervalEty ::= SEQUENCE {
            t3PBitsIntvUnit             UnitID,
            t3PBitsIntvPort             PortID,
            t3PBitsIntvPeriod           INTEGER (1..96),
            t3PBitsIntvES-Count         INTEGER,
            t3PBitsIntvUAS-Count        INTEGER,
            t3PBitsIntvBES-Count        INTEGER,
            t3PBitsIntvSES-Count        INTEGER,
            t3PBitsIntvCV-Count         INTEGER
        }

        t3PBitsIntvUnit  OBJECT-TYPE
            SYNTAX  UnitID
            ACCESS  read-only
            STATUS  mandatory
            DESCRIPTION
            "unit 1 to 4."
            ::= { t3PBitsIntervalEty 1 }

        t3PBitsIntvPort  OBJECT-TYPE
            SYNTAX  PortID
            ACCESS  read-only
            STATUS  mandatory
            DESCRIPTION
                "T3 Port 1 to 3"
            ::= { t3PBitsIntervalEty 2 }

        t3PBitsIntvPeriod  OBJECT-TYPE
            SYNTAX  INTEGER (1..96)
            ACCESS  read-only
            STATUS  mandatory
            DESCRIPTION
                "PBits Interval Period"
            ::= { t3PBitsIntervalEty 3 }

        t3PBitsIntvES-Count  OBJECT-TYPE
            SYNTAX  INTEGER
            ACCESS  read-only
            STATUS  mandatory
            DESCRIPTION
                "Error Second"
            ::= { t3PBitsIntervalEty 4 }

        t3PBitsIntvUAS-Count  OBJECT-TYPE
            SYNTAX  INTEGER
            ACCESS  read-only
            STATUS  mandatory
            DESCRIPTION
                "Unavailable Second"
            ::= { t3PBitsIntervalEty 5 }

        t3PBitsIntvBES-Count  OBJECT-TYPE
            SYNTAX  INTEGER
            ACCESS  read-only
            STATUS  mandatory
            DESCRIPTION
                "Background Error Second"
            ::= { t3PBitsIntervalEty 6 }

        t3PBitsIntvSES-Count  OBJECT-TYPE
            SYNTAX  INTEGER
            ACCESS  read-only
            STATUS  mandatory
            DESCRIPTION
                "Severly Error Second"
            ::= { t3PBitsIntervalEty 7 }

        t3PBitsIntvCV-Count  OBJECT-TYPE
            SYNTAX  INTEGER
            ACCESS  read-only
            STATUS  mandatory
            DESCRIPTION
                "Code Violation"
            ::= { t3PBitsIntervalEty 8 }

--
--  T3 Performance Report Line P-Bits Seven Days Table
--

        t3PBits7DaysTab  OBJECT-TYPE
            SYNTAX  SEQUENCE OF T3PBits7DaysEty
            ACCESS  not-accessible
            STATUS  mandatory
            DESCRIPTION
                "Performance report seven days"
            ::= { t3PerformanceReport 15 }

        t3PBits7DaysEty  OBJECT-TYPE
            SYNTAX  T3PBits7DaysEty
            ACCESS  not-accessible
            STATUS  mandatory
            DESCRIPTION
                "An entry in the performance report seven days table"
            INDEX { t3PBits7DaysUnit ,
                    t3PBits7DaysPort ,
                    t3PBits7DaysDayIndex }
            ::= { t3PBits7DaysTab 1 }

        T3PBits7DaysEty ::= SEQUENCE {
            t3PBits7DaysUnit            UnitID,
            t3PBits7DaysPort            PortID,
            t3PBits7DaysDayIndex        INTEGER (1..7),
            t3PBits7DaysDate            DisplayString (SIZE (0..255) ),
            t3PBits7DaysES-Count        INTEGER,
            t3PBits7DaysUAS-Count       INTEGER,
            t3PBits7DaysBES-Count       INTEGER,
            t3PBits7DaysSES-Count       INTEGER,
            t3PBits7DaysCV-Count        INTEGER
        }

        t3PBits7DaysUnit  OBJECT-TYPE
            SYNTAX  UnitID
            ACCESS  read-only
            STATUS  mandatory
            DESCRIPTION
            "unit 1 to 4."
            ::= { t3PBits7DaysEty 1 }

        t3PBits7DaysPort  OBJECT-TYPE
            SYNTAX  PortID
            ACCESS  read-only
            STATUS  mandatory
            DESCRIPTION
                "T3 Port 1 to 3"
            ::= { t3PBits7DaysEty 2 }

        t3PBits7DaysDayIndex  OBJECT-TYPE
            SYNTAX  INTEGER (1..7)
            ACCESS  read-only
            STATUS  mandatory
            DESCRIPTION
                "PBits Seven Days day index"
            ::= { t3PBits7DaysEty 3 }

        t3PBits7DaysDate  OBJECT-TYPE
            SYNTAX  DisplayString (SIZE (0..255) )
            ACCESS  read-only
            STATUS  mandatory
            DESCRIPTION
                "Seven Days Date"
            ::= { t3PBits7DaysEty 4 }

        t3PBits7DaysES-Count  OBJECT-TYPE
            SYNTAX  INTEGER
            ACCESS  read-only
            STATUS  mandatory
            DESCRIPTION
                "Error Second"
            ::= { t3PBits7DaysEty 5 }

        t3PBits7DaysUAS-Count  OBJECT-TYPE
            SYNTAX  INTEGER
            ACCESS  read-only
            STATUS  mandatory
            DESCRIPTION
                "Unavailable Second"
            ::= { t3PBits7DaysEty 6 }

        t3PBits7DaysBES-Count  OBJECT-TYPE
            SYNTAX  INTEGER
            ACCESS  read-only
            STATUS  mandatory
            DESCRIPTION
                "Background Error Second"
            ::= { t3PBits7DaysEty 7 }

        t3PBits7DaysSES-Count  OBJECT-TYPE
            SYNTAX  INTEGER
            ACCESS  read-only
            STATUS  mandatory
            DESCRIPTION
                "Severly Error Second"
            ::= { t3PBits7DaysEty 8 }

        t3PBits7DaysCV-Count  OBJECT-TYPE
            SYNTAX  INTEGER
            ACCESS  read-only
            STATUS  mandatory
            DESCRIPTION
                "Code Violation"
            ::= { t3PBits7DaysEty 9 }


--
--  T3 Performance Report Line P-Bits Total Table
--

        t3PBitsTotalTab  OBJECT-TYPE
            SYNTAX  SEQUENCE OF T3PBitsTotalEty
            ACCESS  not-accessible
            STATUS  mandatory
            DESCRIPTION
                "Performance report Total"
            ::= { t3PerformanceReport 16 }

        t3PBitsTotalEty  OBJECT-TYPE
            SYNTAX  T3PBitsTotalEty
            ACCESS  not-accessible
            STATUS  mandatory
            DESCRIPTION
                "An entry in the performance report total table"
            INDEX { t3PBitsTotalUnit ,
                    t3PBitsTotalPort }
            ::= { t3PBitsTotalTab 1 }

        T3PBitsTotalEty ::= SEQUENCE {
            t3PBitsTotalUnit            UnitID,
            t3PBitsTotalPort            PortID,
            t3PBitsTotalES-Count        INTEGER,
            t3PBitsTotalUAS-Count       INTEGER,
            t3PBitsTotalBES-Count       INTEGER,
            t3PBitsTotalSES-Count       INTEGER,
            t3PBitsTotalCV-Count        INTEGER
        }

        t3PBitsTotalUnit  OBJECT-TYPE
            SYNTAX  UnitID
            ACCESS  read-only
            STATUS  mandatory
            DESCRIPTION
            "unit 1 to 4."
            ::= { t3PBitsTotalEty 1 }

        t3PBitsTotalPort  OBJECT-TYPE
            SYNTAX  PortID
            ACCESS  read-only
            STATUS  mandatory
            DESCRIPTION
                "T3 Port 1 to 3"
            ::= { t3PBitsTotalEty 2 }

        t3PBitsTotalES-Count  OBJECT-TYPE
            SYNTAX  INTEGER
            ACCESS  read-only
            STATUS  mandatory
            DESCRIPTION
                "Error Second"
            ::= { t3PBitsTotalEty 3 }

        t3PBitsTotalUAS-Count  OBJECT-TYPE
            SYNTAX  INTEGER
            ACCESS  read-only
            STATUS  mandatory
            DESCRIPTION
                "Unavailable Second"
            ::= { t3PBitsTotalEty 4 }

        t3PBitsTotalBES-Count  OBJECT-TYPE
            SYNTAX  INTEGER
            ACCESS  read-only
            STATUS  mandatory
            DESCRIPTION
                "Background Error Second"
            ::= { t3PBitsTotalEty 5 }

        t3PBitsTotalSES-Count  OBJECT-TYPE
            SYNTAX  INTEGER
            ACCESS  read-only
            STATUS  mandatory
            DESCRIPTION
                "Severly Error Second"
            ::= { t3PBitsTotalEty 6 }

        t3PBitsTotalCV-Count  OBJECT-TYPE
            SYNTAX  INTEGER
            ACCESS  read-only
            STATUS  mandatory
            DESCRIPTION
                "Code Violation"
            ::= { t3PBitsTotalEty 7 }

--
--  T3 Performance Report Line C-Bits Current Table
--

        t3CBitsCurrTab  OBJECT-TYPE
            SYNTAX  SEQUENCE OF T3CBitsCurrEty
            ACCESS  not-accessible
            STATUS  mandatory
            DESCRIPTION
                "Performance report current"
            ::= { t3PerformanceReport 17 }

        t3CBitsCurrEty  OBJECT-TYPE
            SYNTAX  T3CBitsCurrEty
            ACCESS  not-accessible
            STATUS  mandatory
            DESCRIPTION
                "An entry in the performance report current table"
            INDEX { t3CBitsCurrUnit ,
                    t3CBitsCurrPort }
            ::= { t3CBitsCurrTab 1 }

        T3CBitsCurrEty ::= SEQUENCE {
            t3CBitsCurrUnit             UnitID,
            t3CBitsCurrPort             PortID,
            t3CBitsCurrES-Count         INTEGER,
            t3CBitsCurrUAS-Count        INTEGER,
            t3CBitsCurrBES-Count        INTEGER,
            t3CBitsCurrSES-Count        INTEGER,
            t3CBitsCurrCV-Count         INTEGER,
            t3CBitsCurr15MinTimeElaps   INTEGER,
            t3CBitsCurr24hrValid15Min   INTEGER,
            t3CBitsCurrDayValid15Min    INTEGER,
            t3CBitsCurr7DayValidDays    INTEGER
        }

        t3CBitsCurrUnit  OBJECT-TYPE
            SYNTAX  UnitID
            ACCESS  read-only
            STATUS  mandatory
            DESCRIPTION
            "unit 1 to 4."
            ::= { t3CBitsCurrEty 1 }

        t3CBitsCurrPort  OBJECT-TYPE
            SYNTAX  PortID
            ACCESS  read-only
            STATUS  mandatory
            DESCRIPTION
                "T3 Port 1 to 3"
            ::= { t3CBitsCurrEty 2 }


        t3CBitsCurrES-Count  OBJECT-TYPE
            SYNTAX  INTEGER
            ACCESS  read-only
            STATUS  mandatory
            DESCRIPTION
                "Error Second"
            ::= { t3CBitsCurrEty 3 }

        t3CBitsCurrUAS-Count  OBJECT-TYPE
            SYNTAX  INTEGER
            ACCESS  read-only
            STATUS  mandatory
            DESCRIPTION
                "Unavailable Second"
            ::= { t3CBitsCurrEty 4 }

        t3CBitsCurrBES-Count  OBJECT-TYPE
            SYNTAX  INTEGER
            ACCESS  read-only
            STATUS  mandatory
            DESCRIPTION
                "Background Error Second"
            ::= { t3CBitsCurrEty 5 }

        t3CBitsCurrSES-Count  OBJECT-TYPE
            SYNTAX  INTEGER
            ACCESS  read-only
            STATUS  mandatory
            DESCRIPTION
                "Severly Error Second"
            ::= { t3CBitsCurrEty 6 }

        t3CBitsCurrCV-Count  OBJECT-TYPE
            SYNTAX  INTEGER
            ACCESS  read-only
            STATUS  mandatory
            DESCRIPTION
                "Code Violation"
            ::= { t3CBitsCurrEty 7 }

        t3CBitsCurr15MinTimeElaps  OBJECT-TYPE
            SYNTAX  INTEGER
            ACCESS  read-only
            STATUS  mandatory
            DESCRIPTION
                "Valid Seconds in Current 15-Min Interval"
            ::= { t3CBitsCurrEty 8 }

        t3CBitsCurr24hrValid15Min  OBJECT-TYPE
            SYNTAX  INTEGER
            ACCESS  read-only
            STATUS  mandatory
            DESCRIPTION
                "Valid 15-Min Intervals in Current 24-Hour Interval"
            ::= { t3CBitsCurrEty 9 }

        t3CBitsCurrDayValid15Min  OBJECT-TYPE
            SYNTAX  INTEGER
            ACCESS  read-only
            STATUS  mandatory
            DESCRIPTION
                "Valid 15-Min Intervals in Current Day"
            ::= { t3CBitsCurrEty 10 }

        t3CBitsCurr7DayValidDays  OBJECT-TYPE
            SYNTAX  INTEGER
            ACCESS  read-only
            STATUS  mandatory
            DESCRIPTION
                "Valid Days in Current Seven Day"
            ::= { t3CBitsCurrEty 11 }


--
--  T3 Performance Report Line C-Bits Interval Table
--

        t3CBitsIntervalTab  OBJECT-TYPE
            SYNTAX  SEQUENCE OF T3CBitsIntervalEty
            ACCESS  not-accessible
            STATUS  mandatory
            DESCRIPTION
                "Performance report Inteval"
            ::= { t3PerformanceReport 18 }

        t3CBitsIntervalEty  OBJECT-TYPE
            SYNTAX  T3CBitsIntervalEty
            ACCESS  not-accessible
            STATUS  mandatory
            DESCRIPTION
                "An entry in the performance report interval table"
            INDEX { t3CBitsIntvUnit ,
                    t3CBitsIntvPort ,
                    t3CBitsIntvPeriod }
            ::= { t3CBitsIntervalTab 1 }

        T3CBitsIntervalEty ::= SEQUENCE {
            t3CBitsIntvUnit             UnitID,
            t3CBitsIntvPort             PortID,
            t3CBitsIntvPeriod           INTEGER (1..96),
            t3CBitsIntvES-Count         INTEGER,
            t3CBitsIntvUAS-Count        INTEGER,
            t3CBitsIntvBES-Count        INTEGER,
            t3CBitsIntvSES-Count        INTEGER,
            t3CBitsIntvCV-Count         INTEGER
        }

        t3CBitsIntvUnit  OBJECT-TYPE
            SYNTAX  UnitID
            ACCESS  read-only
            STATUS  mandatory
            DESCRIPTION
            "unit 1 to 4."
            ::= { t3CBitsIntervalEty 1 }

        t3CBitsIntvPort  OBJECT-TYPE
            SYNTAX  PortID
            ACCESS  read-only
            STATUS  mandatory
            DESCRIPTION
                "T3 Port 1 to 3"
            ::= { t3CBitsIntervalEty 2 }

        t3CBitsIntvPeriod  OBJECT-TYPE
            SYNTAX  INTEGER (1..96)
            ACCESS  read-only
            STATUS  mandatory
            DESCRIPTION
                "CBits Interval Period"
            ::= { t3CBitsIntervalEty 3 }

        t3CBitsIntvES-Count  OBJECT-TYPE
            SYNTAX  INTEGER
            ACCESS  read-only
            STATUS  mandatory
            DESCRIPTION
                "Error Second"
            ::= { t3CBitsIntervalEty 4 }

        t3CBitsIntvUAS-Count  OBJECT-TYPE
            SYNTAX  INTEGER
            ACCESS  read-only
            STATUS  mandatory
            DESCRIPTION
                "Unavailable Second"
            ::= { t3CBitsIntervalEty 5 }

        t3CBitsIntvBES-Count  OBJECT-TYPE
            SYNTAX  INTEGER
            ACCESS  read-only
            STATUS  mandatory
            DESCRIPTION
                "Background Error Second"
            ::= { t3CBitsIntervalEty 6 }

        t3CBitsIntvSES-Count  OBJECT-TYPE
            SYNTAX  INTEGER
            ACCESS  read-only
            STATUS  mandatory
            DESCRIPTION
                "Severly Error Second"
            ::= { t3CBitsIntervalEty 7 }

        t3CBitsIntvCV-Count  OBJECT-TYPE
            SYNTAX  INTEGER
            ACCESS  read-only
            STATUS  mandatory
            DESCRIPTION
                "Code Violation"
            ::= { t3CBitsIntervalEty 8 }

--
--  T3 Performance Report Line C-Bits Seven Days Table
--

        t3CBits7DaysTab  OBJECT-TYPE
            SYNTAX  SEQUENCE OF T3CBits7DaysEty
            ACCESS  not-accessible
            STATUS  mandatory
            DESCRIPTION
                "Performance report seven days"
            ::= { t3PerformanceReport 19 }

        t3CBits7DaysEty  OBJECT-TYPE
            SYNTAX  T3CBits7DaysEty
            ACCESS  not-accessible
            STATUS  mandatory
            DESCRIPTION
                "An entry in the performance report seven days table"
            INDEX { t3CBits7DaysUnit ,
                    t3CBits7DaysPort ,
                    t3CBits7DaysDayIndex }
            ::= { t3CBits7DaysTab 1 }

        T3CBits7DaysEty ::= SEQUENCE {
            t3CBits7DaysUnit            UnitID,
            t3CBits7DaysPort            PortID,
            t3CBits7DaysDayIndex        INTEGER (1..7),
            t3CBits7DaysDate            DisplayString (SIZE (0..255) ),
            t3CBits7DaysES-Count        INTEGER,
            t3CBits7DaysUAS-Count       INTEGER,
            t3CBits7DaysBES-Count       INTEGER,
            t3CBits7DaysSES-Count       INTEGER,
            t3CBits7DaysCV-Count        INTEGER
        }

        t3CBits7DaysUnit  OBJECT-TYPE
            SYNTAX  UnitID
            ACCESS  read-only
            STATUS  mandatory
            DESCRIPTION
            "unit 1 to 4."
            ::= { t3CBits7DaysEty 1 }

        t3CBits7DaysPort  OBJECT-TYPE
            SYNTAX  PortID
            ACCESS  read-only
            STATUS  mandatory
            DESCRIPTION
                "T3 Port 1 to 3"
            ::= { t3CBits7DaysEty 2 }

        t3CBits7DaysDayIndex  OBJECT-TYPE
            SYNTAX  INTEGER (1..7)
            ACCESS  read-only
            STATUS  mandatory
            DESCRIPTION
                "CBits Seven Days day index"
            ::= { t3CBits7DaysEty 3 }

        t3CBits7DaysDate  OBJECT-TYPE
            SYNTAX  DisplayString (SIZE (0..255) )
            ACCESS  read-only
            STATUS  mandatory
            DESCRIPTION
                "Seven Days Date"
            ::= { t3CBits7DaysEty 4 }

        t3CBits7DaysES-Count  OBJECT-TYPE
            SYNTAX  INTEGER
            ACCESS  read-only
            STATUS  mandatory
            DESCRIPTION
                "Error Second"
            ::= { t3CBits7DaysEty 5 }

        t3CBits7DaysUAS-Count  OBJECT-TYPE
            SYNTAX  INTEGER
            ACCESS  read-only
            STATUS  mandatory
            DESCRIPTION
                "Unavailable Second"
            ::= { t3CBits7DaysEty 6 }

        t3CBits7DaysBES-Count  OBJECT-TYPE
            SYNTAX  INTEGER
            ACCESS  read-only
            STATUS  mandatory
            DESCRIPTION
                "Background Error Second"
            ::= { t3CBits7DaysEty 7 }

        t3CBits7DaysSES-Count  OBJECT-TYPE
            SYNTAX  INTEGER
            ACCESS  read-only
            STATUS  mandatory
            DESCRIPTION
                "Severly Error Second"
            ::= { t3CBits7DaysEty 8 }

        t3CBits7DaysCV-Count  OBJECT-TYPE
            SYNTAX  INTEGER
            ACCESS  read-only
            STATUS  mandatory
            DESCRIPTION
                "Code Violation"
            ::= { t3CBits7DaysEty 9 }


--
--  T3 Performance Report Line C-Bits Total Table
--

        t3CBitsTotalTab  OBJECT-TYPE
            SYNTAX  SEQUENCE OF T3CBitsTotalEty
            ACCESS  not-accessible
            STATUS  mandatory
            DESCRIPTION
                "Performance report Total"
            ::= { t3PerformanceReport 20 }

        t3CBitsTotalEty  OBJECT-TYPE
            SYNTAX  T3CBitsTotalEty
            ACCESS  not-accessible
            STATUS  mandatory
            DESCRIPTION
                "An entry in the performance report total table"
            INDEX { t3CBitsTotalUnit ,
                    t3CBitsTotalPort }
            ::= { t3CBitsTotalTab 1 }

        T3CBitsTotalEty ::= SEQUENCE {
            t3CBitsTotalUnit            UnitID,
            t3CBitsTotalPort            PortID,
            t3CBitsTotalES-Count        INTEGER,
            t3CBitsTotalUAS-Count       INTEGER,
            t3CBitsTotalBES-Count       INTEGER,
            t3CBitsTotalSES-Count       INTEGER,
            t3CBitsTotalCV-Count        INTEGER
        }

        t3CBitsTotalUnit  OBJECT-TYPE
            SYNTAX  UnitID
            ACCESS  read-only
            STATUS  mandatory
            DESCRIPTION
            "unit 1 to 4."
            ::= { t3CBitsTotalEty 1 }

        t3CBitsTotalPort  OBJECT-TYPE
            SYNTAX  PortID
            ACCESS  read-only
            STATUS  mandatory
            DESCRIPTION
                "T3 Port 1 to 3"
            ::= { t3CBitsTotalEty 2 }

        t3CBitsTotalES-Count  OBJECT-TYPE
            SYNTAX  INTEGER
            ACCESS  read-only
            STATUS  mandatory
            DESCRIPTION
                "Error Second"
            ::= { t3CBitsTotalEty 3 }

        t3CBitsTotalUAS-Count  OBJECT-TYPE
            SYNTAX  INTEGER
            ACCESS  read-only
            STATUS  mandatory
            DESCRIPTION
                "Unavailable Second"
            ::= { t3CBitsTotalEty 4 }

        t3CBitsTotalBES-Count  OBJECT-TYPE
            SYNTAX  INTEGER
            ACCESS  read-only
            STATUS  mandatory
            DESCRIPTION
                "Background Error Second"
            ::= { t3CBitsTotalEty 5 }

        t3CBitsTotalSES-Count  OBJECT-TYPE
            SYNTAX  INTEGER
            ACCESS  read-only
            STATUS  mandatory
            DESCRIPTION
                "Severly Error Second"
            ::= { t3CBitsTotalEty 6 }

        t3CBitsTotalCV-Count  OBJECT-TYPE
            SYNTAX  INTEGER
            ACCESS  read-only
            STATUS  mandatory
            DESCRIPTION
                "Code Violation"
            ::= { t3CBitsTotalEty 7 }

--
--  T3 Performance Threshold Setup Table
--

        t3PerfThreshSetupTab  OBJECT-TYPE
            SYNTAX  SEQUENCE OF T3PerfThreshSetupEty
            ACCESS  not-accessible
            STATUS  mandatory
            DESCRIPTION
                "Performance threshold setup"
            ::= { t3Performance 2 }

        t3PerfThreshSetupEty  OBJECT-TYPE
            SYNTAX  T3PerfThreshSetupEty
            ACCESS  not-accessible
            STATUS  mandatory
            DESCRIPTION
                "An entry in the performance threshold setup table"
            INDEX { t3PerfTCAUnit ,
                    t3PerfTCAMonitorPoint }
            ::= { t3PerfThreshSetupTab 1 }

        T3PerfThreshSetupEty ::= SEQUENCE {
            t3PerfTCAUnit               UnitID,
            t3PerfTCAMonitorPoint       INTEGER,
            t3PerfTCAEnable             INTEGER,
            t3PerfTCASeverity           Severity,
            t3PerfTCAThreshold          INTEGER
        }

        t3PerfTCAUnit  OBJECT-TYPE
            SYNTAX  UnitID
            ACCESS  read-only
            STATUS  mandatory
            DESCRIPTION
            "unit 1 to 4."
            ::= { t3PerfThreshSetupEty 1 }

        t3PerfTCAMonitorPoint  OBJECT-TYPE
            SYNTAX  INTEGER {
                    hp-bip(1),
                    hp-rei(2),
                    lp-bipv5(3),
                    lp-reiv5(4),
                    lp-bipb3(5),
                    lp-reib3(6),
                    line(7),
                    p-c-bits(8)
                }
            ACCESS  read-only
            STATUS  mandatory
            DESCRIPTION
                "TCA monitor point index"
            ::= { t3PerfThreshSetupEty 2 }

        t3PerfTCAEnable  OBJECT-TYPE
            SYNTAX  INTEGER {
                    disable(1),
                    enable(2)
                }
            ACCESS  read-write
            STATUS  mandatory
            DESCRIPTION
                "TCA disable/enable"
            ::= { t3PerfThreshSetupEty 3 }

        t3PerfTCASeverity  OBJECT-TYPE
            SYNTAX  Severity
            ACCESS  read-write
            STATUS  mandatory
            DESCRIPTION
                "TCA Severity"
            ::= { t3PerfThreshSetupEty 4 }

        t3PerfTCAThreshold  OBJECT-TYPE
            SYNTAX  INTEGER (1..99999)
            ACCESS  read-write
            STATUS  mandatory
            DESCRIPTION
                "TCA threshold"
            ::= { t3PerfThreshSetupEty 5 }

--
--  T3 Performance Control Setup Table
--

        t3PerfControlTab  OBJECT-TYPE
            SYNTAX  SEQUENCE OF T3PerfControlEty
            ACCESS  not-accessible
            STATUS  mandatory
            DESCRIPTION
                "Performance control"
            ::= { t3Performance 4 }

        t3PerfControlEty  OBJECT-TYPE
            SYNTAX  T3PerfControlEty
            ACCESS  not-accessible
            STATUS  mandatory
            DESCRIPTION
                "An entry in the performance control table"
            INDEX { t3PerfCtrlUnit }
            ::= { t3PerfControlTab 1 }

        T3PerfControlEty ::= SEQUENCE {
            t3PerfCtrlUnit              UnitID,
            t3PerfCtrlClearPerf         INTEGER
        }

        t3PerfCtrlUnit  OBJECT-TYPE
            SYNTAX  UnitID
            ACCESS  read-only
            STATUS  mandatory
            DESCRIPTION
            "unit 1 to 4."
            ::= { t3PerfControlEty 1 }

        t3PerfCtrlClearPerf  OBJECT-TYPE
            SYNTAX  INTEGER {
                    none(0),
                    clear-all-port(1),
                    clear-port1(2),
                    clear-port2(3),
                    clear-port3(4)
                }
            ACCESS  read-write
            STATUS  mandatory
            DESCRIPTION
                "Clear performance data"
            ::= { t3PerfControlEty 2 }

--
-- T3 SNCP/UPSR APS Table
--

        t3SncpApsTab  OBJECT-TYPE
            SYNTAX  SEQUENCE OF  T3SncpApsEty
            ACCESS  not-accessible
            STATUS  mandatory
            DESCRIPTION
                "T3 SNCP/UPSR APS table "
            ::= { t3-card 5 }

        t3SncpApsEty  OBJECT-TYPE
            SYNTAX  T3SncpApsEty
            ACCESS  not-accessible
            STATUS  mandatory
            DESCRIPTION
                "T3 SNCP/UPSR APS entry"
            INDEX { t3SncpUnit , t3SncpPort , t3SncpChannel }
            ::= { t3SncpApsTab 1 }

        T3SncpApsEty ::= SEQUENCE {
            t3SncpUnit                  UnitID,
            t3SncpPort                  PortID,
            t3SncpChannel               ChannelNum,
            t3SncpCurrentPathSlot       XcSlot,
            t3SncpCurrentPathPort       PortID,
            t3SncpPrimaryPathSlot       XcSlot,
            t3SncpPrimaryPathPort       PortID,
            t3SncpPPType                XcType,
            t3SncpCmd                   SncpUserCmd
        }

        t3SncpUnit  OBJECT-TYPE
            SYNTAX  UnitID
            ACCESS  read-only
            STATUS  mandatory
            DESCRIPTION
            "unit 1 to 4."
            ::= { t3SncpApsEty 1 }

        t3SncpPort  OBJECT-TYPE
            SYNTAX  PortID
            ACCESS  read-only
            STATUS  mandatory
            DESCRIPTION
                "PORT #1~#3"
            ::= { t3SncpApsEty 2 }

        t3SncpChannel  OBJECT-TYPE
            SYNTAX  ChannelNum
            ACCESS  read-only
            STATUS  mandatory
            DESCRIPTION
                "CHANNEL #1~#28"
            ::= { t3SncpApsEty 3 }

        t3SncpCurrentPathSlot  OBJECT-TYPE
            SYNTAX  XcSlot
            ACCESS  read-only
            STATUS  mandatory
            DESCRIPTION
                "SNCP/UPSR current path"
            ::= { t3SncpApsEty 4 }

        t3SncpCurrentPathPort  OBJECT-TYPE
            SYNTAX  PortID
            ACCESS  read-only
            STATUS  mandatory
            DESCRIPTION
                "SNCP/UPSR current path"
            ::= { t3SncpApsEty 5 }

        t3SncpPrimaryPathSlot  OBJECT-TYPE
            SYNTAX  XcSlot
            ACCESS  read-only
            STATUS  mandatory
            DESCRIPTION
                "SNCP/UPSR primary path"
            ::= { t3SncpApsEty 6 }

        t3SncpPrimaryPathPort  OBJECT-TYPE
            SYNTAX  PortID
            ACCESS  read-only
            STATUS  mandatory
            DESCRIPTION
                "SNCP/UPSR primary path"
            ::= { t3SncpApsEty 7 }

        t3SncpPPType  OBJECT-TYPE
            SYNTAX  XcType
            ACCESS  read-only
            STATUS  mandatory
            DESCRIPTION
                "SNCP/UPSR path protection type"
            ::= { t3SncpApsEty 8 }

        t3SncpCmd  OBJECT-TYPE
            SYNTAX  SncpUserCmd
            ACCESS  read-write
            STATUS  mandatory
            DESCRIPTION
                "SNCP/UPSR APS command"
            ::= { t3SncpApsEty 9 }

--
-- T3 LED Status Table
--

        t3LedStatusTab OBJECT-TYPE
            SYNTAX  SEQUENCE OF T3LedStatusEty
            ACCESS  not-accessible
            STATUS  mandatory
            DESCRIPTION
                "Led Status"
            ::= { t3-card 6 }

        t3LedStatusEty  OBJECT-TYPE
            SYNTAX  T3LedStatusEty
            ACCESS  not-accessible
            STATUS  mandatory
            DESCRIPTION
                "An entry in the led status table"
            INDEX { t3LedStsUnit }
            ::= { t3LedStatusTab 1 }

        T3LedStatusEty ::= SEQUENCE {
            t3LedStsUnit                UnitID,
            t3LedStsActiveLED           LedStatusType,
            t3LedStsTestLED             LedStatusType,
            t3LedStsAlarmLED            LedStatusType,
            t3LedStsPort1LOSLED         LedStatusType,
            t3LedStsPort2LOSLED         LedStatusType,
            t3LedStsPort3LOSLED         LedStatusType
        }

        t3LedStsUnit  OBJECT-TYPE
            SYNTAX  UnitID
            ACCESS  read-only
            STATUS  mandatory
            DESCRIPTION
            "unit 1 to 4."
            ::= { t3LedStatusEty 1 }

        t3LedStsActiveLED  OBJECT-TYPE
            SYNTAX  LedStatusType
            ACCESS  read-only
            STATUS  mandatory
            DESCRIPTION
                "Active Led Status"
            ::= { t3LedStatusEty 2 }

        t3LedStsTestLED  OBJECT-TYPE
            SYNTAX  LedStatusType
            ACCESS  read-only
            STATUS  mandatory
            DESCRIPTION
                "Test Led Status"
            ::= { t3LedStatusEty 3 }

        t3LedStsAlarmLED  OBJECT-TYPE
            SYNTAX  LedStatusType
            ACCESS  read-only
            STATUS  mandatory
            DESCRIPTION
                "Alarm Led Status"
            ::= { t3LedStatusEty 4 }

        t3LedStsPort1LOSLED  OBJECT-TYPE
            SYNTAX  LedStatusType
            ACCESS  read-only
            STATUS  mandatory
            DESCRIPTION
                "T3 Port 1 LOS Led Status"
            ::= { t3LedStatusEty 5 }

        t3LedStsPort2LOSLED  OBJECT-TYPE
            SYNTAX  LedStatusType
            ACCESS  read-only
            STATUS  mandatory
            DESCRIPTION
                "T3 Port 2 LOS Led Status"
            ::= { t3LedStatusEty 6 }

        t3LedStsPort3LOSLED  OBJECT-TYPE
            SYNTAX  LedStatusType
            ACCESS  read-only
            STATUS  mandatory
            DESCRIPTION
                "T3 Port 3 LOS Led Status"
            ::= { t3LedStatusEty 7 }

--
-- T3 Command Control Table
--

        t3CommandControlTab  OBJECT-TYPE
            SYNTAX  SEQUENCE OF T3CommandControlEty
            ACCESS  not-accessible
            STATUS  mandatory
            DESCRIPTION
                "Command control"
            ::= { t3-card 7 }

        t3CommandControlEty  OBJECT-TYPE
            SYNTAX  T3CommandControlEty
            ACCESS  not-accessible
            STATUS  mandatory
            DESCRIPTION
                "An entry in the command control table"
            INDEX { t3CmdCtrlUnit }
            ::= { t3CommandControlTab 1 }

        T3CommandControlEty ::= SEQUENCE {
            t3CmdCtrlUnit               UnitID,
            t3CmdCtrlUnitReset          INTEGER,
            t3CmdCtrlUnitLoadDefault    INTEGER
        }

        t3CmdCtrlUnit  OBJECT-TYPE
            SYNTAX  UnitID
            ACCESS  read-only
            STATUS  mandatory
            DESCRIPTION
            "unit 1 to 4."
            ::= { t3CommandControlEty 1 }

        t3CmdCtrlUnitReset  OBJECT-TYPE
            SYNTAX  INTEGER {
                    warm(1),
                    cold(2)
                }
            ACCESS  read-write
            STATUS  mandatory
            DESCRIPTION
                "Unit reset"
            ::= { t3CommandControlEty 2 }

        t3CmdCtrlUnitLoadDefault  OBJECT-TYPE
            SYNTAX  INTEGER {
                    load-default(1)
                }
            ACCESS  read-write
            STATUS  mandatory
            DESCRIPTION
                "Unit load default"
            ::= { t3CommandControlEty 3 }

--
--  T3 XC Display Table
--
        t3XcDisplayTab  OBJECT-TYPE
            SYNTAX  SEQUENCE OF  T3XcDisplayEty
            ACCESS  not-accessible
            STATUS  mandatory
            DESCRIPTION
                "T3 xc display table "
            ::= { t3-card 8 }

        t3XcDisplayEty  OBJECT-TYPE
            SYNTAX  T3XcDisplayEty
            ACCESS  not-accessible
            STATUS  mandatory
            DESCRIPTION
                "T3 xc display entry"
            INDEX { t3XcDispMapIndex ,
                    t3XcDispUnitIndex ,
                    t3XcDispPortIndex ,
                    t3XcDispChannelIndex }
            ::= { t3XcDisplayTab 1 }

        T3XcDisplayEty ::= SEQUENCE {
            t3XcDispMapIndex            XcMap,
            t3XcDispUnitIndex           UnitID,
            t3XcDispPortIndex           PortID,
            t3XcDispChannelIndex        ChannelNum,
            t3XcDispSrcSlotType         NewXcModel,
            t3XcDispSrcSlot             XcSlot,
            t3XcDispSrcPort             PortID,
            t3XcDispSrcChannel          ChannelNum,
            t3XcDispSrcAug1Sts3Path     Aug1Sts3Num,
            t3XcDispSrcVc3Sts1Path      Vc3Sts1Num,
            t3XcDispSrcVc1xVtxPath      Vc1xVtxNum,
            t3XcDispXcGranularity       INTEGER,
            t3XcDispXcType              XcType
        }

        t3XcDispMapIndex  OBJECT-TYPE
            SYNTAX  XcMap
            ACCESS  read-only
            STATUS  mandatory
            DESCRIPTION
                "xc map index"
            ::= { t3XcDisplayEty 1 }

        t3XcDispUnitIndex  OBJECT-TYPE
            SYNTAX  UnitID
            ACCESS  read-only
            STATUS  mandatory
            DESCRIPTION
            "unit 1 to 4."
            ::= { t3XcDisplayEty 2 }

        t3XcDispPortIndex  OBJECT-TYPE
            SYNTAX  PortID
            ACCESS  read-only
            STATUS  mandatory
            DESCRIPTION
                "PORT index"
            ::= { t3XcDisplayEty 3 }

        t3XcDispChannelIndex  OBJECT-TYPE
            SYNTAX  ChannelNum
            ACCESS  read-only
            STATUS  mandatory
            DESCRIPTION
                "CHANNEL index"
            ::= { t3XcDisplayEty 4 }

        t3XcDispSrcSlotType  OBJECT-TYPE
            SYNTAX  NewXcModel
            ACCESS  read-only
            STATUS  mandatory
            DESCRIPTION
                " Xc src Unit Type"
            ::= { t3XcDisplayEty 5 }

        t3XcDispSrcSlot  OBJECT-TYPE
            SYNTAX  XcSlot
            ACCESS  read-only
            STATUS  mandatory
            DESCRIPTION
                "Xc src Unit "
            ::= { t3XcDisplayEty 6 }

        t3XcDispSrcPort  OBJECT-TYPE
            SYNTAX  PortID
            ACCESS  read-only
            STATUS  mandatory
            DESCRIPTION
                "Xc src port "
            ::= { t3XcDisplayEty 7 }

        t3XcDispSrcChannel  OBJECT-TYPE
            SYNTAX  ChannelNum
            ACCESS  read-only
            STATUS  mandatory
            DESCRIPTION
                "Xc src channel "
            ::= { t3XcDisplayEty 8 }

        t3XcDispSrcAug1Sts3Path  OBJECT-TYPE
            SYNTAX  Aug1Sts3Num
            ACCESS  read-only
            STATUS  mandatory
            DESCRIPTION
                "Xc src AUG1/STS3 path"
            ::= { t3XcDisplayEty 9 }

        t3XcDispSrcVc3Sts1Path  OBJECT-TYPE
            SYNTAX  Vc3Sts1Num
            ACCESS  read-only
            STATUS  mandatory
            DESCRIPTION
                "Xc src VC3/STS1 path"
            ::= { t3XcDisplayEty 10 }

        t3XcDispSrcVc1xVtxPath  OBJECT-TYPE
            SYNTAX  Vc1xVtxNum
            ACCESS  read-only
            STATUS  mandatory
            DESCRIPTION
                "Xc src VC1x/VTx path"
            ::= { t3XcDisplayEty 11 }

        t3XcDispXcGranularity  OBJECT-TYPE
            SYNTAX  INTEGER {
                    tu3(2),
                    au3-sts1(3),
                    tu11-vt15(4),
                    tu12-vt2(5),
                    vc4-sts3c(6),
                    not-available(100)
                }
            ACCESS  read-only
            STATUS  mandatory
            DESCRIPTION
                "Xc granularity"
            ::= { t3XcDisplayEty 12 }

        t3XcDispXcType  OBJECT-TYPE
            SYNTAX  XcType
            ACCESS  read-only
            STATUS  mandatory
            DESCRIPTION
                "Xc type"
            ::= { t3XcDisplayEty 13 }

--2011-3-18 elvis below
--
--  New T3 XC Display Table
--
        new-t3XcDisplayTab  OBJECT-TYPE
            SYNTAX  SEQUENCE OF  NewT3XcDisplayEty
            ACCESS  not-accessible
            STATUS  mandatory
            DESCRIPTION
                "T3 xc display table "
            ::= { t3-card 9 }

        new-t3XcDisplayEty  OBJECT-TYPE
            SYNTAX  NewT3XcDisplayEty
            ACCESS  not-accessible
            STATUS  mandatory
            DESCRIPTION
                "T3 xc display entry"
            INDEX { new-t3XcDispMapIndex ,
                    new-t3XcDispUnitIndex ,
                    new-t3XcDispPortIndex ,
                    new-t3XcDispChannelIndex }
            ::= { new-t3XcDisplayTab 1 }

        NewT3XcDisplayEty ::= SEQUENCE {
            new-t3XcDispMapIndex        XcMap,
            new-t3XcDispUnitIndex       UnitID,
            new-t3XcDispPortIndex       PortID,
            new-t3XcDispChannelIndex    ChannelNum,
            new-t3XcDispPriSlotType     NewXcModel,
            new-t3XcDispPriSlot         XcSlot,
            new-t3XcDispPriPort         PortID,
            new-t3XcDispPriChannel      ChannelNum,
            new-t3XcDispPriAug1Sts3Path Aug1Sts3Num,
            new-t3XcDispPriVc3Sts1Path  Vc3Sts1Num,
            new-t3XcDispPriVc1xVtxPath  Vc1xVtxNum,
            new-t3XcDispXcGranularity   INTEGER,
            new-t3XcDispXcType          XcType,
            new-t3XcDispSecSlotType     NewXcModel,
            new-t3XcDispSecSlot         XcSlot,
            new-t3XcDispSecPort         PortID,
            new-t3XcDispSecChannel      ChannelNum,
            new-t3XcDispSecAug1Sts3Path Aug1Sts3Num,
            new-t3XcDispSecVc3Sts1Path  Vc3Sts1Num,
            new-t3XcDispSecVc1xVtxPath  Vc1xVtxNum
        }

        new-t3XcDispMapIndex  OBJECT-TYPE
            SYNTAX  XcMap
            ACCESS  read-only
            STATUS  mandatory
            DESCRIPTION
                "xc map index"
            ::= { new-t3XcDisplayEty 1 }

        new-t3XcDispUnitIndex  OBJECT-TYPE
            SYNTAX  UnitID
            ACCESS  read-only
            STATUS  mandatory
            DESCRIPTION
                "unit 1 to 8, total 8 units."
            ::= { new-t3XcDisplayEty 2 }

        new-t3XcDispPortIndex  OBJECT-TYPE
            SYNTAX  PortID
            ACCESS  read-only
            STATUS  mandatory
            DESCRIPTION
                "PORT index"
            ::= { new-t3XcDisplayEty 3 }

        new-t3XcDispChannelIndex  OBJECT-TYPE
            SYNTAX  ChannelNum
            ACCESS  read-only
            STATUS  mandatory
            DESCRIPTION
                "CHANNEL index"
            ::= { new-t3XcDisplayEty 4 }

        new-t3XcDispPriSlotType  OBJECT-TYPE
            SYNTAX  NewXcModel
            ACCESS  read-only
            STATUS  mandatory
            DESCRIPTION
                " Xc Primary Unit Type"
            ::= { new-t3XcDisplayEty 5 }

        new-t3XcDispPriSlot  OBJECT-TYPE
            SYNTAX  XcSlot
            ACCESS  read-only
            STATUS  mandatory
            DESCRIPTION
                "Xc Primary Unit "
            ::= { new-t3XcDisplayEty 6 }

        new-t3XcDispPriPort  OBJECT-TYPE
            SYNTAX  PortID
            ACCESS  read-only
            STATUS  mandatory
            DESCRIPTION
                "Xc Primary port "
            ::= { new-t3XcDisplayEty 7 }

        new-t3XcDispPriChannel  OBJECT-TYPE
            SYNTAX  ChannelNum
            ACCESS  read-only
            STATUS  mandatory
            DESCRIPTION
                "Xc Primary channel "
            ::= { new-t3XcDisplayEty 8 }

        new-t3XcDispPriAug1Sts3Path  OBJECT-TYPE
            SYNTAX  Aug1Sts3Num
            ACCESS  read-only
            STATUS  mandatory
            DESCRIPTION
                "Xc Primary AUG1/STS3 path"
            ::= { new-t3XcDisplayEty 9 }

        new-t3XcDispPriVc3Sts1Path  OBJECT-TYPE
            SYNTAX  Vc3Sts1Num
            ACCESS  read-only
            STATUS  mandatory
            DESCRIPTION
                "Xc Primary VC3/STS1 path"
            ::= { new-t3XcDisplayEty 10 }

        new-t3XcDispPriVc1xVtxPath  OBJECT-TYPE
            SYNTAX  Vc1xVtxNum
            ACCESS  read-only
            STATUS  mandatory
            DESCRIPTION
                "Xc Primary VC1x/VTx path"
            ::= { new-t3XcDisplayEty 11 }

        new-t3XcDispXcGranularity  OBJECT-TYPE
            SYNTAX  INTEGER {
                    tu3(2),
                    au3-sts1(3),
                    tu11-vt15(4),
                    tu12-vt2(5),
                    vc4-sts3c(6),
                    not-available(100)
                }
            ACCESS  read-only
            STATUS  mandatory
            DESCRIPTION
                "Xc granularity"
            ::= { new-t3XcDisplayEty 12 }

        new-t3XcDispXcType  OBJECT-TYPE
            SYNTAX  XcType
            ACCESS  read-only
            STATUS  mandatory
            DESCRIPTION
                "Xc type"
            ::= { new-t3XcDisplayEty 13 }

        new-t3XcDispSecSlotType  OBJECT-TYPE
            SYNTAX  NewXcModel
            ACCESS  read-only
            STATUS  mandatory
            DESCRIPTION
                " Xc Secondary Unit Type"
            ::= { new-t3XcDisplayEty 14 }

        new-t3XcDispSecSlot  OBJECT-TYPE
            SYNTAX  XcSlot
            ACCESS  read-only
            STATUS  mandatory
            DESCRIPTION
                "Xc Secondary Unit "
            ::= { new-t3XcDisplayEty 15 }

        new-t3XcDispSecPort  OBJECT-TYPE
            SYNTAX  PortID
            ACCESS  read-only
            STATUS  mandatory
            DESCRIPTION
                "Xc Secondary port "
            ::= { new-t3XcDisplayEty 16 }

        new-t3XcDispSecChannel  OBJECT-TYPE
            SYNTAX  ChannelNum
            ACCESS  read-only
            STATUS  mandatory
            DESCRIPTION
                "Xc Secondary channel "
            ::= { new-t3XcDisplayEty 17 }

        new-t3XcDispSecAug1Sts3Path  OBJECT-TYPE
            SYNTAX  Aug1Sts3Num
            ACCESS  read-only
            STATUS  mandatory
            DESCRIPTION
                "Xc Secondary AUG1/STS3 path"
            ::= { new-t3XcDisplayEty 18 }

        new-t3XcDispSecVc3Sts1Path  OBJECT-TYPE
            SYNTAX  Vc3Sts1Num
            ACCESS  read-only
            STATUS  mandatory
            DESCRIPTION
                "Xc Secondary VC3/STS1 path"
            ::= { new-t3XcDisplayEty 19 }

        new-t3XcDispSecVc1xVtxPath  OBJECT-TYPE
            SYNTAX  Vc1xVtxNum
            ACCESS  read-only
            STATUS  mandatory
            DESCRIPTION
                "Xc Secondary VC1x/VTx path"
            ::= { new-t3XcDisplayEty 20 }

--
-- New T3 SNCP/UPSR APS Table
--

        new-t3SncpApsTab  OBJECT-TYPE
            SYNTAX  SEQUENCE OF  NewT3SncpApsEty
            ACCESS  not-accessible
            STATUS  mandatory
            DESCRIPTION
                "T3 SNCP/UPSR APS table "
            ::= { t3-card 10 }

        new-t3SncpApsEty  OBJECT-TYPE
            SYNTAX  NewT3SncpApsEty
            ACCESS  not-accessible
            STATUS  mandatory
            DESCRIPTION
                "T3 SNCP/UPSR APS entry"
            INDEX { new-t3SncpUnit , new-t3SncpPort , new-t3SncpChannel }
            ::= { new-t3SncpApsTab 1 }

        NewT3SncpApsEty ::= SEQUENCE {
            new-t3SncpUnit              UnitID,
            new-t3SncpPort              PortID,
            new-t3SncpChannel           ChannelNum,
            new-t3SncpCurrSlot          XcSlot,
            new-t3SncpCurrPort          PortID,
            new-t3SncpCurrChannel       ChannelNum,
            new-t3SncpCurrAug1Sts3Path  Aug1Sts3Num,
            new-t3SncpCurrVc3Sts1Path   Vc3Sts1Num,
            new-t3SncpCurrVc1xVtxPath   Vc1xVtxNum,
            new-t3SncpPPType            XcType,
            new-t3SncpCmd               SncpUserCmd,
            new-t3SncpRevertive         INTEGER
        }

        new-t3SncpUnit  OBJECT-TYPE
            SYNTAX  UnitID
            ACCESS  read-only
            STATUS  mandatory
            DESCRIPTION
                "unit 1 to 8, total 8 units."
            ::= { new-t3SncpApsEty 1 }

        new-t3SncpPort  OBJECT-TYPE
            SYNTAX  PortID
            ACCESS  read-only
            STATUS  mandatory
            DESCRIPTION
                "PORT #1~#3"
            ::= { new-t3SncpApsEty 2 }

        new-t3SncpChannel  OBJECT-TYPE
            SYNTAX  ChannelNum
            ACCESS  read-only
            STATUS  mandatory
            DESCRIPTION
                "CHANNEL #1~#28"
            ::= { new-t3SncpApsEty 3 }

        new-t3SncpCurrSlot  OBJECT-TYPE
            SYNTAX  XcSlot
            ACCESS  read-only
            STATUS  mandatory
            DESCRIPTION
                "SNCP/UPSR current slot"
            ::= { new-t3SncpApsEty 4 }

        new-t3SncpCurrPort  OBJECT-TYPE
            SYNTAX  PortID
            ACCESS  read-only
            STATUS  mandatory
            DESCRIPTION
                "SNCP/UPSR current port"
            ::= { new-t3SncpApsEty 5 }

        new-t3SncpCurrChannel  OBJECT-TYPE
            SYNTAX  ChannelNum
            ACCESS  read-only
            STATUS  mandatory
            DESCRIPTION
                "SNCP/UPSR current channel"
            ::= { new-t3SncpApsEty 6 }

        new-t3SncpCurrAug1Sts3Path  OBJECT-TYPE
            SYNTAX  Aug1Sts3Num
            ACCESS  read-only
            STATUS  mandatory
            DESCRIPTION
                "SNCP/UPSR current Aug1/Sts3"
            ::= { new-t3SncpApsEty 7 }

        new-t3SncpCurrVc3Sts1Path  OBJECT-TYPE
            SYNTAX  Vc3Sts1Num
            ACCESS  read-only
            STATUS  mandatory
            DESCRIPTION
                "SNCP/UPSR current Vc3/Sts1"
            ::= { new-t3SncpApsEty 8 }

        new-t3SncpCurrVc1xVtxPath  OBJECT-TYPE
            SYNTAX  Vc1xVtxNum
            ACCESS  read-only
            STATUS  mandatory
            DESCRIPTION
                "SNCP/UPSR current Vc1x/Vtx"
            ::= { new-t3SncpApsEty 9 }

        new-t3SncpPPType  OBJECT-TYPE
            SYNTAX  XcType
            ACCESS  read-only
            STATUS  mandatory
            DESCRIPTION
                "SNCP/UPSR path protection type"
            ::= { new-t3SncpApsEty 10 }

        new-t3SncpCmd  OBJECT-TYPE
            SYNTAX  SncpUserCmd
            ACCESS  read-write
            STATUS  mandatory
            DESCRIPTION
                "SNCP/UPSR APS command"
            ::= { new-t3SncpApsEty 11 }

        new-t3SncpRevertive  OBJECT-TYPE
            SYNTAX  INTEGER {
                    non-revertive(1),
                    revertive(2)
                }
            ACCESS  read-write
            STATUS  mandatory
            DESCRIPTION
                "SNCP/UPSR revertive or non-revertive"
            ::= { new-t3SncpApsEty 12 }

        t3TotalCard   OBJECT-TYPE
            SYNTAX  INTEGER
            ACCESS  read-only
            STATUS  mandatory
            DESCRIPTION
                "Total cards of T3"
            ::= { t3-card 100 }


--2011-3-18 elvis above
--
--  FOM7 Config
--

    fom7Config           OBJECT IDENTIFIER ::= { fom7-card 1 }


--
-- 7FOM Low Order Trace Message & Signal Label Setup Table
--

        fom7LoVTOverheadSetupTab  OBJECT-TYPE
            SYNTAX  SEQUENCE OF Fom7LoVTOverheadSetupEty
            ACCESS  not-accessible
            STATUS  mandatory
            DESCRIPTION
                "Low Order Trace message & Signal label setup table"
            ::= { fom7Config 1 }

        fom7LoVTOverheadSetupEty  OBJECT-TYPE
            SYNTAX  Fom7LoVTOverheadSetupEty
            ACCESS  not-accessible
            STATUS  mandatory
            DESCRIPTION
                "An entry in the trace message & signal label setup table"
            INDEX { fom7LoVTOverheadUnit ,
                    fom7LoVTOverheadPort ,
                    fom7LoVTOverheadChannel }
            ::= { fom7LoVTOverheadSetupTab 1 }

        Fom7LoVTOverheadSetupEty ::= SEQUENCE {
            fom7LoVTOverheadUnit        UnitID,
            fom7LoVTOverheadPort        PortID,
            fom7LoVTOverheadChannel     ChannelNum,
            fom7LoVTOverheadLength      INTEGER,
            fom7LoVTOverheadExpMsg      DisplayString(SIZE(0..15)),
            fom7LoVTOverheadTxMsg       DisplayString(SIZE(0..15)),
            fom7LoVTOverheadRxMsg       DisplayString(SIZE(0..15)),
            fom7LoVTOverheadEPSL        INTEGER,
            fom7LoVTOverheadTxPSL       INTEGER,
            fom7LoVTOverheadRxPSL       INTEGER
        }

        fom7LoVTOverheadUnit  OBJECT-TYPE
            SYNTAX  UnitID
            ACCESS  read-only
            STATUS  mandatory
            DESCRIPTION
            "unit 1 to 4."
            ::= { fom7LoVTOverheadSetupEty 1 }

        fom7LoVTOverheadPort  OBJECT-TYPE
            SYNTAX  PortID
            ACCESS  read-only
            STATUS  mandatory
            DESCRIPTION
                "FOM Port 1 to 7"
            ::= { fom7LoVTOverheadSetupEty 2 }

        fom7LoVTOverheadChannel  OBJECT-TYPE
            SYNTAX  ChannelNum
            ACCESS  read-only
            STATUS  mandatory
            DESCRIPTION
                "E1/T1 channel 1 to 4 for one FOM"
            ::= { fom7LoVTOverheadSetupEty 3 }

        fom7LoVTOverheadLength  OBJECT-TYPE
            SYNTAX  INTEGER{
                    null(1),
                    len-16-BYTE-space(2),
                    len-16-BYTE-null(4)
                }
            ACCESS  read-write
            STATUS  mandatory
            DESCRIPTION
                "message length"
            ::= { fom7LoVTOverheadSetupEty 4 }

        fom7LoVTOverheadExpMsg OBJECT-TYPE
            SYNTAX  DisplayString (SIZE(0..15))
            ACCESS  read-write
            STATUS  mandatory
            DESCRIPTION
                "The expected message"
            ::= { fom7LoVTOverheadSetupEty 5 }

        fom7LoVTOverheadTxMsg OBJECT-TYPE
            SYNTAX  DisplayString (SIZE(0..15))
            ACCESS  read-write
            STATUS  mandatory
            DESCRIPTION
                "The tx message"
            ::= { fom7LoVTOverheadSetupEty 6 }

        fom7LoVTOverheadRxMsg OBJECT-TYPE
            SYNTAX  DisplayString (SIZE(0..15))
            ACCESS  read-only
            STATUS  mandatory
            DESCRIPTION
                "The rx message"
            ::= { fom7LoVTOverheadSetupEty 7 }

        fom7LoVTOverheadEPSL  OBJECT-TYPE
            SYNTAX  INTEGER(0..7)
            ACCESS  read-write
            STATUS  mandatory
            DESCRIPTION
                "The expected Path Signal Label"
            ::= { fom7LoVTOverheadSetupEty 8 }

        fom7LoVTOverheadTxPSL  OBJECT-TYPE
            SYNTAX  INTEGER(0..7)
            ACCESS  read-write
            STATUS  mandatory
            DESCRIPTION
                "The Tx Path Signal Label"
            ::= { fom7LoVTOverheadSetupEty 9 }

        fom7LoVTOverheadRxPSL  OBJECT-TYPE
            SYNTAX  INTEGER(0..7)
            ACCESS  read-only
            STATUS  mandatory
            DESCRIPTION
                "The Rx Path Signal Label"
            ::= { fom7LoVTOverheadSetupEty 10 }

--
--  7FOM Customer Information Setup Table
--

        fom7CustomerInfoSetupTab  OBJECT-TYPE
            SYNTAX  SEQUENCE OF Fom7CustomerInfoSetupEty
            ACCESS  not-accessible
            STATUS  mandatory
            DESCRIPTION
                "Customer information setup table"
            ::= { fom7Config 2 }

        fom7CustomerInfoSetupEty  OBJECT-TYPE
            SYNTAX  Fom7CustomerInfoSetupEty
            ACCESS  not-accessible
            STATUS  mandatory
            DESCRIPTION
                "An entry in the customer information setup table"
            INDEX { fom7CustomerInfoUnit ,
                    fom7CustomerInfoPort }
            ::= { fom7CustomerInfoSetupTab 1 }

        Fom7CustomerInfoSetupEty ::= SEQUENCE {
            fom7CustomerInfoUnit        UnitID,
            fom7CustomerInfoPort        PortID,
            fom7CustomerInfoString      DisplayString(SIZE(0..64))
        }

        fom7CustomerInfoUnit  OBJECT-TYPE
            SYNTAX  UnitID
            ACCESS  read-only
            STATUS  mandatory
            DESCRIPTION
            "unit 1 to 4."
            ::= { fom7CustomerInfoSetupEty 1 }

        fom7CustomerInfoPort  OBJECT-TYPE
            SYNTAX  PortID
            ACCESS  read-only
            STATUS  mandatory
            DESCRIPTION
                "FOM Port 1 to 7"
            ::= { fom7CustomerInfoSetupEty 2 }

        fom7CustomerInfoString OBJECT-TYPE
            SYNTAX  DisplayString (SIZE(0..64))
            ACCESS  read-write
            STATUS  mandatory
            DESCRIPTION
                "Customer information"
            ::= { fom7CustomerInfoSetupEty 3 }

--
-- 7FOM TPSG Protection Setup Table
--
        fom7TPSGProtectSetupTab  OBJECT-TYPE
            SYNTAX  SEQUENCE OF Fom7TPSGProtectSetupEty
            ACCESS  not-accessible
            STATUS  mandatory
            DESCRIPTION
                "TPSG protection setup table"
            ::= { fom7Config 3 }

        fom7TPSGProtectSetupEty  OBJECT-TYPE
            SYNTAX  Fom7TPSGProtectSetupEty
            ACCESS  not-accessible
            STATUS  mandatory
            DESCRIPTION
                "An entry in the TPSG protection setup table"
            INDEX { fom7TPSGProtectUnit }
            ::= { fom7TPSGProtectSetupTab 1 }

        Fom7TPSGProtectSetupEty ::= SEQUENCE {
            fom7TPSGProtectUnit         UnitID,
            fom7TPSGProtectActive       INTEGER,
            fom7TPSGProtectStatus       INTEGER,
            fom7TPSGProtectType         INTEGER,
            fom7TPSGProtectMode         INTEGER
        }

        fom7TPSGProtectUnit  OBJECT-TYPE
            SYNTAX  UnitID
            ACCESS  read-only
            STATUS  mandatory
            DESCRIPTION
            "unit 1 to 4."
            ::= { fom7TPSGProtectSetupEty 1 }

        fom7TPSGProtectActive  OBJECT-TYPE
            SYNTAX  INTEGER{
                    none(0),
                    standby(1),
                    working(2)
                }
            ACCESS  read-only
            STATUS  mandatory
            DESCRIPTION
                "TPSG active working/standby"
            ::= { fom7TPSGProtectSetupEty 2 }

        fom7TPSGProtectStatus  OBJECT-TYPE
            SYNTAX  INTEGER{
                    sync-failed(1),
                    sync-ok(2),
                    start-sync(3),
                    during-sync(4),
                    update-failed(5),
                    unsync(6)
                }
            ACCESS  read-only
            STATUS  mandatory
            DESCRIPTION
                "TPSG Status"
            ::= { fom7TPSGProtectSetupEty 3 }

        fom7TPSGProtectType  OBJECT-TYPE
            SYNTAX  INTEGER{
                    line-1-plus-1(4)
                }
            ACCESS  read-write
            STATUS  mandatory
            DESCRIPTION
                "TPSG protection type"
            ::= { fom7TPSGProtectSetupEty 4 }

        fom7TPSGProtectMode  OBJECT-TYPE
            SYNTAX  INTEGER{
                    non-revertible(1),
                    revertible(2)
                }
            ACCESS  read-write
            STATUS  mandatory
            DESCRIPTION
                "TPSG protection mode"
            ::= { fom7TPSGProtectSetupEty 5 }


--
-- 7FOM TPSG Protection Switch Table
--
        fom7TPSGProtectSwitchTab  OBJECT-TYPE
            SYNTAX  SEQUENCE OF Fom7TPSGProtectSwitchEty
            ACCESS  not-accessible
            STATUS  mandatory
            DESCRIPTION
                "TPSG protection switch table"
            ::= { fom7Config 4 }

        fom7TPSGProtectSwitchEty  OBJECT-TYPE
            SYNTAX  Fom7TPSGProtectSwitchEty
            ACCESS  not-accessible
            STATUS  mandatory
            DESCRIPTION
                "An entry in the TPSG protection switch table"
            INDEX { fom7TPSGProSwitchUnit ,
                    fom7TPSGProSwitchPort }
            ::= { fom7TPSGProtectSwitchTab 1 }

        Fom7TPSGProtectSwitchEty ::= SEQUENCE {
            fom7TPSGProSwitchUnit       UnitID,
            fom7TPSGProSwitchPort       PortID,
            fom7TPSGProSwitchSide       INTEGER
        }

        fom7TPSGProSwitchUnit  OBJECT-TYPE
            SYNTAX  UnitID
            ACCESS  read-only
            STATUS  mandatory
            DESCRIPTION
            "unit 1 to 4."
            ::= { fom7TPSGProtectSwitchEty 1 }

        fom7TPSGProSwitchPort  OBJECT-TYPE
            SYNTAX  PortID
            ACCESS  read-only
            STATUS  mandatory
            DESCRIPTION
                "FOM Port 1 to 7"
            ::= { fom7TPSGProtectSwitchEty 2 }

        fom7TPSGProSwitchSide  OBJECT-TYPE
            SYNTAX  INTEGER {
                    left(1),
                    right(2)
                }
            ACCESS  read-write
            STATUS  mandatory
            DESCRIPTION
                "Switch Side(left/right)"
            ::= { fom7TPSGProtectSwitchEty 3 }

--
--  7FOM Alarm
--

    fom7Alarm           OBJECT IDENTIFIER ::= { fom7-card 2 }

--
--  7FOM Alarm Mask Setup Table
--

    fom7AlarmMask       OBJECT IDENTIFIER ::= { fom7Alarm 1 }

--
--   Low Order Alarm Mask Setup
--

        fom7LoVTAlmMaskSetupTab  OBJECT-TYPE
            SYNTAX  SEQUENCE OF Fom7LoVTAlmMaskSetupEty
            ACCESS  not-accessible
            STATUS  mandatory
            DESCRIPTION
                "Low Order/VT Alarm mask setup table"
            ::= { fom7AlarmMask 1 }

        fom7LoVTAlmMaskSetupEty  OBJECT-TYPE
            SYNTAX  Fom7LoVTAlmMaskSetupEty
            ACCESS  not-accessible
            STATUS  mandatory
            DESCRIPTION
                "An entry in the alarm mask setup table"
            INDEX { fom7LoVTAlmMaskUnit ,
                    fom7LoVTAlmMaskPort ,
                    fom7LoVTAlmMaskChannel }
            ::= { fom7LoVTAlmMaskSetupTab 1 }

        Fom7LoVTAlmMaskSetupEty ::= SEQUENCE {
            fom7LoVTAlmMaskUnit         UnitID,
            fom7LoVTAlmMaskPort         PortID,
            fom7LoVTAlmMaskChannel      ChannelNum,
            fom7LoVTAlmMask-LOP         INTEGER,
            fom7LoVTAlmMask-AIS         INTEGER,
            fom7LoVTAlmMask-UNEQ        INTEGER,
            fom7LoVTAlmMask-PLM         INTEGER,
            fom7LoVTAlmMask-TIM         INTEGER,
            fom7LoVTAlmMask-RDI-P       INTEGER,
            fom7LoVTAlmMask-RDI-S       INTEGER,
            fom7LoVTAlmMask-RDI-C       INTEGER,
            fom7LoVTAlmMask-V5-REI      INTEGER,
            fom7LoVTAlmMask-V5-BIP      INTEGER
        }

        fom7LoVTAlmMaskUnit  OBJECT-TYPE
            SYNTAX  UnitID
            ACCESS  read-only
            STATUS  mandatory
            DESCRIPTION
            "unit 1 to 4."
            ::= { fom7LoVTAlmMaskSetupEty 1 }

        fom7LoVTAlmMaskPort  OBJECT-TYPE
            SYNTAX  PortID
            ACCESS  read-only
            STATUS  mandatory
            DESCRIPTION
                "FOM Port 1 to 7"
            ::= { fom7LoVTAlmMaskSetupEty 2 }

        fom7LoVTAlmMaskChannel  OBJECT-TYPE
            SYNTAX  ChannelNum
            ACCESS  read-only
            STATUS  mandatory
            DESCRIPTION
                "E1/T1 Channel 1 to 4 for one FOM"
            ::= { fom7LoVTAlmMaskSetupEty 3 }

        fom7LoVTAlmMask-LOP  OBJECT-TYPE
            SYNTAX  INTEGER{
                    disable(1),
                    enable(2)
                }
            ACCESS  read-write
            STATUS  mandatory
            DESCRIPTION
                "tu-lop alarm mask"
            ::= { fom7LoVTAlmMaskSetupEty 4 }

        fom7LoVTAlmMask-AIS  OBJECT-TYPE
            SYNTAX  INTEGER{
                    disable(1),
                    enable(2)
                }
            ACCESS  read-write
            STATUS  mandatory
            DESCRIPTION
                "tu-ais alarm mask"
            ::= { fom7LoVTAlmMaskSetupEty 5 }

        fom7LoVTAlmMask-UNEQ  OBJECT-TYPE
            SYNTAX  INTEGER{
                    disable(1),
                    enable(2)
                }
            ACCESS  read-write
            STATUS  mandatory
            DESCRIPTION
                "lp-uneq alarm mask"
            ::= { fom7LoVTAlmMaskSetupEty 6 }

        fom7LoVTAlmMask-PLM  OBJECT-TYPE
            SYNTAX  INTEGER{
                    disable(1),
                    enable(2)
                }
            ACCESS  read-write
            STATUS  mandatory
            DESCRIPTION
                "lp-plm alarm mask"
            ::= { fom7LoVTAlmMaskSetupEty 7 }

        fom7LoVTAlmMask-TIM  OBJECT-TYPE
            SYNTAX  INTEGER{
                    disable(1),
                    enable(2)
                }
            ACCESS  read-write
            STATUS  mandatory
            DESCRIPTION
                "lp-tim alarm mask"
            ::= { fom7LoVTAlmMaskSetupEty 8 }

        fom7LoVTAlmMask-RDI-P  OBJECT-TYPE
            SYNTAX  INTEGER{
                    disable(1),
                    enable(2)
                }
            ACCESS  read-write
            STATUS  mandatory
            DESCRIPTION
                "lp-rdi-p alarm mask"
            ::= { fom7LoVTAlmMaskSetupEty 9 }

        fom7LoVTAlmMask-RDI-S  OBJECT-TYPE
            SYNTAX  INTEGER{
                    disable(1),
                    enable(2)
                }
            ACCESS  read-write
            STATUS  mandatory
            DESCRIPTION
                "lp-rdi-s alarm mask"
            ::= { fom7LoVTAlmMaskSetupEty 10 }

        fom7LoVTAlmMask-RDI-C  OBJECT-TYPE
            SYNTAX  INTEGER{
                    disable(1),
                    enable(2)
                }
            ACCESS  read-write
            STATUS  mandatory
            DESCRIPTION
                "lp-rdi-c alarm mask"
            ::= { fom7LoVTAlmMaskSetupEty 11 }

        fom7LoVTAlmMask-V5-REI  OBJECT-TYPE
            SYNTAX  INTEGER{
                    disable(1),
                    enable(2)
                }
            ACCESS  read-write
            STATUS  mandatory
            DESCRIPTION
                "lp-rei alarm mask"
            ::= { fom7LoVTAlmMaskSetupEty 12 }

        fom7LoVTAlmMask-V5-BIP  OBJECT-TYPE
            SYNTAX  INTEGER{
                    disable(1),
                    enable(2)
                }
            ACCESS  read-write
            STATUS  mandatory
            DESCRIPTION
                "lp-bip alarm mask"
            ::= { fom7LoVTAlmMaskSetupEty 13 }

--
--   E1T1 Alarm Mask Setup
--

        fom7E1T1AlmMaskSetupTab  OBJECT-TYPE
            SYNTAX  SEQUENCE OF Fom7E1T1AlmMaskSetupEty
            ACCESS  not-accessible
            STATUS  mandatory
            DESCRIPTION
                "FOM E1/T1 Alarm mask setup table"
            ::= { fom7AlarmMask 2 }

        fom7E1T1AlmMaskSetupEty  OBJECT-TYPE
            SYNTAX  Fom7E1T1AlmMaskSetupEty
            ACCESS  not-accessible
            STATUS  mandatory
            DESCRIPTION
                "An entry in the alarm mask setup table"
            INDEX { fom7E1T1AlmMaskUnit ,
                    fom7E1T1AlmMaskPort ,
                    fom7E1T1AlmMaskChannel }
            ::= { fom7E1T1AlmMaskSetupTab 1 }

        Fom7E1T1AlmMaskSetupEty ::= SEQUENCE {
            fom7E1T1AlmMaskUnit         UnitID,
            fom7E1T1AlmMaskPort         PortID,
            fom7E1T1AlmMaskChannel      ChannelNum,
            fom7E1T1AlmMask-AIS         INTEGER
        }

        fom7E1T1AlmMaskUnit  OBJECT-TYPE
            SYNTAX  UnitID
            ACCESS  read-only
            STATUS  mandatory
            DESCRIPTION
            "unit 1 to 4."
            ::= { fom7E1T1AlmMaskSetupEty 1 }

        fom7E1T1AlmMaskPort  OBJECT-TYPE
            SYNTAX  PortID
            ACCESS  read-only
            STATUS  mandatory
            DESCRIPTION
                "Fom Port 1 to 7"
            ::= { fom7E1T1AlmMaskSetupEty 2 }

        fom7E1T1AlmMaskChannel  OBJECT-TYPE
            SYNTAX  ChannelNum
            ACCESS  read-only
            STATUS  mandatory
            DESCRIPTION
                "E1/T1 Channel 1 to 4 for one FOM"
            ::= { fom7E1T1AlmMaskSetupEty 3 }

        fom7E1T1AlmMask-AIS  OBJECT-TYPE
            SYNTAX  INTEGER{
                    disable(1),
                    enable(2)
                }
            ACCESS  read-write
            STATUS  mandatory
            DESCRIPTION
                "E1/T1-ais alarm mask"
            ::= { fom7E1T1AlmMaskSetupEty 4 }

--
--   Line Alarm Mask Setup
--

        fom7FOMAlmMaskSetupTab  OBJECT-TYPE
            SYNTAX  SEQUENCE OF Fom7FOMAlmMaskSetupEty
            ACCESS  not-accessible
            STATUS  mandatory
            DESCRIPTION
                "Line Alarm mask setup table"
            ::= { fom7AlarmMask 3 }

        fom7FOMAlmMaskSetupEty  OBJECT-TYPE
            SYNTAX  Fom7FOMAlmMaskSetupEty
            ACCESS  not-accessible
            STATUS  mandatory
            DESCRIPTION
                "An entry in the alarm mask setup table"
            INDEX { fom7FOMAlmMaskUnit ,
                    fom7FOMAlmMaskPort }
            ::= { fom7FOMAlmMaskSetupTab 1 }

        Fom7FOMAlmMaskSetupEty ::= SEQUENCE {
            fom7FOMAlmMaskUnit          UnitID,
            fom7FOMAlmMaskPort          PortID,
            fom7FOMAlmMask-LOS          INTEGER,
            fom7FOMAlmMask-LOF          INTEGER,
            fom7FOMAlmMask-RAI          INTEGER,
            fom7FOMAlmMask-UAS          INTEGER
        }

        fom7FOMAlmMaskUnit  OBJECT-TYPE
            SYNTAX  UnitID
            ACCESS  read-only
            STATUS  mandatory
            DESCRIPTION
            "unit 1 to 4."
            ::= { fom7FOMAlmMaskSetupEty 1 }

        fom7FOMAlmMaskPort  OBJECT-TYPE
            SYNTAX  PortID
            ACCESS  read-only
            STATUS  mandatory
            DESCRIPTION
                "FOM Port 1 to 7"
            ::= { fom7FOMAlmMaskSetupEty 2 }

        fom7FOMAlmMask-LOS  OBJECT-TYPE
            SYNTAX  INTEGER{
                    disable(1),
                    enable(2)
                }
            ACCESS  read-write
            STATUS  mandatory
            DESCRIPTION
                "line-los alarm mask"
            ::= { fom7FOMAlmMaskSetupEty 3 }

        fom7FOMAlmMask-LOF  OBJECT-TYPE
            SYNTAX  INTEGER{
                    disable(1),
                    enable(2)
                }
            ACCESS  read-write
            STATUS  mandatory
            DESCRIPTION
                "line-lof alarm mask"
            ::= { fom7FOMAlmMaskSetupEty 4 }

        fom7FOMAlmMask-RAI  OBJECT-TYPE
            SYNTAX  INTEGER{
                    disable(1),
                    enable(2)
                }
            ACCESS  read-write
            STATUS  mandatory
            DESCRIPTION
                "line-rai alarm mask"
            ::= { fom7FOMAlmMaskSetupEty 5 }

        fom7FOMAlmMask-UAS  OBJECT-TYPE
            SYNTAX  INTEGER{
                    disable(1),
                    enable(2)
                }
            ACCESS  read-write
            STATUS  mandatory
            DESCRIPTION
                "line-uas alarm mask"
            ::= { fom7FOMAlmMaskSetupEty 6 }

--
--  7FOM Alarm Relay Setup Table
--

    fom7AlarmRelay       OBJECT IDENTIFIER ::= { fom7Alarm 2 }

--
--   Low Order Alarm Relay Setup
--

        fom7LoVTAlmRelaySetupTab  OBJECT-TYPE
            SYNTAX  SEQUENCE OF Fom7LoVTAlmRelaySetupEty
            ACCESS  not-accessible
            STATUS  mandatory
            DESCRIPTION
                "Low Order/VT Alarm relay setup table"
            ::= { fom7AlarmRelay 1 }

        fom7LoVTAlmRelaySetupEty  OBJECT-TYPE
            SYNTAX  Fom7LoVTAlmRelaySetupEty
            ACCESS  not-accessible
            STATUS  mandatory
            DESCRIPTION
                "An entry in the alarm relay setup table"
            INDEX { fom7LoVTAlmRelayUnit ,
                    fom7LoVTAlmRelayPort ,
                    fom7LoVTAlmRelayChannel }
            ::= { fom7LoVTAlmRelaySetupTab 1 }

        Fom7LoVTAlmRelaySetupEty ::= SEQUENCE {
            fom7LoVTAlmRelayUnit        UnitID,
            fom7LoVTAlmRelayPort        PortID,
            fom7LoVTAlmRelayChannel     ChannelNum,
            fom7LoVTAlmRelay-LOP        INTEGER,
            fom7LoVTAlmRelay-AIS        INTEGER,
            fom7LoVTAlmRelay-UNEQ       INTEGER,
            fom7LoVTAlmRelay-PLM        INTEGER,
            fom7LoVTAlmRelay-TIM        INTEGER,
            fom7LoVTAlmRelay-RDI-P      INTEGER,
            fom7LoVTAlmRelay-RDI-S      INTEGER,
            fom7LoVTAlmRelay-RDI-C      INTEGER,
            fom7LoVTAlmRelay-V5-REI     INTEGER,
            fom7LoVTAlmRelay-V5-BIP     INTEGER
        }

        fom7LoVTAlmRelayUnit  OBJECT-TYPE
            SYNTAX  UnitID
            ACCESS  read-only
            STATUS  mandatory
            DESCRIPTION
            "unit 1 to 4."
            ::= { fom7LoVTAlmRelaySetupEty 1 }

        fom7LoVTAlmRelayPort  OBJECT-TYPE
            SYNTAX  PortID
            ACCESS  read-only
            STATUS  mandatory
            DESCRIPTION
                "FOM Port 1 to 7"
            ::= { fom7LoVTAlmRelaySetupEty 2 }

        fom7LoVTAlmRelayChannel  OBJECT-TYPE
            SYNTAX  ChannelNum
            ACCESS  read-only
            STATUS  mandatory
            DESCRIPTION
                "E1/T1 Channel 1 to 4 for one FOM"
            ::= { fom7LoVTAlmRelaySetupEty 3 }

        fom7LoVTAlmRelay-LOP  OBJECT-TYPE
            SYNTAX  INTEGER{
                    disable(1),
                    enable(2)
                }
            ACCESS  read-write
            STATUS  mandatory
            DESCRIPTION
                "tu-lop alarm relay"
            ::= { fom7LoVTAlmRelaySetupEty 4 }

        fom7LoVTAlmRelay-AIS  OBJECT-TYPE
            SYNTAX  INTEGER{
                    disable(1),
                    enable(2)
                }
            ACCESS  read-write
            STATUS  mandatory
            DESCRIPTION
                "tu-ais alarm relay"
            ::= { fom7LoVTAlmRelaySetupEty 5 }

        fom7LoVTAlmRelay-UNEQ  OBJECT-TYPE
            SYNTAX  INTEGER{
                    disable(1),
                    enable(2)
                }
            ACCESS  read-write
            STATUS  mandatory
            DESCRIPTION
                "lp-uneq alarm relay"
            ::= { fom7LoVTAlmRelaySetupEty 6 }

        fom7LoVTAlmRelay-PLM  OBJECT-TYPE
            SYNTAX  INTEGER{
                    disable(1),
                    enable(2)
                }
            ACCESS  read-write
            STATUS  mandatory
            DESCRIPTION
                "lp-plm alarm relay"
            ::= { fom7LoVTAlmRelaySetupEty 7 }

        fom7LoVTAlmRelay-TIM  OBJECT-TYPE
            SYNTAX  INTEGER{
                    disable(1),
                    enable(2)
                }
            ACCESS  read-write
            STATUS  mandatory
            DESCRIPTION
                "lp-tim alarm relay"
            ::= { fom7LoVTAlmRelaySetupEty 8 }

        fom7LoVTAlmRelay-RDI-P  OBJECT-TYPE
            SYNTAX  INTEGER{
                    disable(1),
                    enable(2)
                }
            ACCESS  read-write
            STATUS  mandatory
            DESCRIPTION
                "lp-rdi-p alarm relay"
            ::= { fom7LoVTAlmRelaySetupEty 9 }

        fom7LoVTAlmRelay-RDI-S  OBJECT-TYPE
            SYNTAX  INTEGER{
                    disable(1),
                    enable(2)
                }
            ACCESS  read-write
            STATUS  mandatory
            DESCRIPTION
                "lp-rdi-s alarm relay"
            ::= { fom7LoVTAlmRelaySetupEty 10 }

        fom7LoVTAlmRelay-RDI-C  OBJECT-TYPE
            SYNTAX  INTEGER{
                    disable(1),
                    enable(2)
                }
            ACCESS  read-write
            STATUS  mandatory
            DESCRIPTION
                "lp-rdi-c alarm relay"
            ::= { fom7LoVTAlmRelaySetupEty 11 }

        fom7LoVTAlmRelay-V5-REI  OBJECT-TYPE
            SYNTAX  INTEGER{
                    disable(1),
                    enable(2)
                }
            ACCESS  read-write
            STATUS  mandatory
            DESCRIPTION
                "lp-rei alarm relay"
            ::= { fom7LoVTAlmRelaySetupEty 12 }

        fom7LoVTAlmRelay-V5-BIP  OBJECT-TYPE
            SYNTAX  INTEGER{
                    disable(1),
                    enable(2)
                }
            ACCESS  read-write
            STATUS  mandatory
            DESCRIPTION
                "lp-bip alarm relay"
            ::= { fom7LoVTAlmRelaySetupEty 13 }

--
--   E1T1 Alarm Relay Setup
--

        fom7E1T1AlmRelaySetupTab  OBJECT-TYPE
            SYNTAX  SEQUENCE OF Fom7E1T1AlmRelaySetupEty
            ACCESS  not-accessible
            STATUS  mandatory
            DESCRIPTION
                "FOM E1/T1 Alarm relay setup table"
            ::= { fom7AlarmRelay 2 }

        fom7E1T1AlmRelaySetupEty  OBJECT-TYPE
            SYNTAX  Fom7E1T1AlmRelaySetupEty
            ACCESS  not-accessible
            STATUS  mandatory
            DESCRIPTION
                "An entry in the alarm relay setup table"
            INDEX { fom7E1T1AlmRelayUnit ,
                    fom7E1T1AlmRelayPort ,
                    fom7E1T1AlmRelayChannel }
            ::= { fom7E1T1AlmRelaySetupTab 1 }

        Fom7E1T1AlmRelaySetupEty ::= SEQUENCE {
            fom7E1T1AlmRelayUnit        UnitID,
            fom7E1T1AlmRelayPort        PortID,
            fom7E1T1AlmRelayChannel     ChannelNum,
            fom7E1T1AlmRelay-AIS        INTEGER
        }

        fom7E1T1AlmRelayUnit  OBJECT-TYPE
            SYNTAX  UnitID
            ACCESS  read-only
            STATUS  mandatory
            DESCRIPTION
            "unit 1 to 4."
            ::= { fom7E1T1AlmRelaySetupEty 1 }

        fom7E1T1AlmRelayPort  OBJECT-TYPE
            SYNTAX  PortID
            ACCESS  read-only
            STATUS  mandatory
            DESCRIPTION
                "Fom Port 1 to 7"
            ::= { fom7E1T1AlmRelaySetupEty 2 }

        fom7E1T1AlmRelayChannel  OBJECT-TYPE
            SYNTAX  ChannelNum
            ACCESS  read-only
            STATUS  mandatory
            DESCRIPTION
                "E1/T1 Channel 1 to 4 for one FOM"
            ::= { fom7E1T1AlmRelaySetupEty 3 }

        fom7E1T1AlmRelay-AIS  OBJECT-TYPE
            SYNTAX  INTEGER{
                    disable(1),
                    enable(2)
                }
            ACCESS  read-write
            STATUS  mandatory
            DESCRIPTION
                "E1/T1-ais alarm relay"
            ::= { fom7E1T1AlmRelaySetupEty 4 }

--
--   Line Alarm Relay Setup
--

        fom7FOMAlmRelaySetupTab  OBJECT-TYPE
            SYNTAX  SEQUENCE OF Fom7FOMAlmRelaySetupEty
            ACCESS  not-accessible
            STATUS  mandatory
            DESCRIPTION
                "Line Alarm relay setup table"
            ::= { fom7AlarmRelay 3 }

        fom7FOMAlmRelaySetupEty  OBJECT-TYPE
            SYNTAX  Fom7FOMAlmRelaySetupEty
            ACCESS  not-accessible
            STATUS  mandatory
            DESCRIPTION
                "An entry in the alarm relay setup table"
            INDEX { fom7FOMAlmRelayUnit ,
                    fom7FOMAlmRelayPort }
            ::= { fom7FOMAlmRelaySetupTab 1 }

        Fom7FOMAlmRelaySetupEty ::= SEQUENCE {
            fom7FOMAlmRelayUnit         UnitID,
            fom7FOMAlmRelayPort         PortID,
            fom7FOMAlmRelay-LOS         INTEGER,
            fom7FOMAlmRelay-LOF         INTEGER,
            fom7FOMAlmRelay-RAI         INTEGER,
            fom7FOMAlmRelay-UAS         INTEGER
        }

        fom7FOMAlmRelayUnit  OBJECT-TYPE
            SYNTAX  UnitID
            ACCESS  read-only
            STATUS  mandatory
            DESCRIPTION
            "unit 1 to 4."
            ::= { fom7FOMAlmRelaySetupEty 1 }

        fom7FOMAlmRelayPort  OBJECT-TYPE
            SYNTAX  PortID
            ACCESS  read-only
            STATUS  mandatory
            DESCRIPTION
                "FOM Port 1 to 7"
            ::= { fom7FOMAlmRelaySetupEty 2 }

        fom7FOMAlmRelay-LOS  OBJECT-TYPE
            SYNTAX  INTEGER{
                    disable(1),
                    enable(2)
                }
            ACCESS  read-write
            STATUS  mandatory
            DESCRIPTION
                "line-los alarm relay"
            ::= { fom7FOMAlmRelaySetupEty 3 }

        fom7FOMAlmRelay-LOF  OBJECT-TYPE
            SYNTAX  INTEGER{
                    disable(1),
                    enable(2)
                }
            ACCESS  read-write
            STATUS  mandatory
            DESCRIPTION
                "line-lof alarm relay"
            ::= { fom7FOMAlmRelaySetupEty 4 }

        fom7FOMAlmRelay-RAI  OBJECT-TYPE
            SYNTAX  INTEGER{
                    disable(1),
                    enable(2)
                }
            ACCESS  read-write
            STATUS  mandatory
            DESCRIPTION
                "line-rai alarm relay"
            ::= { fom7FOMAlmRelaySetupEty 5 }

        fom7FOMAlmRelay-UAS  OBJECT-TYPE
            SYNTAX  INTEGER{
                    disable(1),
                    enable(2)
                }
            ACCESS  read-write
            STATUS  mandatory
            DESCRIPTION
                "line-uas alarm relay"
            ::= { fom7FOMAlmRelaySetupEty 6 }

--
--  7FOM Alarm Severity Setup Table
--

        fom7AlmSeveritySetupTab  OBJECT-TYPE
            SYNTAX  SEQUENCE OF Fom7AlmSeveritySetupEty
            ACCESS  not-accessible
            STATUS  mandatory
            DESCRIPTION
                "Alarm severity setup table"
            ::= { fom7Alarm 3 }

        fom7AlmSeveritySetupEty  OBJECT-TYPE
            SYNTAX  Fom7AlmSeveritySetupEty
            ACCESS  not-accessible
            STATUS  mandatory
            DESCRIPTION
                "An entry in the alarm severity setup table"
            INDEX { fom7AlmSvrityUnit }
            ::= { fom7AlmSeveritySetupTab 1 }

        Fom7AlmSeveritySetupEty ::= SEQUENCE {
            fom7AlmSvrityUnit           UnitID,
            fom7AlmSvrityLoVT-LOP       Severity,
            fom7AlmSvrityLoVT-AIS       Severity,
            fom7AlmSvrityLoVT-UNEQ      Severity,
            fom7AlmSvrityLoVT-PLM       Severity,
            fom7AlmSvrityLoVT-TIM       Severity,
            fom7AlmSvrityLoVT-RDI-P     Severity,
            fom7AlmSvrityLoVT-RDI-S     Severity,
            fom7AlmSvrityLoVT-RDI-C     Severity,
            fom7AlmSvrityLoVT-V5-REI    Severity,
            fom7AlmSvrityLoVT-V5-BIP    Severity,
            fom7AlmSvrityE1T1-AIS       Severity,
            fom7AlmSvrityFOM-LOS        Severity,
            fom7AlmSvrityFOM-LOF        Severity,
            fom7AlmSvrityFOM-RAI        Severity,
            fom7AlmSvrityFOM-UAS        Severity
        }

        fom7AlmSvrityUnit  OBJECT-TYPE
            SYNTAX  UnitID
            ACCESS  read-only
            STATUS  mandatory
            DESCRIPTION
            "unit 1 to 4."
            ::= { fom7AlmSeveritySetupEty 1 }

        fom7AlmSvrityLoVT-LOP  OBJECT-TYPE
            SYNTAX  Severity
            ACCESS  read-write
            STATUS  mandatory
            DESCRIPTION
                "tu-lop alarm severity type"
            ::= { fom7AlmSeveritySetupEty 2 }

        fom7AlmSvrityLoVT-AIS  OBJECT-TYPE
            SYNTAX  Severity
            ACCESS  read-write
            STATUS  mandatory
            DESCRIPTION
                "tu-ais alarm severity type"
            ::= { fom7AlmSeveritySetupEty 3 }

        fom7AlmSvrityLoVT-UNEQ  OBJECT-TYPE
            SYNTAX  Severity
            ACCESS  read-write
            STATUS  mandatory
            DESCRIPTION
                "lp-uneq alarm severity type"
            ::= { fom7AlmSeveritySetupEty 4 }

        fom7AlmSvrityLoVT-PLM  OBJECT-TYPE
            SYNTAX  Severity
            ACCESS  read-write
            STATUS  mandatory
            DESCRIPTION
                "lp-plm alarm severity type"
            ::= { fom7AlmSeveritySetupEty 5 }

        fom7AlmSvrityLoVT-TIM  OBJECT-TYPE
            SYNTAX  Severity
            ACCESS  read-write
            STATUS  mandatory
            DESCRIPTION
                "lp-tim alarm severity type"
            ::= { fom7AlmSeveritySetupEty 6 }

        fom7AlmSvrityLoVT-RDI-P  OBJECT-TYPE
            SYNTAX  Severity
            ACCESS  read-write
            STATUS  mandatory
            DESCRIPTION
                "lp-rdi-p alarm severity type"
            ::= { fom7AlmSeveritySetupEty 7 }

        fom7AlmSvrityLoVT-RDI-S  OBJECT-TYPE
            SYNTAX  Severity
            ACCESS  read-write
            STATUS  mandatory
            DESCRIPTION
                "lp-rdi-s alarm severity type"
            ::= { fom7AlmSeveritySetupEty 8 }

        fom7AlmSvrityLoVT-RDI-C  OBJECT-TYPE
            SYNTAX  Severity
            ACCESS  read-write
            STATUS  mandatory
            DESCRIPTION
                "lp-rdi-c alarm severity type"
            ::= { fom7AlmSeveritySetupEty 9 }

        fom7AlmSvrityLoVT-V5-REI  OBJECT-TYPE
            SYNTAX  Severity
            ACCESS  read-write
            STATUS  mandatory
            DESCRIPTION
                "lp-rei alarm severity type"
            ::= { fom7AlmSeveritySetupEty 10 }

        fom7AlmSvrityLoVT-V5-BIP  OBJECT-TYPE
            SYNTAX  Severity
            ACCESS  read-write
            STATUS  mandatory
            DESCRIPTION
                "lp-bip alarm severity type"
            ::= { fom7AlmSeveritySetupEty 11 }

        fom7AlmSvrityE1T1-AIS  OBJECT-TYPE
            SYNTAX  Severity
            ACCESS  read-write
            STATUS  mandatory
            DESCRIPTION
                "E1/T1 AIS alarm severity type"
            ::= { fom7AlmSeveritySetupEty 12 }

        fom7AlmSvrityFOM-LOS  OBJECT-TYPE
            SYNTAX  Severity
            ACCESS  read-write
            STATUS  mandatory
            DESCRIPTION
                "FOM-los alarm severity type"
            ::= { fom7AlmSeveritySetupEty 13 }

        fom7AlmSvrityFOM-LOF  OBJECT-TYPE
            SYNTAX  Severity
            ACCESS  read-write
            STATUS  mandatory
            DESCRIPTION
                "FOM-lof alarm severity type"
            ::= { fom7AlmSeveritySetupEty 14 }

        fom7AlmSvrityFOM-RAI  OBJECT-TYPE
            SYNTAX  Severity
            ACCESS  read-write
            STATUS  mandatory
            DESCRIPTION
                "FOM-rai alarm severity type"
            ::= { fom7AlmSeveritySetupEty 15 }

        fom7AlmSvrityFOM-UAS  OBJECT-TYPE
            SYNTAX  Severity
            ACCESS  read-write
            STATUS  mandatory
            DESCRIPTION
                "FOM-uas alarm severity type"
            ::= { fom7AlmSeveritySetupEty 16 }

--
--  7FOM Insert AIS Alarm Setup Table
--

        fom7InsertAisAlmSetupTab  OBJECT-TYPE
            SYNTAX  SEQUENCE OF Fom7InsertAisAlmSetupEty
            ACCESS  not-accessible
            STATUS  mandatory
            DESCRIPTION
                "Insert AIS alarm setup table"
            ::= { fom7Alarm 4 }

        fom7InsertAisAlmSetupEty  OBJECT-TYPE
            SYNTAX  Fom7InsertAisAlmSetupEty
            ACCESS  not-accessible
            STATUS  mandatory
            DESCRIPTION
                "An entry in the insert AIS alarm setup table"
            INDEX { fom7InstUnit }
            ::= { fom7InsertAisAlmSetupTab 1 }

        Fom7InsertAisAlmSetupEty ::= SEQUENCE {
            fom7InstUnit                UnitID,
            fom7InstLpUneqVToAis        INTEGER,
            fom7InstLpTimVToAis         INTEGER,
            fom7InstLpPlmVToAis         INTEGER
        }

        fom7InstUnit  OBJECT-TYPE
            SYNTAX  UnitID
            ACCESS  read-only
            STATUS  mandatory
            DESCRIPTION
            "unit 1 to 4."
            ::= { fom7InsertAisAlmSetupEty 1 }

        fom7InstLpUneqVToAis OBJECT-TYPE
            SYNTAX  INTEGER {
                    disable(1),
                    enable(2)
                }
            ACCESS  read-write
            STATUS  mandatory
            DESCRIPTION
                "LP-UNEQ/UNEQ-V to AIS"
            ::= { fom7InsertAisAlmSetupEty 2 }

        fom7InstLpTimVToAis OBJECT-TYPE
            SYNTAX  INTEGER {
                    disable(1),
                    enable(2)
                }
            ACCESS  read-write
            STATUS  mandatory
            DESCRIPTION
                "LP-TIM/TIM-V to AIS"
            ::= { fom7InsertAisAlmSetupEty 3 }

        fom7InstLpPlmVToAis OBJECT-TYPE
            SYNTAX  INTEGER {
                    disable(1),
                    enable(2)
                }
            ACCESS  read-write
            STATUS  mandatory
            DESCRIPTION
                "LP-PLM/PLM-V to AIS"
            ::= { fom7InsertAisAlmSetupEty 4 }

--
--  7FOM Current Alarm Status Table
--

    fom7CurrAlmStatusTab       OBJECT IDENTIFIER ::= { fom7Alarm 5 }

--
--   Low Order Current Alarm Status
--

        fom7LoVTCurAlmStatusTab  OBJECT-TYPE
            SYNTAX  SEQUENCE OF Fom7LoVTCurAlmStatusEty
            ACCESS  not-accessible
            STATUS  mandatory
            DESCRIPTION
                "Low Order/VT Alarm mask setup table"
            ::= { fom7CurrAlmStatusTab 1 }

        fom7LoVTCurAlmStatusEty  OBJECT-TYPE
            SYNTAX  Fom7LoVTCurAlmStatusEty
            ACCESS  not-accessible
            STATUS  mandatory
            DESCRIPTION
                "An entry in the alarm mask setup table"
            INDEX { fom7LoVTCurAlmUnit ,
                    fom7LoVTCurAlmPort ,
                    fom7LoVTCurAlmChannel }
            ::= { fom7LoVTCurAlmStatusTab 1 }

        Fom7LoVTCurAlmStatusEty ::= SEQUENCE {
            fom7LoVTCurAlmUnit          UnitID,
            fom7LoVTCurAlmPort          PortID,
            fom7LoVTCurAlmChannel       ChannelNum,
            fom7LoVTCurAlm-LOP          AlmStatus,
            fom7LoVTCurAlm-AIS          AlmStatus,
            fom7LoVTCurAlm-UNEQ         AlmStatus,
            fom7LoVTCurAlm-PLM          AlmStatus,
            fom7LoVTCurAlm-TIM          AlmStatus,
            fom7LoVTCurAlm-RDI-P        AlmStatus,
            fom7LoVTCurAlm-RDI-S        AlmStatus,
            fom7LoVTCurAlm-RDI-C        AlmStatus,
            fom7LoVTCurAlm-V5-REI       AlmStatus,
            fom7LoVTCurAlm-V5-BIP       AlmStatus
        }

        fom7LoVTCurAlmUnit  OBJECT-TYPE
            SYNTAX  UnitID
            ACCESS  read-only
            STATUS  mandatory
            DESCRIPTION
            "unit 1 to 4."
            ::= { fom7LoVTCurAlmStatusEty 1 }

        fom7LoVTCurAlmPort  OBJECT-TYPE
            SYNTAX  PortID
            ACCESS  read-only
            STATUS  mandatory
            DESCRIPTION
                "FOM Port 1 to 7"
            ::= { fom7LoVTCurAlmStatusEty 2 }

        fom7LoVTCurAlmChannel  OBJECT-TYPE
            SYNTAX  ChannelNum
            ACCESS  read-only
            STATUS  mandatory
            DESCRIPTION
                "E1/T1 Channel 1 to 4"
            ::= { fom7LoVTCurAlmStatusEty 3 }

        fom7LoVTCurAlm-LOP  OBJECT-TYPE
            SYNTAX  AlmStatus
            ACCESS  read-only
            STATUS  mandatory
            DESCRIPTION
                "tu-lop alarm status"
            ::= { fom7LoVTCurAlmStatusEty 4 }

        fom7LoVTCurAlm-AIS  OBJECT-TYPE
            SYNTAX  AlmStatus
            ACCESS  read-only
            STATUS  mandatory
            DESCRIPTION
                "tu-ais alarm status"
            ::= { fom7LoVTCurAlmStatusEty 5 }

        fom7LoVTCurAlm-UNEQ  OBJECT-TYPE
            SYNTAX  AlmStatus
            ACCESS  read-only
            STATUS  mandatory
            DESCRIPTION
                "lp-uneq alarm status"
            ::= { fom7LoVTCurAlmStatusEty 6 }

        fom7LoVTCurAlm-PLM  OBJECT-TYPE
            SYNTAX  AlmStatus
            ACCESS  read-only
            STATUS  mandatory
            DESCRIPTION
                "lp-plm alarm status"
            ::= { fom7LoVTCurAlmStatusEty 7 }

        fom7LoVTCurAlm-TIM  OBJECT-TYPE
            SYNTAX  AlmStatus
            ACCESS  read-only
            STATUS  mandatory
            DESCRIPTION
                "lp-tim alarm status"
            ::= { fom7LoVTCurAlmStatusEty 8 }

        fom7LoVTCurAlm-RDI-P  OBJECT-TYPE
            SYNTAX  AlmStatus
            ACCESS  read-only
            STATUS  mandatory
            DESCRIPTION
                "lp-rdi-p alarm status"
            ::= { fom7LoVTCurAlmStatusEty 9 }

        fom7LoVTCurAlm-RDI-S  OBJECT-TYPE
            SYNTAX  AlmStatus
            ACCESS  read-only
            STATUS  mandatory
            DESCRIPTION
                "lp-rdi-s alarm status"
            ::= { fom7LoVTCurAlmStatusEty 10 }

        fom7LoVTCurAlm-RDI-C  OBJECT-TYPE
            SYNTAX  AlmStatus
            ACCESS  read-only
            STATUS  mandatory
            DESCRIPTION
                "lp-rdi-c alarm status"
            ::= { fom7LoVTCurAlmStatusEty 11 }

        fom7LoVTCurAlm-V5-REI  OBJECT-TYPE
            SYNTAX  AlmStatus
            ACCESS  read-only
            STATUS  mandatory
            DESCRIPTION
                "lp-rei alarm status"
            ::= { fom7LoVTCurAlmStatusEty 12 }

        fom7LoVTCurAlm-V5-BIP  OBJECT-TYPE
            SYNTAX  AlmStatus
            ACCESS  read-only
            STATUS  mandatory
            DESCRIPTION
                "lp-bip alarm status"
            ::= { fom7LoVTCurAlmStatusEty 13 }

--
--   7FOM E1/T1 Current Alarm Status
--

        fom7E1T1CurAlmStatusTab  OBJECT-TYPE
            SYNTAX  SEQUENCE OF Fom7E1T1CurAlmStatusEty
            ACCESS  not-accessible
            STATUS  mandatory
            DESCRIPTION
                "E1/T1 Alarm mask setup table"
            ::= { fom7CurrAlmStatusTab 2 }

        fom7E1T1CurAlmStatusEty  OBJECT-TYPE
            SYNTAX  Fom7E1T1CurAlmStatusEty
            ACCESS  not-accessible
            STATUS  mandatory
            DESCRIPTION
                "An entry in the alarm mask setup table"
            INDEX { fom7E1T1CurAlmUnit ,
                    fom7E1T1CurAlmPort ,
                    fom7E1T1CurAlmChannel }
            ::= { fom7E1T1CurAlmStatusTab 1 }

        Fom7E1T1CurAlmStatusEty ::= SEQUENCE {
            fom7E1T1CurAlmUnit          UnitID,
            fom7E1T1CurAlmPort          PortID,
            fom7E1T1CurAlmChannel       ChannelNum,
            fom7E1T1CurAlm-AIS          AlmStatus
        }

        fom7E1T1CurAlmUnit  OBJECT-TYPE
            SYNTAX  UnitID
            ACCESS  read-only
            STATUS  mandatory
            DESCRIPTION
            "unit 1 to 4."
            ::= { fom7E1T1CurAlmStatusEty 1 }

        fom7E1T1CurAlmPort  OBJECT-TYPE
            SYNTAX  PortID
            ACCESS  read-only
            STATUS  mandatory
            DESCRIPTION
                "FOM Port 1 to 7"
            ::= { fom7E1T1CurAlmStatusEty 2 }

        fom7E1T1CurAlmChannel  OBJECT-TYPE
            SYNTAX  ChannelNum
            ACCESS  read-only
            STATUS  mandatory
            DESCRIPTION
                "E1/T1 Channel 1 to 4 for one FOM"
            ::= { fom7E1T1CurAlmStatusEty 3 }

        fom7E1T1CurAlm-AIS  OBJECT-TYPE
            SYNTAX  AlmStatus
            ACCESS  read-only
            STATUS  mandatory
            DESCRIPTION
                "AIS alarm status"
            ::= { fom7E1T1CurAlmStatusEty 4 }

--
--   FOM Alarm Current Alarm Status
--

        fom7FOMCurAlmStatusTab  OBJECT-TYPE
            SYNTAX  SEQUENCE OF Fom7FOMCurAlmStatusEty
            ACCESS  not-accessible
            STATUS  mandatory
            DESCRIPTION
                "FOM Alarm mask setup table"
            ::= { fom7CurrAlmStatusTab 3 }

        fom7FOMCurAlmStatusEty  OBJECT-TYPE
            SYNTAX  Fom7FOMCurAlmStatusEty
            ACCESS  not-accessible
            STATUS  mandatory
            DESCRIPTION
                "An entry in the alarm mask setup table"
            INDEX { fom7FOMCurAlmUnit ,
                    fom7FOMCurAlmPort }
            ::= { fom7FOMCurAlmStatusTab 1 }

        Fom7FOMCurAlmStatusEty ::= SEQUENCE {
            fom7FOMCurAlmUnit           UnitID,
            fom7FOMCurAlmPort           PortID,
            fom7FOMCurAlm-LOS           AlmStatus,
            fom7FOMCurAlm-LOF           AlmStatus,
            fom7FOMCurAlm-RAI           AlmStatus,
            fom7FOMCurAlm-UAS           AlmStatus
        }

        fom7FOMCurAlmUnit  OBJECT-TYPE
            SYNTAX  UnitID
            ACCESS  read-only
            STATUS  mandatory
            DESCRIPTION
            "unit 1 to 4."
            ::= { fom7FOMCurAlmStatusEty 1 }

        fom7FOMCurAlmPort  OBJECT-TYPE
            SYNTAX  PortID
            ACCESS  read-only
            STATUS  mandatory
            DESCRIPTION
                "FOM Port 1 to 7"
            ::= { fom7FOMCurAlmStatusEty 2 }

        fom7FOMCurAlm-LOS  OBJECT-TYPE
            SYNTAX  AlmStatus
            ACCESS  read-only
            STATUS  mandatory
            DESCRIPTION
                "FOM-los alarm status"
            ::= { fom7FOMCurAlmStatusEty 3 }

        fom7FOMCurAlm-LOF  OBJECT-TYPE
            SYNTAX  AlmStatus
            ACCESS  read-only
            STATUS  mandatory
            DESCRIPTION
                "FOM-lof alarm status"
            ::= { fom7FOMCurAlmStatusEty 4 }

        fom7FOMCurAlm-RAI  OBJECT-TYPE
            SYNTAX  AlmStatus
            ACCESS  read-only
            STATUS  mandatory
            DESCRIPTION
                "FOM-rai alarm status"
            ::= { fom7FOMCurAlmStatusEty 5 }

        fom7FOMCurAlm-UAS  OBJECT-TYPE
            SYNTAX  AlmStatus
            ACCESS  read-only
            STATUS  mandatory
            DESCRIPTION
                "FOM-uas alarm status"
            ::= { fom7FOMCurAlmStatusEty 6 }

--
--  7FOM Current Active Alarm Summary Table
--
        fom7CurrActAlmSummaryTab  OBJECT-TYPE
            SYNTAX  SEQUENCE OF Fom7CurrActAlmSummaryEty
            ACCESS  not-accessible
            STATUS  mandatory
            DESCRIPTION
                "7FOM Current Active Alarm Summary Table."
            ::= { fom7Alarm 6 }

        fom7CurrActAlmSummaryEty  OBJECT-TYPE
            SYNTAX  Fom7CurrActAlmSummaryEty
            ACCESS  not-accessible
            STATUS  mandatory
            DESCRIPTION
                "7FOM current active alarm summary entry"
            INDEX { fom7AlmSumUnit ,
                    fom7AlmSumIndex }
            ::= { fom7CurrActAlmSummaryTab 1 }

        Fom7CurrActAlmSummaryEty ::= SEQUENCE {
            fom7AlmSumUnit              UnitID,
            fom7AlmSumIndex             INTEGER,
            fom7AlmSumString            DisplayString (SIZE(0..255)),
            fom7AlmSumUnitNum           CardID,
            fom7AlmSumCardModel         CardModel,
            fom7AlmSumPortNum           PortID,
            fom7AlmSumChannel           ChannelNum,
            fom7AlmSumAlmNum            AlarmNum,
            fom7AlmSumStatus            AlmStatus,
            fom7AlmSumSeverity          Severity
        }

        fom7AlmSumUnit  OBJECT-TYPE
            SYNTAX  UnitID
            ACCESS  read-only
            STATUS  mandatory
            DESCRIPTION
            "unit 1 to 4."
            ::= { fom7CurrActAlmSummaryEty 1 }

        fom7AlmSumIndex  OBJECT-TYPE
            SYNTAX  INTEGER
            ACCESS  read-only
            STATUS  mandatory
            DESCRIPTION
                "Select Alarm Summary Index"
            ::= { fom7CurrActAlmSummaryEty 2 }

        fom7AlmSumString  OBJECT-TYPE
            SYNTAX  DisplayString (SIZE (0..255))
            ACCESS  read-only
            STATUS  mandatory
            DESCRIPTION
                "Alarm Summary String"
            ::= { fom7CurrActAlmSummaryEty 3 }

        fom7AlmSumUnitNum  OBJECT-TYPE
            SYNTAX  CardID
            ACCESS  read-only
            STATUS  mandatory
            DESCRIPTION
            "Xcu or Unit 1~4,11~16"
            ::= { fom7CurrActAlmSummaryEty 4 }

        fom7AlmSumCardModel  OBJECT-TYPE
            SYNTAX  CardModel
            ACCESS  read-only
            STATUS  mandatory
            DESCRIPTION
                "Card Model"
            ::= { fom7CurrActAlmSummaryEty 5 }

        fom7AlmSumPortNum  OBJECT-TYPE
            SYNTAX  PortID
            ACCESS  read-only
            STATUS  mandatory
            DESCRIPTION
                "Port number(1..7)"
            ::= { fom7CurrActAlmSummaryEty 6 }

        fom7AlmSumChannel  OBJECT-TYPE
            SYNTAX  ChannelNum
            ACCESS  read-only
            STATUS  mandatory
            DESCRIPTION
                "Channel number(1..4)"
            ::= { fom7CurrActAlmSummaryEty 7 }

        fom7AlmSumAlmNum  OBJECT-TYPE
            SYNTAX  AlarmNum
            ACCESS  read-only
            STATUS  mandatory
            DESCRIPTION
                "Alarm Num"
            ::= { fom7CurrActAlmSummaryEty 8 }

        fom7AlmSumStatus  OBJECT-TYPE
            SYNTAX  AlmStatus
            ACCESS  read-only
            STATUS  mandatory
            DESCRIPTION
                "The Status of Alarm"
            ::= { fom7CurrActAlmSummaryEty 9 }

        fom7AlmSumSeverity  OBJECT-TYPE
            SYNTAX  Severity
            ACCESS  read-only
            STATUS  mandatory
            DESCRIPTION
                "Alarm Severity"
            ::= { fom7CurrActAlmSummaryEty 10 }

--
-- 7FOM FOM Status Table
--

        fom7FomStatusTab  OBJECT-TYPE
            SYNTAX  SEQUENCE OF  Fom7FomStatusEty
            ACCESS  not-accessible
            STATUS  mandatory
            DESCRIPTION
                "7FOM FOM Status table "
            ::= { fom7Alarm 7 }

        fom7FomStatusEty  OBJECT-TYPE
            SYNTAX  Fom7FomStatusEty
            ACCESS  not-accessible
            STATUS  mandatory
            DESCRIPTION
                "7FOM FOM Status entry"
            INDEX { fom7FomUnit , fom7FomPort }
            ::= { fom7FomStatusTab 1 }

        Fom7FomStatusEty ::= SEQUENCE {
            fom7FomUnit                 UnitID,
            fom7FomPort                 PortID,
            fom7FomNeType               INTEGER,
            fom7FomNeLof                INTEGER,
            fom7FomNeFrameErr           INTEGER,
            fom7FomNeChksumErr          INTEGER,
            fom7FomFeType               INTEGER,
            fom7FomFeLof                INTEGER,
            fom7FomFeFrameErr           INTEGER,
            fom7FomFeChksumErr          INTEGER,
            fom7FomFeE1T1Cnan1LosLof    INTEGER,
            fom7FomFeE1T1Cnan2LosLof    INTEGER,
            fom7FomFeE1T1Cnan3LosLof    INTEGER,
            fom7FomFeE1T1Cnan4LosLof    INTEGER,
            fom7FomFeE1T1Cnan1BpvCrc    INTEGER,
            fom7FomFeE1T1Cnan2BpvCrc    INTEGER,
            fom7FomFeE1T1Cnan3BpvCrc    INTEGER,
            fom7FomFeE1T1Cnan4BpvCrc    INTEGER
        }

        fom7FomUnit  OBJECT-TYPE
            SYNTAX  UnitID
            ACCESS  read-only
            STATUS  mandatory
            DESCRIPTION
            "unit 1 to 4."
            ::= { fom7FomStatusEty  1 }

        fom7FomPort  OBJECT-TYPE
            SYNTAX  PortID
            ACCESS  read-only
            STATUS  mandatory
            DESCRIPTION
                "PORT #1~#7"
            ::= { fom7FomStatusEty  2 }

        fom7FomNeType  OBJECT-TYPE
            SYNTAX  INTEGER {
                    unknown(1),
                    cpe-with-cpu(2),
                    mux-fom(3),
                    cpe-without-CPU(4),
                    fom7(11)
                }
            ACCESS  read-only
            STATUS  mandatory
            DESCRIPTION
                "Near-End FOM Type"
            ::= { fom7FomStatusEty 3 }

        fom7FomNeLof  OBJECT-TYPE
            SYNTAX  INTEGER {
                    off(1),
                    on(2)
                }
            ACCESS  read-only
            STATUS  mandatory
            DESCRIPTION
                "Near-End FOM LOF"
            ::= { fom7FomStatusEty 4 }

        fom7FomNeFrameErr  OBJECT-TYPE
            SYNTAX  INTEGER
            ACCESS  read-only
            STATUS  mandatory
            DESCRIPTION
                "Near-End FOM Frame Error Counter"
            ::= { fom7FomStatusEty 5 }

        fom7FomNeChksumErr  OBJECT-TYPE
            SYNTAX  INTEGER
            ACCESS  read-only
            STATUS  mandatory
            DESCRIPTION
                "Near-End FOM Frame Checksum Error Counter"
            ::= { fom7FomStatusEty 6 }

        fom7FomFeType  OBJECT-TYPE
            SYNTAX  INTEGER {
                    unknown(1),
                    cpe-with-cpu(2),
                    mux-fom(3),
                    cpe-without-CPU(4),
                    fom7(11)
                }
            ACCESS  read-only
            STATUS  mandatory
            DESCRIPTION
                "Far-End FOM Type"
            ::= { fom7FomStatusEty 7 }

        fom7FomFeLof  OBJECT-TYPE
            SYNTAX  INTEGER {
                    off(1),
                    on(2),
                    not-available(100)
                }
            ACCESS  read-only
            STATUS  mandatory
            DESCRIPTION
                "Far-End FOM LOF"
            ::= { fom7FomStatusEty 8 }

        fom7FomFeFrameErr  OBJECT-TYPE
            SYNTAX  INTEGER
            ACCESS  read-only
            STATUS  mandatory
            DESCRIPTION
                "Far-End FOM Frame Error Counter"
            ::= { fom7FomStatusEty 9 }

        fom7FomFeChksumErr  OBJECT-TYPE
            SYNTAX  INTEGER
            ACCESS  read-only
            STATUS  mandatory
            DESCRIPTION
                "Far-End FOM Frame Checksum Error Counter"
            ::= { fom7FomStatusEty 10 }

        fom7FomFeE1T1Cnan1LosLof  OBJECT-TYPE
            SYNTAX  INTEGER {
                    off(1),
                    on(2),
                    not-available(100)
                }
            ACCESS  read-only
            STATUS  mandatory
            DESCRIPTION
                "FOM E1T1 Channel#1 LOS/LOF"
            ::= { fom7FomStatusEty 11 }

        fom7FomFeE1T1Cnan2LosLof  OBJECT-TYPE
            SYNTAX  INTEGER {
                    off(1),
                    on(2),
                    not-available(100)
                }
            ACCESS  read-only
            STATUS  mandatory
            DESCRIPTION
                "FOM E1T1 Channel#2 LOS/LOF"
            ::= { fom7FomStatusEty 12 }

        fom7FomFeE1T1Cnan3LosLof  OBJECT-TYPE
            SYNTAX  INTEGER {
                    off(1),
                    on(2),
                    not-available(100)
                }
            ACCESS  read-only
            STATUS  mandatory
            DESCRIPTION
                "FOM E1T1 Channel#3 LOS/LOF"
            ::= { fom7FomStatusEty 13 }

        fom7FomFeE1T1Cnan4LosLof  OBJECT-TYPE
            SYNTAX  INTEGER {
                    off(1),
                    on(2),
                    not-available(100)
                }
            ACCESS  read-only
            STATUS  mandatory
            DESCRIPTION
                "FOM E1T1 Channel#4 LOS/LOF"
            ::= { fom7FomStatusEty 14 }

        fom7FomFeE1T1Cnan1BpvCrc  OBJECT-TYPE
            SYNTAX  INTEGER
            ACCESS  read-only
            STATUS  mandatory
            DESCRIPTION
                "FOM E1T1 Channel#1 BPV/CRC Error Counter"
            ::= { fom7FomStatusEty 15 }

        fom7FomFeE1T1Cnan2BpvCrc  OBJECT-TYPE
            SYNTAX  INTEGER
            ACCESS  read-only
            STATUS  mandatory
            DESCRIPTION
                "FOM E1T1 Channel#2 BPV/CRC Error Counter"
            ::= { fom7FomStatusEty 16 }

        fom7FomFeE1T1Cnan3BpvCrc  OBJECT-TYPE
            SYNTAX  INTEGER
            ACCESS  read-only
            STATUS  mandatory
            DESCRIPTION
                "FOM E1T1 Channel#3 BPV/CRC Error Counter"
            ::= { fom7FomStatusEty 17 }

        fom7FomFeE1T1Cnan4BpvCrc  OBJECT-TYPE
            SYNTAX  INTEGER
            ACCESS  read-only
            STATUS  mandatory
            DESCRIPTION
                "FOM E1T1 Channel#4 BPV/CRC Error Counter"
            ::= { fom7FomStatusEty 18 }

--
--  7FOM Loopback & Diagnostics
--

    fom7Diagnostics           OBJECT IDENTIFIER ::= { fom7-card 3 }

--
--  7FOM Loopback Setup Table
--

        fom7NeFomLbTab  OBJECT-TYPE
            SYNTAX  SEQUENCE OF Fom7NeFomLbEty
            ACCESS  not-accessible
            STATUS  mandatory
            DESCRIPTION
                "FOM near-end(NE) loopback setup table"
            ::= { fom7Diagnostics 1 }

        fom7NeFomLbEty  OBJECT-TYPE
            SYNTAX  Fom7NeFomLbEty
            ACCESS  not-accessible
            STATUS  mandatory
            DESCRIPTION
                "An entry in the loopback setup table"
            INDEX { fom7NeFomLbUnit ,
                    fom7NeFomLbPort }
            ::= { fom7NeFomLbTab 1 }

        Fom7NeFomLbEty ::= SEQUENCE {
            fom7NeFomLbUnit             UnitID,
            fom7NeFomLbPort             PortID,
            fom7NeFomLbLoopbackType     INTEGER
        }

        fom7NeFomLbUnit  OBJECT-TYPE
            SYNTAX  UnitID
            ACCESS  read-only
            STATUS  mandatory
            DESCRIPTION
            "unit 1 to 4."
            ::= { fom7NeFomLbEty 1 }

        fom7NeFomLbPort  OBJECT-TYPE
            SYNTAX  PortID
            ACCESS  read-only
            STATUS  mandatory
            DESCRIPTION
                "FOM Port 1 to 7"
            ::= { fom7NeFomLbEty 2 }

        fom7NeFomLbLoopbackType  OBJECT-TYPE
            SYNTAX  INTEGER{
                    off(1),
                    local(2),
                    line(3)
                }
            ACCESS  read-write
            STATUS  mandatory
            DESCRIPTION
                "Loopback type"
            ::= { fom7NeFomLbEty 3 }

--
--  7FOM E1/T1 Loopback Setup Table
--

        fom7NeE1T1LbTab  OBJECT-TYPE
            SYNTAX  SEQUENCE OF Fom7NeE1T1LbEty
            ACCESS  not-accessible
            STATUS  mandatory
            DESCRIPTION
                "E1/T1 near-end(NE) Loopback setup table"
            ::= { fom7Diagnostics 2 }

        fom7NeE1T1LbEty  OBJECT-TYPE
            SYNTAX  Fom7NeE1T1LbEty
            ACCESS  not-accessible
            STATUS  mandatory
            DESCRIPTION
                "An entry in the E1/T1 loopback setup table"
            INDEX { fom7NeE1T1LbUnit ,
                    fom7NeE1T1LbPort ,
                    fom7NeE1T1LbChannel }
            ::= { fom7NeE1T1LbTab 1 }

        Fom7NeE1T1LbEty ::= SEQUENCE {
            fom7NeE1T1LbUnit            UnitID,
            fom7NeE1T1LbPort            PortID,
            fom7NeE1T1LbChannel         ChannelNum,
            fom7NeE1T1LbLoopbackType    INTEGER
        }

        fom7NeE1T1LbUnit  OBJECT-TYPE
            SYNTAX  UnitID
            ACCESS  read-only
            STATUS  mandatory
            DESCRIPTION
            "unit 1 to 4."
            ::= { fom7NeE1T1LbEty 1 }

        fom7NeE1T1LbPort  OBJECT-TYPE
            SYNTAX  PortID
            ACCESS  read-only
            STATUS  mandatory
            DESCRIPTION
                "FOM Port 1 to 7"
            ::= { fom7NeE1T1LbEty 2 }

        fom7NeE1T1LbChannel  OBJECT-TYPE
            SYNTAX  ChannelNum
            ACCESS  read-only
            STATUS  mandatory
            DESCRIPTION
                "E1/T1 Channel 1 to 4"
            ::= { fom7NeE1T1LbEty 3 }

        fom7NeE1T1LbLoopbackType  OBJECT-TYPE
            SYNTAX  INTEGER{
                    off(1),
                    to-backplane(2),
                    to-fom(3)
                }
            ACCESS  read-write
            STATUS  mandatory
            DESCRIPTION
                "Loopback type"
            ::= { fom7NeE1T1LbEty 4 }


--
--  7FOM E1/T1 BERT Setup Table
--

        fom7NeE1T1BERTTab  OBJECT-TYPE
            SYNTAX  SEQUENCE OF Fom7NeE1T1BERTEty
            ACCESS  not-accessible
            STATUS  mandatory
            DESCRIPTION
                "E1/T1 near-end(NE) BERT setup table"
            ::= { fom7Diagnostics 3 }

        fom7NeE1T1BERTEty  OBJECT-TYPE
            SYNTAX  Fom7NeE1T1BERTEty
            ACCESS  not-accessible
            STATUS  mandatory
            DESCRIPTION
                "An entry in the E1/T1 BERT setup table"
            INDEX { fom7NeE1T1Unit ,
                    fom7NeE1T1Port ,
                    fom7NeE1T1Channel }
            ::= { fom7NeE1T1BERTTab 1 }

        Fom7NeE1T1BERTEty ::= SEQUENCE {
            fom7NeE1T1Unit              UnitID,
            fom7NeE1T1Port              PortID,
            fom7NeE1T1Channel           ChannelNum,
            fom7NeE1T1Direction         INTEGER,
            fom7NeE1T1Pattern           INTEGER,
            fom7NeE1T1Action            INTEGER,
            fom7NeE1T1Status            INTEGER,
            fom7NeE1T1ElapseSecond      INTEGER,
            fom7NeE1T1ESCount           INTEGER,
            fom7NeE1T1ESRatio           DisplayString (SIZE (0..25) ),
            fom7NeE1T1UASCount          INTEGER,
            fom7NeE1T1UASRatio          DisplayString (SIZE (0..25) )
        }

        fom7NeE1T1Unit  OBJECT-TYPE
            SYNTAX  UnitID
            ACCESS  read-only
            STATUS  mandatory
            DESCRIPTION
                "Unit 1 to 8"
            ::= { fom7NeE1T1BERTEty 1 }

        fom7NeE1T1Port  OBJECT-TYPE
            SYNTAX  PortID
            ACCESS  read-only
            STATUS  mandatory
            DESCRIPTION
                "FOM Port 1 to 7"
            ::= { fom7NeE1T1BERTEty 2 }

        fom7NeE1T1Channel  OBJECT-TYPE
            SYNTAX  ChannelNum
            ACCESS  read-only
            STATUS  mandatory
            DESCRIPTION
                "E1/T1 Channel 1 to 4"
            ::= { fom7NeE1T1BERTEty 3 }

        fom7NeE1T1Direction  OBJECT-TYPE
            SYNTAX  INTEGER{
                    system-site(1),
                    fom-site(2)
                }
            ACCESS  read-write
            STATUS  mandatory
            DESCRIPTION
                "BERT test direction"
            ::= { fom7NeE1T1BERTEty 4 }

        fom7NeE1T1Pattern  OBJECT-TYPE
            SYNTAX  INTEGER{
                    off(1),
                    patt-2exp15-1(2),
                    patt-2exp20-1(3)
                }
            ACCESS  read-write
            STATUS  mandatory
            DESCRIPTION
                "BERT test pattern"
            ::= { fom7NeE1T1BERTEty 5 }

        fom7NeE1T1Action  OBJECT-TYPE
            SYNTAX  INTEGER{
                    none(0),
                    reset(1)
--                         insert-error(2)
                }
            ACCESS  read-write
            STATUS  mandatory
            DESCRIPTION
                "BERT test action"
            ::= { fom7NeE1T1BERTEty 6 }

        fom7NeE1T1Status  OBJECT-TYPE
            SYNTAX  INTEGER{
                    unsync(1),
                    sync(2)
                }
            ACCESS  read-only
            STATUS  mandatory
            DESCRIPTION
                "BERT status"
            ::= { fom7NeE1T1BERTEty 7 }

        fom7NeE1T1ElapseSecond  OBJECT-TYPE
            SYNTAX  INTEGER
            ACCESS  read-only
            STATUS  mandatory
            DESCRIPTION
                "BERT elapsed time(s)"
            ::= { fom7NeE1T1BERTEty 8 }

        fom7NeE1T1ESCount  OBJECT-TYPE
            SYNTAX  INTEGER
            ACCESS  read-only
            STATUS  mandatory
            DESCRIPTION
                "BERT ES Count"
            ::= { fom7NeE1T1BERTEty 9 }

        fom7NeE1T1ESRatio  OBJECT-TYPE
            SYNTAX  DisplayString (SIZE (0..25) )
            ACCESS  read-only
            STATUS  mandatory
            DESCRIPTION
                "BERT ES Ratio"
            ::= { fom7NeE1T1BERTEty 10 }

        fom7NeE1T1UASCount  OBJECT-TYPE
            SYNTAX  INTEGER
            ACCESS  read-only
            STATUS  mandatory
            DESCRIPTION
                "BERT UAS Count"
            ::= { fom7NeE1T1BERTEty 11 }

        fom7NeE1T1UASRatio  OBJECT-TYPE
            SYNTAX  DisplayString (SIZE (0..25) )
            ACCESS  read-only
            STATUS  mandatory
            DESCRIPTION
                "BERT UAS Ratio"
            ::= { fom7NeE1T1BERTEty 12 }

--
--  7FOM Remote Loopback Setup Table
--

        fom7FeFomLbTab  OBJECT-TYPE
            SYNTAX  SEQUENCE OF Fom7FeFomLbEty
            ACCESS  not-accessible
            STATUS  mandatory
            DESCRIPTION
                "FOM far-end(FE) loopback setup table"
            ::= { fom7Diagnostics 4 }

        fom7FeFomLbEty  OBJECT-TYPE
            SYNTAX  Fom7FeFomLbEty
            ACCESS  not-accessible
            STATUS  mandatory
            DESCRIPTION
                "An entry in the remote loopback setup table"
            INDEX { fom7FeFomLbUnit ,
                    fom7FeFomLbPort }
            ::= { fom7FeFomLbTab 1 }

        Fom7FeFomLbEty ::= SEQUENCE {
            fom7FeFomLbUnit             UnitID,
            fom7FeFomLbPort             PortID,
            fom7FeFomLbLoopbackType     INTEGER
        }

        fom7FeFomLbUnit  OBJECT-TYPE
            SYNTAX  UnitID
            ACCESS  read-only
            STATUS  mandatory
            DESCRIPTION
            "unit 1 to 4."
            ::= { fom7FeFomLbEty 1 }

        fom7FeFomLbPort  OBJECT-TYPE
            SYNTAX  PortID
            ACCESS  read-only
            STATUS  mandatory
            DESCRIPTION
                "FOM Port 1 to 7"
            ::= { fom7FeFomLbEty 2 }

        fom7FeFomLbLoopbackType  OBJECT-TYPE
            SYNTAX  INTEGER{
                    off(1),
--                         local(2),
                    line(3)
                }
            ACCESS  read-write
            STATUS  mandatory
            DESCRIPTION
                "Loopback type"
            ::= { fom7FeFomLbEty 3 }

--
--  7FOM E1/T1 Remote Loopback Setup Table
--

        fom7FeE1T1LbTab  OBJECT-TYPE
            SYNTAX  SEQUENCE OF Fom7FeE1T1LbEty
            ACCESS  not-accessible
            STATUS  mandatory
            DESCRIPTION
                "E1/T1 far-end(FE) Loopback setup table"
            ::= { fom7Diagnostics 5 }

        fom7FeE1T1LbEty  OBJECT-TYPE
            SYNTAX  Fom7FeE1T1LbEty
            ACCESS  not-accessible
            STATUS  mandatory
            DESCRIPTION
                "An entry in the E1/T1 far-end(FE) loopback setup table"
            INDEX { fom7FeE1T1LbUnit ,
                    fom7FeE1T1LbPort ,
                    fom7FeE1T1LbChannel }
            ::= { fom7FeE1T1LbTab 1 }

        Fom7FeE1T1LbEty ::= SEQUENCE {
            fom7FeE1T1LbUnit            UnitID,
            fom7FeE1T1LbPort            PortID,
            fom7FeE1T1LbChannel         ChannelNum,
            fom7FeE1T1LbLoopbackType    INTEGER
        }

        fom7FeE1T1LbUnit  OBJECT-TYPE
            SYNTAX  UnitID
            ACCESS  read-only
            STATUS  mandatory
            DESCRIPTION
            "unit 1 to 4."
            ::= { fom7FeE1T1LbEty 1 }

        fom7FeE1T1LbPort  OBJECT-TYPE
            SYNTAX  PortID
            ACCESS  read-only
            STATUS  mandatory
            DESCRIPTION
                "FOM Port 1 to 7"
            ::= { fom7FeE1T1LbEty 2 }

        fom7FeE1T1LbChannel  OBJECT-TYPE
            SYNTAX  ChannelNum
            ACCESS  read-only
            STATUS  mandatory
            DESCRIPTION
                "E1/T1 Channel 1 to 4"
            ::= { fom7FeE1T1LbEty 3 }

        fom7FeE1T1LbLoopbackType  OBJECT-TYPE
            SYNTAX  INTEGER{
                    off(1),
                    to-backplane(2),
                    to-fom(3)
                }
            ACCESS  read-write
            STATUS  mandatory
            DESCRIPTION
                "Loopback type"
            ::= { fom7FeE1T1LbEty 4 }

--
--  7FOM Performance
--

    fom7Performance           OBJECT IDENTIFIER ::= { fom7-card 4 }

--
--  7FOM Performance Report
--

    fom7PerformanceReport           OBJECT IDENTIFIER ::= { fom7Performance 1 }

--
--  7FOM Performance Report LoPath/VTPath Current Table
--

        fom7LoVTPathCurrIntvTab  OBJECT-TYPE
            SYNTAX  SEQUENCE OF Fom7LoVTPathCurrIntvEty
            ACCESS  not-accessible
            STATUS  mandatory
            DESCRIPTION
                "Performance report current"
            ::= { fom7PerformanceReport 1 }

        fom7LoVTPathCurrIntvEty  OBJECT-TYPE
            SYNTAX  Fom7LoVTPathCurrIntvEty
            ACCESS  not-accessible
            STATUS  mandatory
            DESCRIPTION
                "An entry in the performance report current table"
            INDEX { fom7LoVTCurrUnit ,
                    fom7LoVTCurrPort ,
                    fom7LoVTCurrChannel ,
                    fom7LoVTCurrAnomalyType }
            ::= { fom7LoVTPathCurrIntvTab 1 }

        Fom7LoVTPathCurrIntvEty ::= SEQUENCE {
            fom7LoVTCurrUnit            UnitID,
            fom7LoVTCurrPort            PortID,
            fom7LoVTCurrChannel         ChannelNum,
            fom7LoVTCurrAnomalyType     LoPathPerfAnomalyType,
            fom7LoVTCurrEB-Count        INTEGER,
            fom7LoVTCurrBBE-Count       INTEGER,
            fom7LoVTCurrES-Count        INTEGER,
            fom7LoVTCurrUAS-Count       INTEGER,
            fom7LoVTCurrBES-Count       INTEGER,
            fom7LoVTCurrSES-Count       INTEGER,
            fom7LoVT15MinTimeElaps      INTEGER,
            fom7LoVT24hrValid15Min      INTEGER,
            fom7LoVTDayValid15Min       INTEGER,
            fom7LoVT7DayValidDays       INTEGER
        }

        fom7LoVTCurrUnit  OBJECT-TYPE
            SYNTAX  UnitID
            ACCESS  read-only
            STATUS  mandatory
            DESCRIPTION
            "unit 1 to 4."
            ::= { fom7LoVTPathCurrIntvEty 1 }

        fom7LoVTCurrPort  OBJECT-TYPE
            SYNTAX  PortID
            ACCESS  read-only
            STATUS  mandatory
            DESCRIPTION
                "FOM Port 1 to 7"
            ::= { fom7LoVTPathCurrIntvEty 2 }

        fom7LoVTCurrChannel  OBJECT-TYPE
            SYNTAX  ChannelNum
            ACCESS  read-only
            STATUS  mandatory
            DESCRIPTION
                "E1/T1 Channel 1 to 4"
            ::= { fom7LoVTPathCurrIntvEty 3 }

        fom7LoVTCurrAnomalyType  OBJECT-TYPE
            SYNTAX  LoPathPerfAnomalyType
            ACCESS  read-only
            STATUS  mandatory
            DESCRIPTION
                "Performance report LoPath/VTPath Anomaly Type"
            ::= { fom7LoVTPathCurrIntvEty 4 }

        fom7LoVTCurrEB-Count  OBJECT-TYPE
            SYNTAX  INTEGER
            ACCESS  read-only
            STATUS  mandatory
            DESCRIPTION
                "Current Error Block"
            ::= { fom7LoVTPathCurrIntvEty 5 }

        fom7LoVTCurrBBE-Count  OBJECT-TYPE
            SYNTAX  INTEGER
            ACCESS  read-only
            STATUS  mandatory
            DESCRIPTION
                "Current Background Block Error"
            ::= { fom7LoVTPathCurrIntvEty 6 }

        fom7LoVTCurrES-Count  OBJECT-TYPE
            SYNTAX  INTEGER
            ACCESS  read-only
            STATUS  mandatory
            DESCRIPTION
                "Error Second"
            ::= { fom7LoVTPathCurrIntvEty 7 }

        fom7LoVTCurrUAS-Count  OBJECT-TYPE
            SYNTAX  INTEGER
            ACCESS  read-only
            STATUS  mandatory
            DESCRIPTION
                "Unavailable Second"
            ::= { fom7LoVTPathCurrIntvEty 8 }

        fom7LoVTCurrBES-Count  OBJECT-TYPE
            SYNTAX  INTEGER
            ACCESS  read-only
            STATUS  mandatory
            DESCRIPTION
                "Background Error Second"
            ::= { fom7LoVTPathCurrIntvEty 9 }

        fom7LoVTCurrSES-Count  OBJECT-TYPE
            SYNTAX  INTEGER
            ACCESS  read-only
            STATUS  mandatory
            DESCRIPTION
                "Severly Error Second"
            ::= { fom7LoVTPathCurrIntvEty 10 }

        fom7LoVT15MinTimeElaps  OBJECT-TYPE
            SYNTAX  INTEGER
            ACCESS  read-only
            STATUS  mandatory
            DESCRIPTION
                "Valid Seconds in Current 15-Min Interval"
            ::= { fom7LoVTPathCurrIntvEty 11 }

        fom7LoVT24hrValid15Min  OBJECT-TYPE
            SYNTAX  INTEGER
            ACCESS  read-only
            STATUS  mandatory
            DESCRIPTION
                "Valid 15-Min Intervals in Current 24-Hour Interval"
            ::= { fom7LoVTPathCurrIntvEty 12 }

        fom7LoVTDayValid15Min  OBJECT-TYPE
            SYNTAX  INTEGER
            ACCESS  read-only
            STATUS  mandatory
            DESCRIPTION
                "Valid 15-Min Intervals in Current Day"
            ::= { fom7LoVTPathCurrIntvEty 13 }

        fom7LoVT7DayValidDays  OBJECT-TYPE
            SYNTAX  INTEGER
            ACCESS  read-only
            STATUS  mandatory
            DESCRIPTION
                "Valid Days in Current Seven Day"
            ::= { fom7LoVTPathCurrIntvEty 14 }


--
--  7FOM Performance Report LoPath/VTPath Interval Table
--

        fom7LoVTPath96IntvTab  OBJECT-TYPE
            SYNTAX  SEQUENCE OF Fom7LoVTPath96IntvEty
            ACCESS  not-accessible
            STATUS  mandatory
            DESCRIPTION
                "Performance report Inteval"
            ::= { fom7PerformanceReport 2 }

        fom7LoVTPath96IntvEty  OBJECT-TYPE
            SYNTAX  Fom7LoVTPath96IntvEty
            ACCESS  not-accessible
            STATUS  mandatory
            DESCRIPTION
                "An entry in the performance report interval table"
            INDEX { fom7LoVTIntvUnit ,
                    fom7LoVTIntvPort ,
                    fom7LoVTIntvChannel ,
                    fom7LoVTIntvAnomalyType ,
                    fom7LoVTIntvPeriod }
            ::= { fom7LoVTPath96IntvTab 1 }

        Fom7LoVTPath96IntvEty ::= SEQUENCE {
            fom7LoVTIntvUnit            UnitID,
            fom7LoVTIntvPort            PortID,
            fom7LoVTIntvChannel         ChannelNum,
            fom7LoVTIntvAnomalyType     LoPathPerfAnomalyType,
            fom7LoVTIntvPeriod          INTEGER (1..96),
            fom7LoVTIntvEB-Count        INTEGER,
            fom7LoVTIntvBBE-Count       INTEGER,
            fom7LoVTIntvES-Count        INTEGER,
            fom7LoVTIntvUAS-Count       INTEGER,
            fom7LoVTIntvBES-Count       INTEGER,
            fom7LoVTIntvSES-Count       INTEGER
        }

        fom7LoVTIntvUnit  OBJECT-TYPE
            SYNTAX  UnitID
            ACCESS  read-only
            STATUS  mandatory
            DESCRIPTION
            "unit 1 to 4."
            ::= { fom7LoVTPath96IntvEty 1 }

        fom7LoVTIntvPort  OBJECT-TYPE
            SYNTAX  PortID
            ACCESS  read-only
            STATUS  mandatory
            DESCRIPTION
                "FOM Port 1 to 7"
            ::= { fom7LoVTPath96IntvEty 2 }

        fom7LoVTIntvChannel  OBJECT-TYPE
            SYNTAX  ChannelNum
            ACCESS  read-only
            STATUS  mandatory
            DESCRIPTION
                "E1/T1 Channel 1 to 4"
            ::= { fom7LoVTPath96IntvEty 3 }

        fom7LoVTIntvAnomalyType  OBJECT-TYPE
            SYNTAX  LoPathPerfAnomalyType
            ACCESS  read-only
            STATUS  mandatory
            DESCRIPTION
                "Performance report LoPath/VTPath Anomaly Type"
            ::= { fom7LoVTPath96IntvEty 4 }

        fom7LoVTIntvPeriod  OBJECT-TYPE
            SYNTAX  INTEGER (1..96)
            ACCESS  read-only
            STATUS  mandatory
            DESCRIPTION
                "LoPath Interval Period"
            ::= { fom7LoVTPath96IntvEty 5 }

        fom7LoVTIntvEB-Count  OBJECT-TYPE
            SYNTAX  INTEGER
            ACCESS  read-only
            STATUS  mandatory
            DESCRIPTION
                "Current Error Block"
            ::= { fom7LoVTPath96IntvEty 6 }

        fom7LoVTIntvBBE-Count  OBJECT-TYPE
            SYNTAX  INTEGER
            ACCESS  read-only
            STATUS  mandatory
            DESCRIPTION
                "Current Background Block Error"
            ::= { fom7LoVTPath96IntvEty 7 }

        fom7LoVTIntvES-Count  OBJECT-TYPE
            SYNTAX  INTEGER
            ACCESS  read-only
            STATUS  mandatory
            DESCRIPTION
                "Error Second"
            ::= { fom7LoVTPath96IntvEty 8 }

        fom7LoVTIntvUAS-Count  OBJECT-TYPE
            SYNTAX  INTEGER
            ACCESS  read-only
            STATUS  mandatory
            DESCRIPTION
                "Unavailable Second"
            ::= { fom7LoVTPath96IntvEty 9 }

        fom7LoVTIntvBES-Count  OBJECT-TYPE
            SYNTAX  INTEGER
            ACCESS  read-only
            STATUS  mandatory
            DESCRIPTION
                "Background Error Second"
            ::= { fom7LoVTPath96IntvEty 10 }

        fom7LoVTIntvSES-Count  OBJECT-TYPE
            SYNTAX  INTEGER
            ACCESS  read-only
            STATUS  mandatory
            DESCRIPTION
                "Severly Error Second"
            ::= { fom7LoVTPath96IntvEty 11 }

--
--  7FOM Performance Report LoPath/VTPath Total Table
--

        fom7LoVTPathTotalTab  OBJECT-TYPE
            SYNTAX  SEQUENCE OF Fom7LoVTPathTotalEty
            ACCESS  not-accessible
            STATUS  mandatory
            DESCRIPTION
                "Performance report Total"
            ::= { fom7PerformanceReport 3 }

        fom7LoVTPathTotalEty  OBJECT-TYPE
            SYNTAX  Fom7LoVTPathTotalEty
            ACCESS  not-accessible
            STATUS  mandatory
            DESCRIPTION
                "An entry in the performance report total table"
            INDEX { fom7LoVTTotalUnit ,
                    fom7LoVTTotalPort ,
                    fom7LoVTTotalChannel ,
                    fom7LoVTTotalAnomalyType }
            ::= { fom7LoVTPathTotalTab 1 }

        Fom7LoVTPathTotalEty ::= SEQUENCE {
            fom7LoVTTotalUnit           UnitID,
            fom7LoVTTotalPort           PortID,
            fom7LoVTTotalChannel        ChannelNum,
            fom7LoVTTotalAnomalyType    LoPathPerfAnomalyType,
            fom7LoVTTotalEB-Count       INTEGER,
            fom7LoVTTotalBBE-Count      INTEGER,
            fom7LoVTTotalES-Count       INTEGER,
            fom7LoVTTotalUAS-Count      INTEGER,
            fom7LoVTTotalBES-Count      INTEGER,
            fom7LoVTTotalSES-Count      INTEGER
        }

        fom7LoVTTotalUnit  OBJECT-TYPE
            SYNTAX  UnitID
            ACCESS  read-only
            STATUS  mandatory
            DESCRIPTION
            "unit 1 to 4."
            ::= { fom7LoVTPathTotalEty 1 }

        fom7LoVTTotalPort  OBJECT-TYPE
            SYNTAX  PortID
            ACCESS  read-only
            STATUS  mandatory
            DESCRIPTION
                "FOM Port 1 to 7"
            ::= { fom7LoVTPathTotalEty 2 }

        fom7LoVTTotalChannel  OBJECT-TYPE
            SYNTAX  ChannelNum
            ACCESS  read-only
            STATUS  mandatory
            DESCRIPTION
                "E3 Channel 1 to 28"
            ::= { fom7LoVTPathTotalEty 3 }

        fom7LoVTTotalAnomalyType  OBJECT-TYPE
            SYNTAX  LoPathPerfAnomalyType
            ACCESS  read-only
            STATUS  mandatory
            DESCRIPTION
                "Performance report LoPath/VTPath Anomaly Type"
            ::= { fom7LoVTPathTotalEty 4 }

        fom7LoVTTotalEB-Count  OBJECT-TYPE
            SYNTAX  INTEGER
            ACCESS  read-only
            STATUS  mandatory
            DESCRIPTION
                "Current Error Block"
            ::= { fom7LoVTPathTotalEty 5 }

        fom7LoVTTotalBBE-Count  OBJECT-TYPE
            SYNTAX  INTEGER
            ACCESS  read-only
            STATUS  mandatory
            DESCRIPTION
                "Current Background Block Error"
            ::= { fom7LoVTPathTotalEty 6 }

        fom7LoVTTotalES-Count  OBJECT-TYPE
            SYNTAX  INTEGER
            ACCESS  read-only
            STATUS  mandatory
            DESCRIPTION
                "Error Second"
            ::= { fom7LoVTPathTotalEty 7 }

        fom7LoVTTotalUAS-Count  OBJECT-TYPE
            SYNTAX  INTEGER
            ACCESS  read-only
            STATUS  mandatory
            DESCRIPTION
                "Unavailable Second"
            ::= { fom7LoVTPathTotalEty 8 }

        fom7LoVTTotalBES-Count  OBJECT-TYPE
            SYNTAX  INTEGER
            ACCESS  read-only
            STATUS  mandatory
            DESCRIPTION
                "Background Error Second"
            ::= { fom7LoVTPathTotalEty 9 }

        fom7LoVTTotalSES-Count  OBJECT-TYPE
            SYNTAX  INTEGER
            ACCESS  read-only
            STATUS  mandatory
            DESCRIPTION
                "Severly Error Second"
            ::= { fom7LoVTPathTotalEty 10 }

--
--  7FOM Performance Report LoPath/VT-Path Seven Days Table
--

        fom7LoVTPath7DaysTab  OBJECT-TYPE
            SYNTAX  SEQUENCE OF Fom7LoVTPath7DaysEty
            ACCESS  not-accessible
            STATUS  mandatory
            DESCRIPTION
                "Performance report Seven Days"
            ::= { fom7PerformanceReport 4 }

        fom7LoVTPath7DaysEty  OBJECT-TYPE
            SYNTAX  Fom7LoVTPath7DaysEty
            ACCESS  not-accessible
            STATUS  mandatory
            DESCRIPTION
                "An entry in the performance report seven days table"
            INDEX { fom7LoVT7DaysUnit ,
                    fom7LoVT7DaysPort ,
                    fom7LoVT7DaysChannel ,
                    fom7LoVT7DaysAnomalyType ,
                    fom7LoVT7DaysDayIndex }
            ::= { fom7LoVTPath7DaysTab 1 }

        Fom7LoVTPath7DaysEty ::= SEQUENCE {
            fom7LoVT7DaysUnit           UnitID,
            fom7LoVT7DaysPort           PortID,
            fom7LoVT7DaysChannel        ChannelNum,
            fom7LoVT7DaysAnomalyType    LoPathPerfAnomalyType,
            fom7LoVT7DaysDayIndex       INTEGER (1..7),
            fom7LoVT7DaysDate           DisplayString (SIZE (0..255) ),
            fom7LoVT7DaysEB-Count       INTEGER,
            fom7LoVT7DaysBBE-Count      INTEGER,
            fom7LoVT7DaysES-Count       INTEGER,
            fom7LoVT7DaysUAS-Count      INTEGER,
            fom7LoVT7DaysBES-Count      INTEGER,
            fom7LoVT7DaysSES-Count      INTEGER
        }

        fom7LoVT7DaysUnit  OBJECT-TYPE
            SYNTAX  UnitID
            ACCESS  read-only
            STATUS  mandatory
            DESCRIPTION
            "unit 1 to 4."
            ::= { fom7LoVTPath7DaysEty 1 }

        fom7LoVT7DaysPort  OBJECT-TYPE
            SYNTAX  PortID
            ACCESS  read-only
            STATUS  mandatory
            DESCRIPTION
                "FOM Port 1 to 7"
            ::= { fom7LoVTPath7DaysEty 2 }

        fom7LoVT7DaysChannel  OBJECT-TYPE
            SYNTAX  ChannelNum
            ACCESS  read-only
            STATUS  mandatory
            DESCRIPTION
                "E1/T1 Channel 1 to 4"
            ::= { fom7LoVTPath7DaysEty 3 }

        fom7LoVT7DaysAnomalyType  OBJECT-TYPE
            SYNTAX  LoPathPerfAnomalyType
            ACCESS  read-only
            STATUS  mandatory
            DESCRIPTION
                "Performance report LoPath/VTPath Anomaly Type"
            ::= { fom7LoVTPath7DaysEty 4 }

        fom7LoVT7DaysDayIndex  OBJECT-TYPE
            SYNTAX  INTEGER (1..7)
            ACCESS  read-only
            STATUS  mandatory
            DESCRIPTION
                "LoPath Seven Days day index"
            ::= { fom7LoVTPath7DaysEty 5 }

        fom7LoVT7DaysDate  OBJECT-TYPE
            SYNTAX  DisplayString (SIZE (0..255) )
            ACCESS  read-only
            STATUS  mandatory
            DESCRIPTION
                "Seven Days Date"
            ::= { fom7LoVTPath7DaysEty 6 }

        fom7LoVT7DaysEB-Count  OBJECT-TYPE
            SYNTAX  INTEGER
            ACCESS  read-only
            STATUS  mandatory
            DESCRIPTION
                "Current Error Block"
            ::= { fom7LoVTPath7DaysEty 7 }

        fom7LoVT7DaysBBE-Count  OBJECT-TYPE
            SYNTAX  INTEGER
            ACCESS  read-only
            STATUS  mandatory
            DESCRIPTION
                "Current Background Block Error"
            ::= { fom7LoVTPath7DaysEty 8 }

        fom7LoVT7DaysES-Count  OBJECT-TYPE
            SYNTAX  INTEGER
            ACCESS  read-only
            STATUS  mandatory
            DESCRIPTION
                "Error Second"
            ::= { fom7LoVTPath7DaysEty 9 }

        fom7LoVT7DaysUAS-Count  OBJECT-TYPE
            SYNTAX  INTEGER
            ACCESS  read-only
            STATUS  mandatory
            DESCRIPTION
                "Unavailable Second"
            ::= { fom7LoVTPath7DaysEty 10 }

        fom7LoVT7DaysBES-Count  OBJECT-TYPE
            SYNTAX  INTEGER
            ACCESS  read-only
            STATUS  mandatory
            DESCRIPTION
                "Background Error Second"
            ::= { fom7LoVTPath7DaysEty 11 }

        fom7LoVT7DaysSES-Count  OBJECT-TYPE
            SYNTAX  INTEGER
            ACCESS  read-only
            STATUS  mandatory
            DESCRIPTION
                "Severly Error Second"
            ::= { fom7LoVTPath7DaysEty 12 }

--
--  7FOM Performance Report Line Current Table
--

        fom7FOMLineCurrIntvTab  OBJECT-TYPE
            SYNTAX  SEQUENCE OF Fom7FOMLineCurrIntvEty
            ACCESS  not-accessible
            STATUS  mandatory
            DESCRIPTION
                "Performance report current"
            ::= { fom7PerformanceReport 5 }

        fom7FOMLineCurrIntvEty  OBJECT-TYPE
            SYNTAX  Fom7FOMLineCurrIntvEty
            ACCESS  not-accessible
            STATUS  mandatory
            DESCRIPTION
                "An entry in the performance report current table"
            INDEX { fom7LineCurrUnit ,
                    fom7LineCurrPort }
            ::= { fom7FOMLineCurrIntvTab 1 }

        Fom7FOMLineCurrIntvEty ::= SEQUENCE {
            fom7LineCurrUnit            UnitID,
            fom7LineCurrPort            PortID,
            fom7LineCurrES-Count        INTEGER,
            fom7LineCurrUAS-Count       INTEGER,
            fom7LineCurrBES-Count       INTEGER,
            fom7LineCurrSES-Count       INTEGER,
            fom7LineCurrBPV-Count       INTEGER,
            fom7Line15MinTimeElaps      INTEGER,
            fom7Line24hrValid15Min      INTEGER,
            fom7LineDayValid15Min       INTEGER,
            fom7Line7DayValidDays       INTEGER
        }

        fom7LineCurrUnit  OBJECT-TYPE
            SYNTAX  UnitID
            ACCESS  read-only
            STATUS  mandatory
            DESCRIPTION
            "unit 1 to 4."
            ::= { fom7FOMLineCurrIntvEty 1 }

        fom7LineCurrPort  OBJECT-TYPE
            SYNTAX  PortID
            ACCESS  read-only
            STATUS  mandatory
            DESCRIPTION
                "FOM Port 1 to 7"
            ::= { fom7FOMLineCurrIntvEty 2 }


        fom7LineCurrES-Count  OBJECT-TYPE
            SYNTAX  INTEGER
            ACCESS  read-only
            STATUS  mandatory
            DESCRIPTION
                "Error Second"
            ::= { fom7FOMLineCurrIntvEty 3 }

        fom7LineCurrUAS-Count  OBJECT-TYPE
            SYNTAX  INTEGER
            ACCESS  read-only
            STATUS  mandatory
            DESCRIPTION
                "Unavailable Second"
            ::= { fom7FOMLineCurrIntvEty 4 }

        fom7LineCurrBES-Count  OBJECT-TYPE
            SYNTAX  INTEGER
            ACCESS  read-only
            STATUS  mandatory
            DESCRIPTION
                "Background Error Second"
            ::= { fom7FOMLineCurrIntvEty 5 }

        fom7LineCurrSES-Count  OBJECT-TYPE
            SYNTAX  INTEGER
            ACCESS  read-only
            STATUS  mandatory
            DESCRIPTION
                "Severly Error Second"
            ::= { fom7FOMLineCurrIntvEty 6 }

        fom7LineCurrBPV-Count  OBJECT-TYPE
            SYNTAX  INTEGER
            ACCESS  read-only
            STATUS  mandatory
            DESCRIPTION
                "Bipolar Violation"
            ::= { fom7FOMLineCurrIntvEty 7 }

        fom7Line15MinTimeElaps  OBJECT-TYPE
            SYNTAX  INTEGER
            ACCESS  read-only
            STATUS  mandatory
            DESCRIPTION
                "Valid Seconds in Current 15-Min Interval"
            ::= { fom7FOMLineCurrIntvEty 8 }

        fom7Line24hrValid15Min  OBJECT-TYPE
            SYNTAX  INTEGER
            ACCESS  read-only
            STATUS  mandatory
            DESCRIPTION
                "Valid 15-Min Intervals in Current 24-Hour Interval"
            ::= { fom7FOMLineCurrIntvEty 9 }

        fom7LineDayValid15Min  OBJECT-TYPE
            SYNTAX  INTEGER
            ACCESS  read-only
            STATUS  mandatory
            DESCRIPTION
                "Valid 15-Min Intervals in Current Day"
            ::= { fom7FOMLineCurrIntvEty 10 }

        fom7Line7DayValidDays  OBJECT-TYPE
            SYNTAX  INTEGER
            ACCESS  read-only
            STATUS  mandatory
            DESCRIPTION
                "Valid Days in Current Seven Day"
            ::= { fom7FOMLineCurrIntvEty 11 }


--
--  7FOM Performance Report Line Interval Table
--

        fom7FOMLine96IntvTab  OBJECT-TYPE
            SYNTAX  SEQUENCE OF Fom7FOMLine96IntvEty
            ACCESS  not-accessible
            STATUS  mandatory
            DESCRIPTION
                "Performance report Inteval"
            ::= { fom7PerformanceReport 6 }

        fom7FOMLine96IntvEty  OBJECT-TYPE
            SYNTAX  Fom7FOMLine96IntvEty
            ACCESS  not-accessible
            STATUS  mandatory
            DESCRIPTION
                "An entry in the performance report interval table"
            INDEX { fom7LineIntvUnit ,
                    fom7LineIntvPort ,
                    fom7LineIntvPeriod }
            ::= { fom7FOMLine96IntvTab 1 }

        Fom7FOMLine96IntvEty ::= SEQUENCE {
            fom7LineIntvUnit            UnitID,
            fom7LineIntvPort            PortID,
            fom7LineIntvPeriod          INTEGER (1..96),
            fom7LineIntvES-Count        INTEGER,
            fom7LineIntvUAS-Count       INTEGER,
            fom7LineIntvBES-Count       INTEGER,
            fom7LineIntvSES-Count       INTEGER,
            fom7LineIntvBPV-Count       INTEGER
        }

        fom7LineIntvUnit  OBJECT-TYPE
            SYNTAX  UnitID
            ACCESS  read-only
            STATUS  mandatory
            DESCRIPTION
            "unit 1 to 4."
            ::= { fom7FOMLine96IntvEty 1 }

        fom7LineIntvPort  OBJECT-TYPE
            SYNTAX  PortID
            ACCESS  read-only
            STATUS  mandatory
            DESCRIPTION
                "FOM Port 1 to 7"
            ::= { fom7FOMLine96IntvEty 2 }

        fom7LineIntvPeriod  OBJECT-TYPE
            SYNTAX  INTEGER (1..96)
            ACCESS  read-only
            STATUS  mandatory
            DESCRIPTION
                "Line Interval Period"
            ::= { fom7FOMLine96IntvEty 3 }

        fom7LineIntvES-Count  OBJECT-TYPE
            SYNTAX  INTEGER
            ACCESS  read-only
            STATUS  mandatory
            DESCRIPTION
                "Error Second"
            ::= { fom7FOMLine96IntvEty 4 }

        fom7LineIntvUAS-Count  OBJECT-TYPE
            SYNTAX  INTEGER
            ACCESS  read-only
            STATUS  mandatory
            DESCRIPTION
                "Unavailable Second"
            ::= { fom7FOMLine96IntvEty 5 }

        fom7LineIntvBES-Count  OBJECT-TYPE
            SYNTAX  INTEGER
            ACCESS  read-only
            STATUS  mandatory
            DESCRIPTION
                "Background Error Second"
            ::= { fom7FOMLine96IntvEty 6 }

        fom7LineIntvSES-Count  OBJECT-TYPE
            SYNTAX  INTEGER
            ACCESS  read-only
            STATUS  mandatory
            DESCRIPTION
                "Severly Error Second"
            ::= { fom7FOMLine96IntvEty 7 }

        fom7LineIntvBPV-Count  OBJECT-TYPE
            SYNTAX  INTEGER
            ACCESS  read-only
            STATUS  mandatory
            DESCRIPTION
                "Bipolar Violation"
            ::= { fom7FOMLine96IntvEty 8 }

--
--  7FOM Performance Report Line Total Table
--

        fom7FOMLineTotalTab  OBJECT-TYPE
            SYNTAX  SEQUENCE OF Fom7FOMLineTotalEty
            ACCESS  not-accessible
            STATUS  mandatory
            DESCRIPTION
                "Performance report Total"
            ::= { fom7PerformanceReport 7 }

        fom7FOMLineTotalEty  OBJECT-TYPE
            SYNTAX  Fom7FOMLineTotalEty
            ACCESS  not-accessible
            STATUS  mandatory
            DESCRIPTION
                "An entry in the performance report total table"
            INDEX { fom7LineTotalUnit ,
                    fom7LineTotalPort }
            ::= { fom7FOMLineTotalTab 1 }

        Fom7FOMLineTotalEty ::= SEQUENCE {
            fom7LineTotalUnit           UnitID,
            fom7LineTotalPort           PortID,
            fom7LineTotalES-Count       INTEGER,
            fom7LineTotalUAS-Count      INTEGER,
            fom7LineTotalBES-Count      INTEGER,
            fom7LineTotalSES-Count      INTEGER,
            fom7LineTotalBPV-Count      INTEGER
        }

        fom7LineTotalUnit  OBJECT-TYPE
            SYNTAX  UnitID
            ACCESS  read-only
            STATUS  mandatory
            DESCRIPTION
            "unit 1 to 4."
            ::= { fom7FOMLineTotalEty 1 }

        fom7LineTotalPort  OBJECT-TYPE
            SYNTAX  PortID
            ACCESS  read-only
            STATUS  mandatory
            DESCRIPTION
                "FOM Port 1 to 7"
            ::= { fom7FOMLineTotalEty 2 }

        fom7LineTotalES-Count  OBJECT-TYPE
            SYNTAX  INTEGER
            ACCESS  read-only
            STATUS  mandatory
            DESCRIPTION
                "Error Second"
            ::= { fom7FOMLineTotalEty 3 }

        fom7LineTotalUAS-Count  OBJECT-TYPE
            SYNTAX  INTEGER
            ACCESS  read-only
            STATUS  mandatory
            DESCRIPTION
                "Unavailable Second"
            ::= { fom7FOMLineTotalEty 4 }

        fom7LineTotalBES-Count  OBJECT-TYPE
            SYNTAX  INTEGER
            ACCESS  read-only
            STATUS  mandatory
            DESCRIPTION
                "Background Error Second"
            ::= { fom7FOMLineTotalEty 5 }

        fom7LineTotalSES-Count  OBJECT-TYPE
            SYNTAX  INTEGER
            ACCESS  read-only
            STATUS  mandatory
            DESCRIPTION
                "Severly Error Second"
            ::= { fom7FOMLineTotalEty 6 }

        fom7LineTotalBPV-Count  OBJECT-TYPE
            SYNTAX  INTEGER
            ACCESS  read-only
            STATUS  mandatory
            DESCRIPTION
                "Bipolar Violation"
            ::= { fom7FOMLineTotalEty 7 }

--
--  7FOM Performance Report Line Seven Days Table
--

        fom7FOMLine7DaysTab  OBJECT-TYPE
            SYNTAX  SEQUENCE OF Fom7FOMLine7DaysEty
            ACCESS  not-accessible
            STATUS  mandatory
            DESCRIPTION
                "Performance report seven days"
            ::= { fom7PerformanceReport 8 }

        fom7FOMLine7DaysEty  OBJECT-TYPE
            SYNTAX  Fom7FOMLine7DaysEty
            ACCESS  not-accessible
            STATUS  mandatory
            DESCRIPTION
                "An entry in the performance report seven days table"
            INDEX { fom7Line7DaysUnit ,
                    fom7Line7DaysPort ,
                    fom7Line7DaysDayIndex }
            ::= { fom7FOMLine7DaysTab 1 }

        Fom7FOMLine7DaysEty ::= SEQUENCE {
            fom7Line7DaysUnit           UnitID,
            fom7Line7DaysPort           PortID,
            fom7Line7DaysDayIndex       INTEGER (1..7),
            fom7Line7DaysDate           DisplayString (SIZE (0..255) ),
            fom7Line7DaysES-Count       INTEGER,
            fom7Line7DaysUAS-Count      INTEGER,
            fom7Line7DaysBES-Count      INTEGER,
            fom7Line7DaysSES-Count      INTEGER,
            fom7Line7DaysBPV-Count      INTEGER
        }

        fom7Line7DaysUnit  OBJECT-TYPE
            SYNTAX  UnitID
            ACCESS  read-only
            STATUS  mandatory
            DESCRIPTION
            "unit 1 to 4."
            ::= { fom7FOMLine7DaysEty 1 }

        fom7Line7DaysPort  OBJECT-TYPE
            SYNTAX  PortID
            ACCESS  read-only
            STATUS  mandatory
            DESCRIPTION
                "FOM Port 1 to 7"
            ::= { fom7FOMLine7DaysEty 2 }

        fom7Line7DaysDayIndex  OBJECT-TYPE
            SYNTAX  INTEGER (1..7)
            ACCESS  read-only
            STATUS  mandatory
            DESCRIPTION
                "Line Seven Days day index"
            ::= { fom7FOMLine7DaysEty 3 }

        fom7Line7DaysDate  OBJECT-TYPE
            SYNTAX  DisplayString (SIZE (0..255) )
            ACCESS  read-only
            STATUS  mandatory
            DESCRIPTION
                "Seven Days Date"
            ::= { fom7FOMLine7DaysEty 4 }

        fom7Line7DaysES-Count  OBJECT-TYPE
            SYNTAX  INTEGER
            ACCESS  read-only
            STATUS  mandatory
            DESCRIPTION
                "Error Second"
            ::= { fom7FOMLine7DaysEty 5 }

        fom7Line7DaysUAS-Count  OBJECT-TYPE
            SYNTAX  INTEGER
            ACCESS  read-only
            STATUS  mandatory
            DESCRIPTION
                "Unavailable Second"
            ::= { fom7FOMLine7DaysEty 6 }

        fom7Line7DaysBES-Count  OBJECT-TYPE
            SYNTAX  INTEGER
            ACCESS  read-only
            STATUS  mandatory
            DESCRIPTION
                "Background Error Second"
            ::= { fom7FOMLine7DaysEty 7 }

        fom7Line7DaysSES-Count  OBJECT-TYPE
            SYNTAX  INTEGER
            ACCESS  read-only
            STATUS  mandatory
            DESCRIPTION
                "Severly Error Second"
            ::= { fom7FOMLine7DaysEty 8 }

        fom7Line7DaysBPV-Count  OBJECT-TYPE
            SYNTAX  INTEGER
            ACCESS  read-only
            STATUS  mandatory
            DESCRIPTION
                "Bipolar Violation"
            ::= { fom7FOMLine7DaysEty 9 }

--
--  7FOM Performance Threshold Setup Table
--

        fom7PerfThreshSetupTab  OBJECT-TYPE
            SYNTAX  SEQUENCE OF Fom7PerfThreshSetupEty
            ACCESS  not-accessible
            STATUS  mandatory
            DESCRIPTION
                "Performance threshold setup"
            ::= { fom7Performance 2 }

        fom7PerfThreshSetupEty  OBJECT-TYPE
            SYNTAX  Fom7PerfThreshSetupEty
            ACCESS  not-accessible
            STATUS  mandatory
            DESCRIPTION
                "An entry in the performance threshold setup table"
            INDEX { fom7PerfTCAUnit ,
                    fom7PerfTCAMonitorPoint }
            ::= { fom7PerfThreshSetupTab 1 }

        Fom7PerfThreshSetupEty ::= SEQUENCE {
            fom7PerfTCAUnit             UnitID,
            fom7PerfTCAMonitorPoint     INTEGER,
            fom7PerfTCAEnable           INTEGER,
            fom7PerfTCASeverity         Severity,
            fom7PerfTCAThreshold        INTEGER
        }

        fom7PerfTCAUnit  OBJECT-TYPE
            SYNTAX  UnitID
            ACCESS  read-only
            STATUS  mandatory
            DESCRIPTION
            "unit 1 to 4."
            ::= { fom7PerfThreshSetupEty 1 }

        fom7PerfTCAMonitorPoint  OBJECT-TYPE
            SYNTAX  INTEGER {
                    lp-bip-v5(1),
                    lp-rei-v5(2),
                    line(3)
                }
            ACCESS  read-only
            STATUS  mandatory
            DESCRIPTION
                "TCA monitor point index"
            ::= { fom7PerfThreshSetupEty 2 }

        fom7PerfTCAEnable  OBJECT-TYPE
            SYNTAX  INTEGER {
                    disable(1),
                    enable(2)
                }
            ACCESS  read-write
            STATUS  mandatory
            DESCRIPTION
                "TCA disable/enable"
            ::= { fom7PerfThreshSetupEty 3 }

        fom7PerfTCASeverity  OBJECT-TYPE
            SYNTAX  Severity
            ACCESS  read-write
            STATUS  mandatory
            DESCRIPTION
                "TCA Severity"
            ::= { fom7PerfThreshSetupEty 4 }

        fom7PerfTCAThreshold  OBJECT-TYPE
            SYNTAX  INTEGER (1..99999)
            ACCESS  read-write
            STATUS  mandatory
            DESCRIPTION
                "TCA threshold"
            ::= { fom7PerfThreshSetupEty 5 }

--
--  7FOM Performance Control Setup Table
--

        fom7PerfControlTab  OBJECT-TYPE
            SYNTAX  SEQUENCE OF Fom7PerfControlEty
            ACCESS  not-accessible
            STATUS  mandatory
            DESCRIPTION
                "Performance control"
            ::= { fom7Performance 3 }

        fom7PerfControlEty  OBJECT-TYPE
            SYNTAX  Fom7PerfControlEty
            ACCESS  not-accessible
            STATUS  mandatory
            DESCRIPTION
                "An entry in the performance control table"
            INDEX { fom7PerfCtrlUnit }
            ::= { fom7PerfControlTab 1 }

        Fom7PerfControlEty ::= SEQUENCE {
            fom7PerfCtrlUnit            UnitID,
            fom7PerfCtrlClearPerf       INTEGER
        }

        fom7PerfCtrlUnit  OBJECT-TYPE
            SYNTAX  UnitID
            ACCESS  read-only
            STATUS  mandatory
            DESCRIPTION
            "unit 1 to 4."
            ::= { fom7PerfControlEty 1 }

        fom7PerfCtrlClearPerf  OBJECT-TYPE
            SYNTAX  INTEGER {
                    none(0),
                    clear-all-port(1),
                    clear-port1(2),
                    clear-port2(3),
                    clear-port3(4),
                    clear-port4(5),
                    clear-port5(6),
                    clear-port6(7),
                    clear-port7(8)
                }
            ACCESS  read-write
            STATUS  mandatory
            DESCRIPTION
                "Clear performance data"
            ::= { fom7PerfControlEty 2 }

--
-- 7FOM SNCP/UPSR APS Table
--

        fom7SncpApsTab  OBJECT-TYPE
            SYNTAX  SEQUENCE OF  Fom7SncpApsEty
            ACCESS  not-accessible
            STATUS  mandatory
            DESCRIPTION
                "7FOM SNCP/UPSR APS table "
            ::= { fom7-card 5 }

        fom7SncpApsEty  OBJECT-TYPE
            SYNTAX  Fom7SncpApsEty
            ACCESS  not-accessible
            STATUS  mandatory
            DESCRIPTION
                "7FOM SNCP/UPSR APS entry"
            INDEX { fom7SncpUnit , fom7SncpPort , fom7SncpChannel }
            ::= { fom7SncpApsTab 1 }

        Fom7SncpApsEty ::= SEQUENCE {
            fom7SncpUnit                UnitID,
            fom7SncpPort                PortID,
            fom7SncpChannel             ChannelNum,
            fom7SncpCurrentPathSlot     XcSlot,
            fom7SncpCurrentPathPort     PortID,
            fom7SncpPrimaryPathSlot     XcSlot,
            fom7SncpPrimaryPathPort     PortID,
            fom7SncpPPType              XcType,
            fom7SncpCmd                 SncpUserCmd
        }

        fom7SncpUnit  OBJECT-TYPE
            SYNTAX  UnitID
            ACCESS  read-only
            STATUS  mandatory
            DESCRIPTION
            "unit 1 to 4."
            ::= { fom7SncpApsEty 1 }

        fom7SncpPort  OBJECT-TYPE
            SYNTAX  PortID
            ACCESS  read-only
            STATUS  mandatory
            DESCRIPTION
                "PORT #1~#7"
            ::= { fom7SncpApsEty 2 }

        fom7SncpChannel  OBJECT-TYPE
            SYNTAX  ChannelNum
            ACCESS  read-only
            STATUS  mandatory
            DESCRIPTION
                "CHANNEL #1~#4"
            ::= { fom7SncpApsEty 3 }

        fom7SncpCurrentPathSlot  OBJECT-TYPE
            SYNTAX  XcSlot
            ACCESS  read-only
            STATUS  mandatory
            DESCRIPTION
                "SNCP/UPSR current path"
            ::= { fom7SncpApsEty 4 }

        fom7SncpCurrentPathPort  OBJECT-TYPE
            SYNTAX  PortID
            ACCESS  read-only
            STATUS  mandatory
            DESCRIPTION
                "SNCP/UPSR current port"
            ::= { fom7SncpApsEty 5 }

        fom7SncpPrimaryPathSlot  OBJECT-TYPE
            SYNTAX  XcSlot
            ACCESS  read-only
            STATUS  mandatory
            DESCRIPTION
                "SNCP/UPSR primary path"
            ::= { fom7SncpApsEty 6 }

        fom7SncpPrimaryPathPort  OBJECT-TYPE
            SYNTAX  PortID
            ACCESS  read-only
            STATUS  mandatory
            DESCRIPTION
                "SNCP/UPSR primary port"
            ::= { fom7SncpApsEty 7 }

        fom7SncpPPType  OBJECT-TYPE
            SYNTAX  XcType
            ACCESS  read-only
            STATUS  mandatory
            DESCRIPTION
                "SNCP/UPSR path protection type"
            ::= { fom7SncpApsEty 8 }

        fom7SncpCmd  OBJECT-TYPE
            SYNTAX  SncpUserCmd
            ACCESS  read-write
            STATUS  mandatory
            DESCRIPTION
                "SNCP/UPSR APS command"
            ::= { fom7SncpApsEty 9 }

--
-- 7FOM LED Status Table
--

        fom7LedStatusTab OBJECT-TYPE
            SYNTAX  SEQUENCE OF Fom7LedStatusEty
            ACCESS  not-accessible
            STATUS  mandatory
            DESCRIPTION
                "Led Status"
            ::= { fom7-card 6 }

        fom7LedStatusEty  OBJECT-TYPE
            SYNTAX  Fom7LedStatusEty
            ACCESS  not-accessible
            STATUS  mandatory
            DESCRIPTION
                "An entry in the led status table"
            INDEX { fom7LedStsUnit }
            ::= { fom7LedStatusTab 1 }

        Fom7LedStatusEty ::= SEQUENCE {
            fom7LedStsUnit              UnitID,
            fom7LedStsActiveLED         LedStatusType,
            fom7LedStsTestLED           LedStatusType,
            fom7LedStsAlarmLED          LedStatusType,
            fom7LedStsPort1SyncLED      LedStatusType,
            fom7LedStsPort2SyncLED      LedStatusType,
            fom7LedStsPort3SyncLED      LedStatusType,
            fom7LedStsPort4SyncLED      LedStatusType,
            fom7LedStsPort5SyncLED      LedStatusType,
            fom7LedStsPort6SyncLED      LedStatusType,
            fom7LedStsPort7SyncLED      LedStatusType,
            fom7LedStsPort1RAILED       LedStatusType,
            fom7LedStsPort2RAILED       LedStatusType,
            fom7LedStsPort3RAILED       LedStatusType,
            fom7LedStsPort4RAILED       LedStatusType,
            fom7LedStsPort5RAILED       LedStatusType,
            fom7LedStsPort6RAILED       LedStatusType,
            fom7LedStsPort7RAILED       LedStatusType,
            fom7LedStsPort1UnSyncLED    LedStatusType,
            fom7LedStsPort2UnSyncLED    LedStatusType,
            fom7LedStsPort3UnSyncLED    LedStatusType,
            fom7LedStsPort4UnSyncLED    LedStatusType,
            fom7LedStsPort5UnSyncLED    LedStatusType,
            fom7LedStsPort6UnSyncLED    LedStatusType,
            fom7LedStsPort7UnSyncLED    LedStatusType
        }

        fom7LedStsUnit  OBJECT-TYPE
            SYNTAX  UnitID
            ACCESS  read-only
            STATUS  mandatory
            DESCRIPTION
            "unit 1 to 4."
            ::= { fom7LedStatusEty 1 }

        fom7LedStsActiveLED  OBJECT-TYPE
            SYNTAX  LedStatusType
            ACCESS  read-only
            STATUS  mandatory
            DESCRIPTION
                "Active Led Status"
            ::= { fom7LedStatusEty 2 }

        fom7LedStsTestLED  OBJECT-TYPE
            SYNTAX  LedStatusType
            ACCESS  read-only
            STATUS  mandatory
            DESCRIPTION
                "Test Led Status"
            ::= { fom7LedStatusEty 3 }

        fom7LedStsAlarmLED  OBJECT-TYPE
            SYNTAX  LedStatusType
            ACCESS  read-only
            STATUS  mandatory
            DESCRIPTION
                "Alarm Led Status"
            ::= { fom7LedStatusEty 4 }

        fom7LedStsPort1SyncLED  OBJECT-TYPE
            SYNTAX  LedStatusType
            ACCESS  read-only
            STATUS  mandatory
            DESCRIPTION
                "FOM Port 1 Sync Led Status"
            ::= { fom7LedStatusEty 5 }

        fom7LedStsPort2SyncLED  OBJECT-TYPE
            SYNTAX  LedStatusType
            ACCESS  read-only
            STATUS  mandatory
            DESCRIPTION
                "FOM Port 2 Sync Led Status"
            ::= { fom7LedStatusEty 6 }

        fom7LedStsPort3SyncLED  OBJECT-TYPE
            SYNTAX  LedStatusType
            ACCESS  read-only
            STATUS  mandatory
            DESCRIPTION
                "FOM Port 3 Sync Led Status"
            ::= { fom7LedStatusEty 7 }

        fom7LedStsPort4SyncLED  OBJECT-TYPE
            SYNTAX  LedStatusType
            ACCESS  read-only
            STATUS  mandatory
            DESCRIPTION
                "FOM Port 4 Sync Led Status"
            ::= { fom7LedStatusEty 8 }

        fom7LedStsPort5SyncLED  OBJECT-TYPE
            SYNTAX  LedStatusType
            ACCESS  read-only
            STATUS  mandatory
            DESCRIPTION
                "FOM Port 5 Sync Led Status"
            ::= { fom7LedStatusEty 9 }

        fom7LedStsPort6SyncLED  OBJECT-TYPE
            SYNTAX  LedStatusType
            ACCESS  read-only
            STATUS  mandatory
            DESCRIPTION
                "FOM Port 6 Sync Led Status"
            ::= { fom7LedStatusEty 10 }

        fom7LedStsPort7SyncLED  OBJECT-TYPE
            SYNTAX  LedStatusType
            ACCESS  read-only
            STATUS  mandatory
            DESCRIPTION
                "FOM Port 7 Sync Led Status"
            ::= { fom7LedStatusEty 11 }

        fom7LedStsPort1RAILED  OBJECT-TYPE
            SYNTAX  LedStatusType
            ACCESS  read-only
            STATUS  mandatory
            DESCRIPTION
                "FOM Port 1 RAI Led Status"
            ::= { fom7LedStatusEty 12 }

        fom7LedStsPort2RAILED  OBJECT-TYPE
            SYNTAX  LedStatusType
            ACCESS  read-only
            STATUS  mandatory
            DESCRIPTION
                "FOM Port 2 RAI Led Status"
            ::= { fom7LedStatusEty 13 }

        fom7LedStsPort3RAILED  OBJECT-TYPE
            SYNTAX  LedStatusType
            ACCESS  read-only
            STATUS  mandatory
            DESCRIPTION
                "FOM Port 3 RAI Led Status"
            ::= { fom7LedStatusEty 14 }

        fom7LedStsPort4RAILED  OBJECT-TYPE
            SYNTAX  LedStatusType
            ACCESS  read-only
            STATUS  mandatory
            DESCRIPTION
                "FOM Port 4 RAI Led Status"
            ::= { fom7LedStatusEty 15 }

        fom7LedStsPort5RAILED  OBJECT-TYPE
            SYNTAX  LedStatusType
            ACCESS  read-only
            STATUS  mandatory
            DESCRIPTION
                "FOM Port 5 RAI Led Status"
            ::= { fom7LedStatusEty 16 }

        fom7LedStsPort6RAILED  OBJECT-TYPE
            SYNTAX  LedStatusType
            ACCESS  read-only
            STATUS  mandatory
            DESCRIPTION
                "FOM Port 6 RAI Led Status"
            ::= { fom7LedStatusEty 17 }

        fom7LedStsPort7RAILED  OBJECT-TYPE
            SYNTAX  LedStatusType
            ACCESS  read-only
            STATUS  mandatory
            DESCRIPTION
                "FOM Port 7 RAI Led Status"
            ::= { fom7LedStatusEty 18 }

        fom7LedStsPort1UnSyncLED  OBJECT-TYPE
            SYNTAX  LedStatusType
            ACCESS  read-only
            STATUS  mandatory
            DESCRIPTION
                "FOM Port 1 Un-Sync Led Status"
            ::= { fom7LedStatusEty 19 }

        fom7LedStsPort2UnSyncLED  OBJECT-TYPE
            SYNTAX  LedStatusType
            ACCESS  read-only
            STATUS  mandatory
            DESCRIPTION
                "FOM Port 2 Un-Sync Led Status"
            ::= { fom7LedStatusEty 20 }

        fom7LedStsPort3UnSyncLED  OBJECT-TYPE
            SYNTAX  LedStatusType
            ACCESS  read-only
            STATUS  mandatory
            DESCRIPTION
                "FOM Port 3 Un-Sync Led Status"
            ::= { fom7LedStatusEty 21 }

        fom7LedStsPort4UnSyncLED  OBJECT-TYPE
            SYNTAX  LedStatusType
            ACCESS  read-only
            STATUS  mandatory
            DESCRIPTION
                "FOM Port 4 Un-Sync Led Status"
            ::= { fom7LedStatusEty 22 }

        fom7LedStsPort5UnSyncLED  OBJECT-TYPE
            SYNTAX  LedStatusType
            ACCESS  read-only
            STATUS  mandatory
            DESCRIPTION
                "FOM Port 5 Un-Sync Led Status"
            ::= { fom7LedStatusEty 23 }

        fom7LedStsPort6UnSyncLED  OBJECT-TYPE
            SYNTAX  LedStatusType
            ACCESS  read-only
            STATUS  mandatory
            DESCRIPTION
                "FOM Port 6 Un-Sync Led Status"
            ::= { fom7LedStatusEty 24 }

        fom7LedStsPort7UnSyncLED  OBJECT-TYPE
            SYNTAX  LedStatusType
            ACCESS  read-only
            STATUS  mandatory
            DESCRIPTION
                "FOM Port 7 Un-Sync Led Status"
            ::= { fom7LedStatusEty 25 }

--
-- 7FOM SFP Information Table
--

        fom7SfpInfoTab  OBJECT-TYPE
            SYNTAX  SEQUENCE OF  Fom7SfpInfoEty
            ACCESS  not-accessible
            STATUS  mandatory
            DESCRIPTION
                "7FOM SFP information table "
            ::= { fom7-card 7 }

        fom7SfpInfoEty  OBJECT-TYPE
            SYNTAX  Fom7SfpInfoEty
            ACCESS  not-accessible
            STATUS  mandatory
            DESCRIPTION
                "7FOM SFP information entry"
            INDEX { fom7SfpInfoUnit , fom7SfpInfoPort }
            ::= { fom7SfpInfoTab 1 }

        Fom7SfpInfoEty ::= SEQUENCE {
            fom7SfpInfoUnit             UnitID,
            fom7SfpInfoPort             PortID,
            fom7SfpInfoEquip            INTEGER,
            fom7SfpInfoConnector        INTEGER,
            fom7SfpInfoTransceiver      DisplayString,
            fom7SfpInfoLinkLength       DisplayString,
            fom7SfpInfoTechnology       DisplayString,
            fom7SfpInfoEncoding         DisplayString,
            fom7SfpInfoLen9-125um       DisplayString,
            fom7SfpInfoLen50-125um      DisplayString,
            fom7SfpInfoLen62p5-125um    DisplayString,
            fom7SfpInfoLen-copper       DisplayString,
            fom7SfpInfoTemperature      DisplayString,
            fom7SfpInfoVcc              DisplayString,
            fom7SfpInfoTxBias           DisplayString,
            fom7SfpInfoTxPower          DisplayString,
            fom7SfpInfoRxPower          DisplayString,
            fom7SfpInfoDateCode     DisplayString,
            fom7SfpInfoVendorName   DisplayString,
            fom7SfpInfoVendorOUI    DisplayString,
            fom7SfpInfoVendorPN     DisplayString,
            fom7SfpInfoVendorRev    DisplayString,
            fom7SfpInfoWaveLength   DisplayString
        }

        fom7SfpInfoUnit  OBJECT-TYPE
            SYNTAX  UnitID
            ACCESS  read-only
            STATUS  mandatory
            DESCRIPTION
            "unit 1 to 4."
            ::= { fom7SfpInfoEty  1 }

        fom7SfpInfoPort  OBJECT-TYPE
            SYNTAX  PortID
            ACCESS  read-only
            STATUS  mandatory
            DESCRIPTION
                "PORT #1~#7"
            ::= { fom7SfpInfoEty  2 }

        fom7SfpInfoEquip  OBJECT-TYPE
            SYNTAX  INTEGER {
                    unequipped(1),
                    equipped(2)
                }
            ACCESS  read-only
            STATUS  mandatory
            DESCRIPTION
                "Port equip or not"
            ::= { fom7SfpInfoEty 3 }

        fom7SfpInfoConnector  OBJECT-TYPE
            SYNTAX  INTEGER {
                    not-available(1),
                    sc(2),
                    fibre-channel-style-1-copper(3),
                    fibre-hannel-style-2-copper(4),
                    bnc-tnc(5),
                    fibre-channel-coaxial-header(6),
                    fiberJack(7),
                    lc(8),
                    mt-rj(9),
                    mu(10),
                    sg(11),
                    optcal-pigtail(12),
                    hssdc-ii(13),
                    copper-pigtail(14)
                }
            ACCESS  read-only
            STATUS  mandatory
            DESCRIPTION
                "Port connector"
            ::= { fom7SfpInfoEty 4 }

        fom7SfpInfoTransceiver  OBJECT-TYPE
            SYNTAX  DisplayString (SIZE (0..255) )
            ACCESS  read-only
            STATUS  mandatory
            DESCRIPTION
                "Port transceiver"
            ::= { fom7SfpInfoEty 5 }

        fom7SfpInfoLinkLength  OBJECT-TYPE
            SYNTAX  DisplayString (SIZE (0..255) )
            ACCESS  read-only
            STATUS  mandatory
            DESCRIPTION
                "Port Link Length"
            ::= { fom7SfpInfoEty 6 }

        fom7SfpInfoTechnology  OBJECT-TYPE
            SYNTAX  DisplayString (SIZE (0..255) )
            ACCESS  read-only
            STATUS  mandatory
            DESCRIPTION
                "Port Technology"
            ::= { fom7SfpInfoEty 7 }

        fom7SfpInfoEncoding  OBJECT-TYPE
            SYNTAX  DisplayString (SIZE (0..255) )
            ACCESS  read-only
            STATUS  mandatory
            DESCRIPTION
                "Port Encoding"
            ::= { fom7SfpInfoEty 8 }

        fom7SfpInfoLen9-125um  OBJECT-TYPE
            SYNTAX  DisplayString (SIZE (0..255) )
            ACCESS  read-only
            STATUS  mandatory
            DESCRIPTION
                "Port length for 9/125 um fiber"
            ::= { fom7SfpInfoEty 9 }

        fom7SfpInfoLen50-125um  OBJECT-TYPE
            SYNTAX  DisplayString (SIZE (0..255) )
            ACCESS  read-only
            STATUS  mandatory
            DESCRIPTION
                "Port length for 50/125 um fiber"
            ::= { fom7SfpInfoEty 10 }

        fom7SfpInfoLen62p5-125um  OBJECT-TYPE
            SYNTAX  DisplayString (SIZE (0..255) )
            ACCESS  read-only
            STATUS  mandatory
            DESCRIPTION
                "Port length for 62.5/125 um fiber"
            ::= { fom7SfpInfoEty 11 }

        fom7SfpInfoLen-copper  OBJECT-TYPE
            SYNTAX  DisplayString (SIZE (0..255) )
            ACCESS  read-only
            STATUS  mandatory
            DESCRIPTION
                "Port length for copper"
            ::= { fom7SfpInfoEty 12 }

        fom7SfpInfoTemperature  OBJECT-TYPE
            SYNTAX  DisplayString (SIZE (0..255) )
            ACCESS  read-only
            STATUS  mandatory
            DESCRIPTION
                "Port Temperature"
            ::= { fom7SfpInfoEty 13 }

        fom7SfpInfoVcc  OBJECT-TYPE
            SYNTAX  DisplayString (SIZE (0..255) )
            ACCESS  read-only
            STATUS  mandatory
            DESCRIPTION
                "Port Vcc"
            ::= { fom7SfpInfoEty 14 }

        fom7SfpInfoTxBias  OBJECT-TYPE
            SYNTAX  DisplayString (SIZE (0..255) )
            ACCESS  read-only
            STATUS  mandatory
            DESCRIPTION
                "Port Tx Bias current"
            ::= { fom7SfpInfoEty 15 }

        fom7SfpInfoTxPower  OBJECT-TYPE
            SYNTAX  DisplayString (SIZE (0..255) )
            ACCESS  read-only
            STATUS  mandatory
            DESCRIPTION
                "Port Tx power"
            ::= { fom7SfpInfoEty 16 }

        fom7SfpInfoRxPower  OBJECT-TYPE
            SYNTAX  DisplayString (SIZE (0..255) )
            ACCESS  read-only
            STATUS  mandatory
            DESCRIPTION
                "Port Rx power"
            ::= { fom7SfpInfoEty 17 }

        fom7SfpInfoDateCode  OBJECT-TYPE
            SYNTAX  DisplayString (SIZE (0..255) )
            ACCESS  read-only
            STATUS  mandatory
            DESCRIPTION
                "Port date code "
            ::= { fom7SfpInfoEty 18 }

        fom7SfpInfoVendorName  OBJECT-TYPE
            SYNTAX  DisplayString (SIZE (0..255) )
            ACCESS  read-only
            STATUS  mandatory
            DESCRIPTION
                "Port vendor name "
            ::= { fom7SfpInfoEty 19 }

        fom7SfpInfoVendorOUI  OBJECT-TYPE
            SYNTAX  DisplayString (SIZE (0..255) )
            ACCESS  read-only
            STATUS  mandatory
            DESCRIPTION
                "Port vendor OUI "
            ::= { fom7SfpInfoEty 20 }

        fom7SfpInfoVendorPN  OBJECT-TYPE
            SYNTAX  DisplayString (SIZE (0..255) )
            ACCESS  read-only
            STATUS  mandatory
            DESCRIPTION
                "Port vendor pn "
            ::= { fom7SfpInfoEty 21 }

        fom7SfpInfoVendorRev  OBJECT-TYPE
            SYNTAX  DisplayString (SIZE (0..255) )
            ACCESS  read-only
            STATUS  mandatory
            DESCRIPTION
                "Port vendor rev "
            ::= { fom7SfpInfoEty 22 }

        fom7SfpInfoWaveLength  OBJECT-TYPE
            SYNTAX  DisplayString (SIZE (0..255) )
            ACCESS  read-only
            STATUS  mandatory
            DESCRIPTION
                "Port wave length "
            ::= { fom7SfpInfoEty 23 }

--
--  7FOM Line APSD Setup Table
--

        fom7AlsSetupTab  OBJECT-TYPE
            SYNTAX  SEQUENCE OF Fom7AlsSetupEty
            ACCESS  not-accessible
            STATUS  mandatory
            DESCRIPTION
                "Line ALS/APSD setup table"
            ::= { fom7-card 8 }

        fom7AlsSetupEty  OBJECT-TYPE
            SYNTAX  Fom7AlsSetupEty
            ACCESS  not-accessible
            STATUS  mandatory
            DESCRIPTION
                "An entry in the line ALS/APSD setup table"
            INDEX { fom7AlsUnit }
            ::= { fom7AlsSetupTab 1 }

        Fom7AlsSetupEty ::= SEQUENCE {
            fom7AlsUnit                 UnitID,
            fom7AlsEnable               INTEGER,
            fom7AlsPulseTime            INTEGER,
            fom7AlsP1PowerDown          INTEGER,
            fom7AlsP2PowerDown          INTEGER,
            fom7AlsP3PowerDown          INTEGER,
            fom7AlsP4PowerDown          INTEGER,
            fom7AlsP5PowerDown          INTEGER,
            fom7AlsP6PowerDown          INTEGER,
            fom7AlsP7PowerDown          INTEGER,
            fom7AlsP1ManualRestart      INTEGER,
            fom7AlsP2ManualRestart      INTEGER,
            fom7AlsP3ManualRestart      INTEGER,
            fom7AlsP4ManualRestart      INTEGER,
            fom7AlsP5ManualRestart      INTEGER,
            fom7AlsP6ManualRestart      INTEGER,
            fom7AlsP7ManualRestart      INTEGER
        }

        fom7AlsUnit  OBJECT-TYPE
            SYNTAX  UnitID
            ACCESS  read-only
            STATUS  mandatory
            DESCRIPTION
            "unit 1 to 4."
            ::= { fom7AlsSetupEty 1 }

        fom7AlsEnable  OBJECT-TYPE
            SYNTAX  INTEGER{
                    off(1),
                    on(2)
                }
            ACCESS  read-write
            STATUS  mandatory
            DESCRIPTION
                "FOM ALS enable setup"
            ::= { fom7AlsSetupEty 2 }

        fom7AlsPulseTime  OBJECT-TYPE
            SYNTAX  INTEGER (60..300)
            ACCESS  read-write
            STATUS  mandatory
            DESCRIPTION
                "FOM ALS Pulse repetition time for automatic restart(sec) setup"
            ::= { fom7AlsSetupEty 3 }

        fom7AlsP1PowerDown  OBJECT-TYPE
            SYNTAX  INTEGER{
                    off(1),
                    on(2)
                }
            ACCESS  read-write
            STATUS  mandatory
            DESCRIPTION
                "FOM P1 power down setup"
            ::= { fom7AlsSetupEty 4 }

        fom7AlsP2PowerDown  OBJECT-TYPE
            SYNTAX  INTEGER{
                    off(1),
                    on(2)
                }
            ACCESS  read-write
            STATUS  mandatory
            DESCRIPTION
                "FOM P2 power down setup"
            ::= { fom7AlsSetupEty 5 }

        fom7AlsP3PowerDown  OBJECT-TYPE
            SYNTAX  INTEGER{
                    off(1),
                    on(2)
                }
            ACCESS  read-write
            STATUS  mandatory
            DESCRIPTION
                "FOM P3 power down setup"
            ::= { fom7AlsSetupEty 6 }

        fom7AlsP4PowerDown  OBJECT-TYPE
            SYNTAX  INTEGER{
                    off(1),
                    on(2)
                }
            ACCESS  read-write
            STATUS  mandatory
            DESCRIPTION
                "FOM P4 power down setup"
            ::= { fom7AlsSetupEty 7 }

        fom7AlsP5PowerDown  OBJECT-TYPE
            SYNTAX  INTEGER{
                    off(1),
                    on(2)
                }
            ACCESS  read-write
            STATUS  mandatory
            DESCRIPTION
                "FOM P5 power down setup"
            ::= { fom7AlsSetupEty 8 }

        fom7AlsP6PowerDown  OBJECT-TYPE
            SYNTAX  INTEGER{
                    off(1),
                    on(2)
                }
            ACCESS  read-write
            STATUS  mandatory
            DESCRIPTION
                "FOM P6 power down setup"
            ::= { fom7AlsSetupEty 9 }

        fom7AlsP7PowerDown  OBJECT-TYPE
            SYNTAX  INTEGER{
                    off(1),
                    on(2)
                }
            ACCESS  read-write
            STATUS  mandatory
            DESCRIPTION
                "FOM P7 power down setup"
            ::= { fom7AlsSetupEty 10 }

        fom7AlsP1ManualRestart  OBJECT-TYPE
            SYNTAX  INTEGER{
                    off(1),
                    on(2)
                }
            ACCESS  read-write
            STATUS  mandatory
            DESCRIPTION
                "FOM P1 ALS manual restart setup"
            ::= { fom7AlsSetupEty 11 }

        fom7AlsP2ManualRestart  OBJECT-TYPE
            SYNTAX  INTEGER{
                    off(1),
                    on(2)
                }
            ACCESS  read-write
            STATUS  mandatory
            DESCRIPTION
                "FOM P2 ALS manual restart setup"
            ::= { fom7AlsSetupEty 12 }

        fom7AlsP3ManualRestart  OBJECT-TYPE
            SYNTAX  INTEGER{
                    off(1),
                    on(2)
                }
            ACCESS  read-write
            STATUS  mandatory
            DESCRIPTION
                "FOM P3 ALS manual restart setup"
            ::= { fom7AlsSetupEty 13 }

        fom7AlsP4ManualRestart  OBJECT-TYPE
            SYNTAX  INTEGER{
                    off(1),
                    on(2)
                }
            ACCESS  read-write
            STATUS  mandatory
            DESCRIPTION
                "FOM P4 ALS manual restart setup"
            ::= { fom7AlsSetupEty 14 }

        fom7AlsP5ManualRestart  OBJECT-TYPE
            SYNTAX  INTEGER{
                    off(1),
                    on(2)
                }
            ACCESS  read-write
            STATUS  mandatory
            DESCRIPTION
                "FOM P5 ALS manual restart setup"
            ::= { fom7AlsSetupEty 15 }

        fom7AlsP6ManualRestart  OBJECT-TYPE
            SYNTAX  INTEGER{
                    off(1),
                    on(2)
                }
            ACCESS  read-write
            STATUS  mandatory
            DESCRIPTION
                "FOM P6 ALS manual restart setup"
            ::= { fom7AlsSetupEty 16 }

        fom7AlsP7ManualRestart  OBJECT-TYPE
            SYNTAX  INTEGER{
                    off(1),
                    on(2)
                }
            ACCESS  read-write
            STATUS  mandatory
            DESCRIPTION
                "FOM P7 ALS manual restart setup"
            ::= { fom7AlsSetupEty 17 }

--
-- 7FOM Command Control Table
--

        fom7CommandControlTab  OBJECT-TYPE
            SYNTAX  SEQUENCE OF Fom7CommandControlEty
            ACCESS  not-accessible
            STATUS  mandatory
            DESCRIPTION
                "Command control"
            ::= { fom7-card 9 }

        fom7CommandControlEty  OBJECT-TYPE
            SYNTAX  Fom7CommandControlEty
            ACCESS  not-accessible
            STATUS  mandatory
            DESCRIPTION
                "An entry in the command control table"
            INDEX { fom7CmdUnit }
            ::= { fom7CommandControlTab 1 }

        Fom7CommandControlEty ::= SEQUENCE {
            fom7CmdUnit                 UnitID,
            fom7CmdUnitReset            INTEGER,
            fom7CmdUnitLoadDefault      INTEGER
        }

        fom7CmdUnit  OBJECT-TYPE
            SYNTAX  UnitID
            ACCESS  read-only
            STATUS  mandatory
            DESCRIPTION
            "unit 1 to 4."
            ::= { fom7CommandControlEty 1 }

        fom7CmdUnitReset  OBJECT-TYPE
            SYNTAX  INTEGER {
                    warm(1),
                    cold(2)
                }
            ACCESS  read-write
            STATUS  mandatory
            DESCRIPTION
                "Unit reset"
            ::= { fom7CommandControlEty 2 }

        fom7CmdUnitLoadDefault  OBJECT-TYPE
            SYNTAX  INTEGER {
                    load-default(1)
                }
            ACCESS  read-write
            STATUS  mandatory
            DESCRIPTION
                "Unit load default"
            ::= { fom7CommandControlEty 3 }

--
--  7FOM XC Display Table
--
        fom7XcDisplayTab  OBJECT-TYPE
            SYNTAX  SEQUENCE OF  Fom7XcDisplayEty
            ACCESS  not-accessible
            STATUS  mandatory
            DESCRIPTION
                "7FOM xc display table "
            ::= { fom7-card 10 }

        fom7XcDisplayEty  OBJECT-TYPE
            SYNTAX  Fom7XcDisplayEty
            ACCESS  not-accessible
            STATUS  mandatory
            DESCRIPTION
                "7FOM xc display entry"
            INDEX { fom7XcDispMapIndex ,
                    fom7XcDispUnitIndex ,
                    fom7XcDispPortIndex ,
                    fom7XcDispChannelIndex }
            ::= { fom7XcDisplayTab 1 }

        Fom7XcDisplayEty ::= SEQUENCE {
            fom7XcDispMapIndex          XcMap,
            fom7XcDispUnitIndex         UnitID,
            fom7XcDispPortIndex         PortID,
            fom7XcDispChannelIndex      ChannelNum,
            fom7XcDispSrcSlotType       NewXcModel,
            fom7XcDispSrcSlot           XcSlot,
            fom7XcDispSrcPort           PortID,
            fom7XcDispSrcChannel        ChannelNum,
            fom7XcDispSrcAug1Sts3       Aug1Sts3Num,
            fom7XcDispSrcVc3Sts1        Vc3Sts1Num,
            fom7XcDispSrcVc1xVtx        Vc1xVtxNum,
            fom7XcDispXcGranularity     INTEGER,
            fom7XcDispXcType            XcType
        }

        fom7XcDispMapIndex  OBJECT-TYPE
            SYNTAX  XcMap
            ACCESS  read-only
            STATUS  mandatory
            DESCRIPTION
                "xc map index"
            ::= { fom7XcDisplayEty 1 }

        fom7XcDispUnitIndex  OBJECT-TYPE
            SYNTAX  UnitID
            ACCESS  read-only
            STATUS  mandatory
            DESCRIPTION
            "unit 1 to 4."
            ::= { fom7XcDisplayEty 2 }

        fom7XcDispPortIndex  OBJECT-TYPE
            SYNTAX  PortID
            ACCESS  read-only
            STATUS  mandatory
            DESCRIPTION
                "PORT index"
            ::= { fom7XcDisplayEty 3 }

        fom7XcDispChannelIndex  OBJECT-TYPE
            SYNTAX  ChannelNum
            ACCESS  read-only
            STATUS  mandatory
            DESCRIPTION
                "CHANNEL index"
            ::= { fom7XcDisplayEty 4 }

        fom7XcDispSrcSlotType  OBJECT-TYPE
            SYNTAX  NewXcModel
            ACCESS  read-only
            STATUS  mandatory
            DESCRIPTION
                " Xc src Unit Type"
            ::= { fom7XcDisplayEty 5 }

        fom7XcDispSrcSlot  OBJECT-TYPE
            SYNTAX  XcSlot
            ACCESS  read-only
            STATUS  mandatory
            DESCRIPTION
                "Xc src Unit "
            ::= { fom7XcDisplayEty 6 }

        fom7XcDispSrcPort  OBJECT-TYPE
            SYNTAX  PortID
            ACCESS  read-only
            STATUS  mandatory
            DESCRIPTION
                "Xc src port "
            ::= { fom7XcDisplayEty 7 }

        fom7XcDispSrcChannel  OBJECT-TYPE
            SYNTAX  ChannelNum
            ACCESS  read-only
            STATUS  mandatory
            DESCRIPTION
                "Xc src channel "
            ::= { fom7XcDisplayEty 8 }

        fom7XcDispSrcAug1Sts3  OBJECT-TYPE
            SYNTAX  Aug1Sts3Num
            ACCESS  read-only
            STATUS  mandatory
            DESCRIPTION
                "Xc src AUG1/STS3 path"
            ::= { fom7XcDisplayEty 9 }

        fom7XcDispSrcVc3Sts1  OBJECT-TYPE
            SYNTAX  Vc3Sts1Num
            ACCESS  read-only
            STATUS  mandatory
            DESCRIPTION
                "Xc src VC3/STS1 path"
            ::= { fom7XcDisplayEty 10 }

        fom7XcDispSrcVc1xVtx  OBJECT-TYPE
            SYNTAX  Vc1xVtxNum
            ACCESS  read-only
            STATUS  mandatory
            DESCRIPTION
                "Xc src VC1x/VTx path"
            ::= { fom7XcDisplayEty 11 }

        fom7XcDispXcGranularity  OBJECT-TYPE
            SYNTAX  INTEGER {
                    tu3(2),
                    au3-sts1(3),
                    tu11-vt15(4),
                    tu12-vt2(5),
                    vc4-sts3c(6),
                    not-available(100)
                }
            ACCESS  read-only
            STATUS  mandatory
            DESCRIPTION
                "Xc granularity"
            ::= { fom7XcDisplayEty 12 }

        fom7XcDispXcType  OBJECT-TYPE
            SYNTAX  XcType
            ACCESS  read-only
            STATUS  mandatory
            DESCRIPTION
                "Xc type"
            ::= { fom7XcDisplayEty 13 }

--  2011-7-6 elvis add below

--
--  NEW 7FOM XC Display Table
--
        new-fom7XcDisplayTab  OBJECT-TYPE
            SYNTAX  SEQUENCE OF  NewFom7XcDisplayEty
            ACCESS  not-accessible
            STATUS  mandatory
            DESCRIPTION
                "new 7FOM xc display table "
            ::= { fom7-card 11 }

        new-fom7XcDisplayEty  OBJECT-TYPE
            SYNTAX  NewFom7XcDisplayEty
            ACCESS  not-accessible
            STATUS  mandatory
            DESCRIPTION
                "new 7FOM xc display entry"
            INDEX { new-fom7XcDispMapIndex ,
                    new-fom7XcDispUnitIndex ,
                    new-fom7XcDispPortIndex ,
                    new-fom7XcDispChannelIndex }
            ::= { new-fom7XcDisplayTab 1 }

        NewFom7XcDisplayEty ::= SEQUENCE {
            new-fom7XcDispMapIndex          XcMap,
            new-fom7XcDispUnitIndex         UnitID,
            new-fom7XcDispPortIndex         PortID,
            new-fom7XcDispChannelIndex      ChannelNum,
            new-fom7XcDispPriSlotType       NewXcModel,
            new-fom7XcDispPriSlot           XcSlot,
            new-fom7XcDispPriPort           PortID,
            new-fom7XcDispPriChannel        ChannelNum,
            new-fom7XcDispPriAug1Sts3       Aug1Sts3Num,
            new-fom7XcDispPriVc3Sts1        Vc3Sts1Num,
            new-fom7XcDispPriVc1xVtx        Vc1xVtxNum,
            new-fom7XcDispXcGranularity     INTEGER,
            new-fom7XcDispXcType            XcType,
            new-fom7XcDispSecSlotType       NewXcModel,
            new-fom7XcDispSecSlot           XcSlot,
            new-fom7XcDispSecPort           PortID,
            new-fom7XcDispSecChannel        ChannelNum,
            new-fom7XcDispSecAug1Sts3       Aug1Sts3Num,
            new-fom7XcDispSecVc3Sts1        Vc3Sts1Num,
            new-fom7XcDispSecVc1xVtx        Vc1xVtxNum
        }

        new-fom7XcDispMapIndex  OBJECT-TYPE
            SYNTAX  XcMap
            ACCESS  read-only
            STATUS  mandatory
            DESCRIPTION
                "xc map index"
            ::= { new-fom7XcDisplayEty 1 }

        new-fom7XcDispUnitIndex  OBJECT-TYPE
            SYNTAX  UnitID
            ACCESS  read-only
            STATUS  mandatory
            DESCRIPTION
                "unit 1 to 8."
            ::= { new-fom7XcDisplayEty 2 }

        new-fom7XcDispPortIndex  OBJECT-TYPE
            SYNTAX  PortID
            ACCESS  read-only
            STATUS  mandatory
            DESCRIPTION
                "PORT index"
            ::= { new-fom7XcDisplayEty 3 }

        new-fom7XcDispChannelIndex  OBJECT-TYPE
            SYNTAX  ChannelNum
            ACCESS  read-only
            STATUS  mandatory
            DESCRIPTION
                "CHANNEL index"
            ::= { new-fom7XcDisplayEty 4 }

        new-fom7XcDispPriSlotType  OBJECT-TYPE
            SYNTAX  NewXcModel
            ACCESS  read-only
            STATUS  mandatory
            DESCRIPTION
                " Xc Pri Unit Type"
            ::= { new-fom7XcDisplayEty 5 }

        new-fom7XcDispPriSlot  OBJECT-TYPE
            SYNTAX  XcSlot
            ACCESS  read-only
            STATUS  mandatory
            DESCRIPTION
                "Xc Pri Unit "
            ::= { new-fom7XcDisplayEty 6 }

        new-fom7XcDispPriPort  OBJECT-TYPE
            SYNTAX  PortID
            ACCESS  read-only
            STATUS  mandatory
            DESCRIPTION
                "Xc Pri port "
            ::= { new-fom7XcDisplayEty 7 }

        new-fom7XcDispPriChannel  OBJECT-TYPE
            SYNTAX  ChannelNum
            ACCESS  read-only
            STATUS  mandatory
            DESCRIPTION
                "Xc Pri channel "
            ::= { new-fom7XcDisplayEty 8 }

        new-fom7XcDispPriAug1Sts3  OBJECT-TYPE
            SYNTAX  Aug1Sts3Num
            ACCESS  read-only
            STATUS  mandatory
            DESCRIPTION
                "Xc Pri AUG1/STS3 path"
            ::= { new-fom7XcDisplayEty 9 }

        new-fom7XcDispPriVc3Sts1  OBJECT-TYPE
            SYNTAX  Vc3Sts1Num
            ACCESS  read-only
            STATUS  mandatory
            DESCRIPTION
                "Xc Pri VC3/STS1 path"
            ::= { new-fom7XcDisplayEty 10 }

        new-fom7XcDispPriVc1xVtx  OBJECT-TYPE
            SYNTAX  Vc1xVtxNum
            ACCESS  read-only
            STATUS  mandatory
            DESCRIPTION
                "Xc Pri VC1x/VTx path"
            ::= { new-fom7XcDisplayEty 11 }

        new-fom7XcDispXcGranularity  OBJECT-TYPE
            SYNTAX  INTEGER {
                    tu3(2),
                    au3-sts1(3),
                    tu11-vt15(4),
                    tu12-vt2(5),
                    vc4-sts3c(6),
                    not-available(100)
                }
            ACCESS  read-only
            STATUS  mandatory
            DESCRIPTION
                "Xc granularity"
            ::= { new-fom7XcDisplayEty 12 }

        new-fom7XcDispXcType  OBJECT-TYPE
            SYNTAX  XcType
            ACCESS  read-only
            STATUS  mandatory
            DESCRIPTION
                "Xc type"
            ::= { new-fom7XcDisplayEty 13 }

        new-fom7XcDispSecSlotType  OBJECT-TYPE
            SYNTAX  NewXcModel
            ACCESS  read-only
            STATUS  mandatory
            DESCRIPTION
                " Xc Sec Unit Type"
            ::= { new-fom7XcDisplayEty 14 }

        new-fom7XcDispSecSlot  OBJECT-TYPE
            SYNTAX  XcSlot
            ACCESS  read-only
            STATUS  mandatory
            DESCRIPTION
                "Xc Sec Unit "
            ::= { new-fom7XcDisplayEty 15 }

        new-fom7XcDispSecPort  OBJECT-TYPE
            SYNTAX  PortID
            ACCESS  read-only
            STATUS  mandatory
            DESCRIPTION
                "Xc Sec port "
            ::= { new-fom7XcDisplayEty 16 }

        new-fom7XcDispSecChannel  OBJECT-TYPE
            SYNTAX  ChannelNum
            ACCESS  read-only
            STATUS  mandatory
            DESCRIPTION
                "Xc Sec channel "
            ::= { new-fom7XcDisplayEty 17 }

        new-fom7XcDispSecAug1Sts3  OBJECT-TYPE
            SYNTAX  Aug1Sts3Num
            ACCESS  read-only
            STATUS  mandatory
            DESCRIPTION
                "Xc Sec AUG1/STS3 path"
            ::= { new-fom7XcDisplayEty 18 }

        new-fom7XcDispSecVc3Sts1  OBJECT-TYPE
            SYNTAX  Vc3Sts1Num
            ACCESS  read-only
            STATUS  mandatory
            DESCRIPTION
                "Xc Sec VC3/STS1 path"
            ::= { new-fom7XcDisplayEty 19 }

        new-fom7XcDispSecVc1xVtx  OBJECT-TYPE
            SYNTAX  Vc1xVtxNum
            ACCESS  read-only
            STATUS  mandatory
            DESCRIPTION
                "Xc Sec VC1x/VTx path"
            ::= { new-fom7XcDisplayEty 20 }

--
-- NEW 7FOM SNCP/UPSR APS Table
--

        new-fom7SncpApsTab  OBJECT-TYPE
            SYNTAX  SEQUENCE OF  NewFom7SncpApsEty
            ACCESS  not-accessible
            STATUS  mandatory
            DESCRIPTION
                "New 7FOM SNCP/UPSR APS table "
            ::= { fom7-card 12 }

        new-fom7SncpApsEty  OBJECT-TYPE
            SYNTAX  NewFom7SncpApsEty
            ACCESS  not-accessible
            STATUS  mandatory
            DESCRIPTION
                "7FOM SNCP/UPSR APS entry"
            INDEX { new-fom7SncpUnit , new-fom7SncpPort , new-fom7SncpChannel }
            ::= { new-fom7SncpApsTab 1 }

        NewFom7SncpApsEty ::= SEQUENCE {
            new-fom7SncpUnit                UnitID,
            new-fom7SncpPort                PortID,
            new-fom7SncpChannel             ChannelNum,
            new-fom7SncpCurrSlot            XcSlot,
            new-fom7SncpCurrPort            PortID,
            new-fom7SncpCurrChannel         ChannelNum,
            new-fom7SncpCurrAug1Sts3Path    Aug1Sts3Num,
            new-fom7SncpCurrVc3Sts1Path     Vc3Sts1Num,
            new-fom7SncpCurrVc1xVtxPath     Vc1xVtxNum,
            new-fom7SncpPPType              XcType,
            new-fom7SncpCmd                 SncpUserCmd,
            new-fom7SncpRevertive           INTEGER
        }

        new-fom7SncpUnit  OBJECT-TYPE
            SYNTAX  UnitID
            ACCESS  read-only
            STATUS  mandatory
            DESCRIPTION
                "unit 1 to 8."
            ::= { new-fom7SncpApsEty 1 }

        new-fom7SncpPort  OBJECT-TYPE
            SYNTAX  PortID
            ACCESS  read-only
            STATUS  mandatory
            DESCRIPTION
                "PORT #1~#7"
            ::= { new-fom7SncpApsEty 2 }

        new-fom7SncpChannel  OBJECT-TYPE
            SYNTAX  ChannelNum
            ACCESS  read-only
            STATUS  mandatory
            DESCRIPTION
                "CHANNEL #1~#4"
            ::= { new-fom7SncpApsEty 3 }

        new-fom7SncpCurrSlot  OBJECT-TYPE
            SYNTAX  XcSlot
            ACCESS  read-only
            STATUS  mandatory
            DESCRIPTION
                "SNCP/UPSR current slot"
            ::= { new-fom7SncpApsEty 4 }

        new-fom7SncpCurrPort  OBJECT-TYPE
            SYNTAX  PortID
            ACCESS  read-only
            STATUS  mandatory
            DESCRIPTION
                "SNCP/UPSR current port"
            ::= { new-fom7SncpApsEty 5 }

        new-fom7SncpCurrChannel  OBJECT-TYPE
            SYNTAX  ChannelNum
            ACCESS  read-only
            STATUS  mandatory
            DESCRIPTION
                "SNCP/UPSR current channel"
            ::= { new-fom7SncpApsEty 6 }

        new-fom7SncpCurrAug1Sts3Path  OBJECT-TYPE
            SYNTAX  Aug1Sts3Num
            ACCESS  read-only
            STATUS  mandatory
            DESCRIPTION
                "SNCP/UPSR current Aug1/Sts3"
            ::= { new-fom7SncpApsEty 7 }

        new-fom7SncpCurrVc3Sts1Path  OBJECT-TYPE
            SYNTAX  Vc3Sts1Num
            ACCESS  read-only
            STATUS  mandatory
            DESCRIPTION
                "SNCP/UPSR current Vc3/Sts1"
            ::= { new-fom7SncpApsEty 8 }

        new-fom7SncpCurrVc1xVtxPath  OBJECT-TYPE
            SYNTAX  Vc1xVtxNum
            ACCESS  read-only
            STATUS  mandatory
            DESCRIPTION
                "SNCP/UPSR current Vc1x/Vtx"
            ::= { new-fom7SncpApsEty 9 }

        new-fom7SncpPPType  OBJECT-TYPE
            SYNTAX  XcType
            ACCESS  read-only
            STATUS  mandatory
            DESCRIPTION
                "SNCP/UPSR path protection type"
            ::= { new-fom7SncpApsEty 10 }

        new-fom7SncpCmd  OBJECT-TYPE
            SYNTAX  SncpUserCmd
            ACCESS  read-write
            STATUS  mandatory
            DESCRIPTION
                "SNCP/UPSR APS command"
            ::= { new-fom7SncpApsEty 11 }

        new-fom7SncpRevertive  OBJECT-TYPE
            SYNTAX  INTEGER {
                    non-revertive(1),
                    revertive(2)
                }
            ACCESS  read-write
            STATUS  mandatory
            DESCRIPTION
                "SNCP/UPSR revertive or non-revertive"
            ::= { new-fom7SncpApsEty 12 }

        fom7TotalCard   OBJECT-TYPE
            SYNTAX  INTEGER
            ACCESS  read-only
            STATUS  mandatory
            DESCRIPTION
                "Total cards of FOM7"
            ::= { fom7-card 100 }


--  2011-7-6 elvis add above

--======================================================================--
--======================================================================--
--======================================================================--

--======================================================================--
--======================================================================--
--  8GESW card MIB
--======================================================================--
--======================================================================--

--
-- ge8ModeTable
--
        ge8ModeTable  OBJECT-TYPE
            SYNTAX  SEQUENCE OF Ge8ModeEntry
            ACCESS  not-accessible
            STATUS  mandatory
            DESCRIPTION
                "display 8GESW  unit mode"
            ::= { ge8EosCard 1 }

        ge8ModeEntry  OBJECT-TYPE
            SYNTAX  Ge8ModeEntry
            ACCESS  not-accessible
            STATUS  mandatory
            DESCRIPTION
                "unit model entry"
            INDEX { ge8ModeUnitIndex }
            ::= { ge8ModeTable 1 }

        Ge8ModeEntry ::= SEQUENCE {
            ge8ModeUnitIndex             UnitID,
            ge8ModeSetup                 INTEGER
        }

        ge8ModeUnitIndex  OBJECT-TYPE
            SYNTAX  UnitID
            ACCESS  read-only
            STATUS  mandatory
            DESCRIPTION
                "8GESW  unit index: 1~8 "
            ::= { ge8ModeEntry 1 }

        ge8ModeSetup   OBJECT-TYPE
            SYNTAX  INTEGER {
                    eLine(1),
                    eLan(2),
--                    portMap(3),
                    virtualeLine(4),
                    eLan4Kvlan(5)
                }
            ACCESS  read-write
            STATUS  mandatory
            DESCRIPTION
                " 8GESW  card mode: e-line/e-lan, change MODE will force card reset!"
            ::= { ge8ModeEntry 2 }


--
-- ge8VcgWanVlanMapTable
--

        ge8VcgWanVlanMapTable  OBJECT-TYPE
            SYNTAX  SEQUENCE OF Ge8VcgWanVlanMapEntry
            ACCESS  not-accessible
            STATUS  mandatory
            DESCRIPTION
                "VCG-WAN-VLAN map setup table"
            ::= { ge8EosCard 2 }

        ge8VcgWanVlanMapEntry  OBJECT-TYPE
            SYNTAX  Ge8VcgWanVlanMapEntry
            ACCESS  not-accessible
            STATUS  mandatory
            DESCRIPTION
                "VCG-WAN-VLAN map setup entry"
            INDEX { ge8VmapUnitIndex , ge8VcgMapIndex }
            ::= { ge8VcgWanVlanMapTable 1 }

        Ge8VcgWanVlanMapEntry ::= SEQUENCE {
            ge8VmapUnitIndex               UnitID,
            ge8VcgMapIndex                 INTEGER,
            ge8VcgWanNo                    INTEGER,
            ge8VcgVlanId                   INTEGER,
            ge8VcgVlanCmd                  INTEGER,
            ge8VcgVlanList                 DisplayString
        }

        ge8VmapUnitIndex  OBJECT-TYPE
            SYNTAX  UnitID
            ACCESS  read-only
            STATUS  mandatory
            DESCRIPTION
                "unit index: 1~8 "
            ::= { ge8VcgWanVlanMapEntry 1 }

        ge8VcgMapIndex  OBJECT-TYPE
            SYNTAX  INTEGER (1..48)
            ACCESS  read-only
            STATUS  mandatory
            DESCRIPTION
                "VCG index"
            ::= { ge8VcgWanVlanMapEntry 2 }

        ge8VcgWanNo  OBJECT-TYPE
            SYNTAX  INTEGER {
                    wan1(1),
                    wan2(2),
                    wan3(3),
                    wan4(4),
                    no(99)
                }
            ACCESS  read-write
            STATUS  mandatory
            DESCRIPTION
                "WAN number"
            ::= { ge8VcgWanVlanMapEntry 3 }

        ge8VcgVlanId  OBJECT-TYPE
            SYNTAX  INTEGER (1..4094)
            ACCESS  read-write
            STATUS  mandatory
            DESCRIPTION
                "Vlan ID"
            ::= { ge8VcgWanVlanMapEntry 4 }

        ge8VcgVlanCmd  OBJECT-TYPE
            SYNTAX  INTEGER {
                    no(1),
                    add(2),
                    delete(3),
                    deleteAll(4)
                }
            ACCESS  read-write
            STATUS  mandatory
            DESCRIPTION
                "Vlan command"
            ::= { ge8VcgWanVlanMapEntry 5 }

        ge8VcgVlanList  OBJECT-TYPE
            SYNTAX  DisplayString (SIZE (0..200))
            ACCESS  read-only
            STATUS  mandatory
            DESCRIPTION
                "VLAN ID list"
            ::= { ge8VcgWanVlanMapEntry 6 }


--
-- ge8VcgConfigSetupTable
--

        ge8VcgConfigSetupTable  OBJECT-TYPE
            SYNTAX  SEQUENCE OF Ge8VcgConfigSetupEntry
            ACCESS  not-accessible
            STATUS  mandatory
            DESCRIPTION
                "VCG-WAN-VLAN map setup table"
            ::= { ge8EosCard 3 }

        ge8VcgConfigSetupEntry  OBJECT-TYPE
            SYNTAX  Ge8VcgConfigSetupEntry
            ACCESS  not-accessible
            STATUS  mandatory
            DESCRIPTION
                "VCG-WAN-VLAN map setup entry"
            INDEX { ge8VgroupUnitIndex , ge8VcgSetIndex }
            ::= { ge8VcgConfigSetupTable 1 }

        Ge8VcgConfigSetupEntry ::= SEQUENCE {
            ge8VgroupUnitIndex             UnitID,
            ge8VcgSetIndex                 INTEGER,
            ge8VcgGranularityType          INTEGER,
            ge8VcgLcas                     INTEGER,
            ge8VcgEncapType                INTEGER,
            ge8VcgProfileAssign            INTEGER
        }

        ge8VgroupUnitIndex  OBJECT-TYPE
            SYNTAX  UnitID
            ACCESS  read-only
            STATUS  mandatory
            DESCRIPTION
                "unit index: 1~8 "
            ::= { ge8VcgConfigSetupEntry 1 }

        ge8VcgSetIndex  OBJECT-TYPE
            SYNTAX  INTEGER (1..48)
            ACCESS  read-only
            STATUS  mandatory
            DESCRIPTION
                "VCG index"
            ::= { ge8VcgConfigSetupEntry 2 }

        ge8VcgGranularityType  OBJECT-TYPE
            SYNTAX  INTEGER {
                    tu3(1),
                    au3Sts1(2),
                    tu11Vt15(3),
                    tu12Vt2(4),
                    au4Sts3c(5)
                }
            ACCESS  read-write
            STATUS  mandatory
            DESCRIPTION
                "vcg payload type"
            ::= { ge8VcgConfigSetupEntry 3 }

        ge8VcgLcas  OBJECT-TYPE
            SYNTAX  INTEGER {
                    nonLcas(1),
                    lcas(2)
                }
            ACCESS  read-write
            STATUS  mandatory
            DESCRIPTION
                "vcg lcas state"
            ::= { ge8VcgConfigSetupEntry 4 }


        ge8VcgEncapType  OBJECT-TYPE
            SYNTAX  INTEGER {
                    gfpF(1),
                    laps(2),
--                    ppp(3)
                    bcp(4)
--                    gfpT(5)
                }
            ACCESS  read-write
            STATUS  mandatory
            DESCRIPTION
                "vcg encapturation type"
            ::= { ge8VcgConfigSetupEntry 5 }

        ge8VcgProfileAssign  OBJECT-TYPE
            SYNTAX  INTEGER (1..8)
            ACCESS  read-write
            STATUS  mandatory
            DESCRIPTION
                "Group number"
            ::= { ge8VcgConfigSetupEntry 6 }


--
-- ge8VcgProfileSetup
--
    ge8VcgProfileSetup        OBJECT IDENTIFIER ::= { ge8EosCard 4 }


--
-- ge8WanVcgAlmSetupTable
--
        ge8WanVcgAlmSetupTable  OBJECT-TYPE
            SYNTAX  SEQUENCE OF Ge8WanVcgAlmSetupEntry
            ACCESS  not-accessible
            STATUS  mandatory
            DESCRIPTION
                "vcg member alarm setup table"
            ::= { ge8VcgProfileSetup 1 }

        ge8WanVcgAlmSetupEntry  OBJECT-TYPE
            SYNTAX  Ge8WanVcgAlmSetupEntry
            ACCESS  not-accessible
            STATUS  mandatory
            DESCRIPTION
                "vcg member alarm setup entry"
            INDEX { ge8VcgAlmSetupUnitIndex , ge8VcgAlmProfileIndex ,
                    ge8VcgAlmSetupPathIndex , ge8VcgAlmSetupTypeIndex }
            ::= { ge8WanVcgAlmSetupTable 1 }

        Ge8WanVcgAlmSetupEntry ::= SEQUENCE {
            ge8VcgAlmSetupUnitIndex        UnitID,
            ge8VcgAlmProfileIndex          INTEGER,
            ge8VcgAlmSetupPathIndex        INTEGER,
            ge8VcgAlmSetupTypeIndex        INTEGER,
            ge8VcgAlmSetupAlarm            INTEGER,
            ge8VcgAlmSetupRelay            INTEGER,
            ge8VcgAlmSetupSeverity         Severity
        }

        ge8VcgAlmSetupUnitIndex  OBJECT-TYPE
            SYNTAX  UnitID
            ACCESS  read-only
            STATUS  mandatory
            DESCRIPTION
                "vcg unit index: 1~8 "
            ::= { ge8WanVcgAlmSetupEntry 1 }

        ge8VcgAlmProfileIndex  OBJECT-TYPE
            SYNTAX  INTEGER (1..8)
            ACCESS  read-only
            STATUS  mandatory
            DESCRIPTION
                "vcg port index "
            ::= { ge8WanVcgAlmSetupEntry 2 }

        ge8VcgAlmSetupPathIndex  OBJECT-TYPE
            SYNTAX  INTEGER {
                    lowOrder(1),
                    hiOrder(2)
                }
            ACCESS  read-only
            STATUS  mandatory
            DESCRIPTION
                "vcg path index: low-order path or hi-order path "
            ::= { ge8WanVcgAlmSetupEntry 3 }

        ge8VcgAlmSetupTypeIndex  OBJECT-TYPE
            SYNTAX  INTEGER {
                    lop(1),
                    ais(2),
                    sd(3),
                    sf(4),
                    uneq(5),
                    plm(6),
                    tim(7),
                    rdiP(8),
                    rdiS(9),
                    rdiC(10),
                    rei(11),
                    bip(12)
                }
            ACCESS  read-only
            STATUS  mandatory
            DESCRIPTION
                "path alarm type: tu-lop,tu-ais,.... "
            ::= { ge8WanVcgAlmSetupEntry 4 }

        ge8VcgAlmSetupAlarm  OBJECT-TYPE
            SYNTAX  INTEGER {
                    disable(1),
                    enable(2)
                }
            ACCESS  read-write
            STATUS  mandatory
            DESCRIPTION
                "vcg member alarm mask enable/disable"
            ::= { ge8WanVcgAlmSetupEntry 5 }

        ge8VcgAlmSetupRelay  OBJECT-TYPE
            SYNTAX  INTEGER {
                    disable(1),
                    enable(2)
                }
            ACCESS  read-write
            STATUS  mandatory
            DESCRIPTION
                "vcg member alarm relay enable/disable"
            ::= { ge8WanVcgAlmSetupEntry 6 }

        ge8VcgAlmSetupSeverity  OBJECT-TYPE
            SYNTAX  Severity
            ACCESS  read-write
            STATUS  mandatory
            DESCRIPTION
                "vcg member alarm severity"
            ::= { ge8WanVcgAlmSetupEntry 7 }


--
--   ge8WanVcgTcaTable
--
        ge8WanVcgTcaTable  OBJECT-TYPE
            SYNTAX  SEQUENCE OF Ge8WanVcgTcaEntry
            ACCESS  not-accessible
            STATUS  mandatory
            DESCRIPTION
                "vcg threshold cross alarm entry table"
            ::= { ge8VcgProfileSetup 2 }

        ge8WanVcgTcaEntry  OBJECT-TYPE
            SYNTAX  Ge8WanVcgTcaEntry
            ACCESS  not-accessible
            STATUS  mandatory
            DESCRIPTION
                "vcg threshold cross alarm entry"
            INDEX { ge8VcgTcaUnitIndex , ge8VcgTcaProfileIndex , ge8VcgTcaTypeIndex }
            ::= { ge8WanVcgTcaTable 1 }

        Ge8WanVcgTcaEntry ::= SEQUENCE {
            ge8VcgTcaUnitIndex             UnitID,
            ge8VcgTcaProfileIndex          INTEGER,
            ge8VcgTcaTypeIndex             INTEGER,
            ge8VcgTcaAlmMask               INTEGER,
            ge8VcgTcaSeverity              Severity,
            ge8VcgTcaThreshold             INTEGER
        }

        ge8VcgTcaUnitIndex  OBJECT-TYPE
            SYNTAX  UnitID
            ACCESS  read-only
            STATUS  mandatory
            DESCRIPTION
                "vcg unit index: 1~8 "
            ::= { ge8WanVcgTcaEntry 1 }

        ge8VcgTcaProfileIndex  OBJECT-TYPE
            SYNTAX  INTEGER (1..8)
            ACCESS  read-only
            STATUS  mandatory
            DESCRIPTION
                "vcg group index"
            ::= { ge8WanVcgTcaEntry 2 }

        ge8VcgTcaTypeIndex  OBJECT-TYPE
            SYNTAX  INTEGER {
                    erroredFcsCount(1),
                    fifoOverflowFrameCount(2),
                    droppedFrameCount(3)
                }
            ACCESS  read-only
            STATUS  mandatory
            DESCRIPTION
                "vcg tca type index"
            ::= { ge8WanVcgTcaEntry 3 }

        ge8VcgTcaAlmMask  OBJECT-TYPE
            SYNTAX  INTEGER {
                    disable(1),
                    enable(2)
                }
            ACCESS  read-write
            STATUS  mandatory
            DESCRIPTION
                "vcg tca alarm mask enable/disable"
            ::= { ge8WanVcgTcaEntry 4 }

        ge8VcgTcaSeverity  OBJECT-TYPE
            SYNTAX  Severity
            ACCESS  read-write
            STATUS  mandatory
            DESCRIPTION
                "vcg tca alarm severity"
            ::= { ge8WanVcgTcaEntry 5 }

        ge8VcgTcaThreshold  OBJECT-TYPE
            SYNTAX  INTEGER (1..99999)
            ACCESS  read-write
            STATUS  mandatory
            DESCRIPTION
                "vcg tca threshold"
            ::= { ge8WanVcgTcaEntry 6 }


--
-- ge8WanVcgGfpParaTable
--
        ge8WanVcgGfpParaTable  OBJECT-TYPE
            SYNTAX  SEQUENCE OF Ge8WanVcgGfpParaEntry
            ACCESS  not-accessible
            STATUS  mandatory
            DESCRIPTION
                "vcg gfp parameter configuration"
            ::= { ge8VcgProfileSetup 3 }

        ge8WanVcgGfpParaEntry  OBJECT-TYPE
            SYNTAX  Ge8WanVcgGfpParaEntry
            ACCESS  not-accessible
            STATUS  mandatory
            DESCRIPTION
                "vcg gfp parameter configuration entry"
            INDEX { ge8VcgGfpUnitIndex , ge8VcgGfpProfileIndex }
            ::= { ge8WanVcgGfpParaTable 1 }

        Ge8WanVcgGfpParaEntry ::= SEQUENCE {
            ge8VcgGfpUnitIndex             UnitID,
            ge8VcgGfpProfileIndex          INTEGER,
            ge8VcgGfpRxPti                 INTEGER,
            ge8VcgGfpTxPti                 INTEGER,
            ge8VcgGfpRxExi                 INTEGER,
            ge8VcgGfpTxExi                 INTEGER,
            ge8VcgGfpRxUpi                 INTEGER,
            ge8VcgGfpTxUpi                 INTEGER,
            ge8VcgGfpDelta                 INTEGER,
            ge8VcgGfpTxPfi                 INTEGER,
            ge8VcgGfpRxDescramble          INTEGER,
            ge8VcgGfpTxScramble            INTEGER,
            ge8VcgGfpRxPayloadFcsCheck     INTEGER,
            ge8VcgGfpTxPayloadFcsInsert    INTEGER,
            ge8VcgGfpRxPtiCheck            INTEGER,
            ge8VcgGfpRxUpiCheck            INTEGER,
            ge8VcgGfpTxRxFcsMode           INTEGER
        }

        ge8VcgGfpUnitIndex  OBJECT-TYPE
            SYNTAX  UnitID
            ACCESS  read-only
            STATUS  mandatory
            DESCRIPTION
                "vcg unit index: 1~8 "
            ::= { ge8WanVcgGfpParaEntry 1 }

        ge8VcgGfpProfileIndex  OBJECT-TYPE
            SYNTAX  INTEGER (1..8)
            ACCESS  read-only
            STATUS  mandatory
            DESCRIPTION
                "vcg port index "
            ::= { ge8WanVcgGfpParaEntry 2 }

        ge8VcgGfpRxPti  OBJECT-TYPE
            SYNTAX  INTEGER (0..7)
            ACCESS  read-write
            STATUS  mandatory
            DESCRIPTION
                "vcg Gfp Rx PTI"
            ::= { ge8WanVcgGfpParaEntry 3 }

        ge8VcgGfpTxPti  OBJECT-TYPE
            SYNTAX  INTEGER (0..7)
            ACCESS  read-write
            STATUS  mandatory
            DESCRIPTION
                "vcg Gfp Tx PTI"
            ::= { ge8WanVcgGfpParaEntry 4 }

        ge8VcgGfpRxExi  OBJECT-TYPE
            SYNTAX  INTEGER (0..15)
            ACCESS  read-write
            STATUS  mandatory
            DESCRIPTION
                "vcg Gfp Rx EXI"
            ::= { ge8WanVcgGfpParaEntry 5 }

        ge8VcgGfpTxExi  OBJECT-TYPE
            SYNTAX  INTEGER (0..15)
            ACCESS  read-write
            STATUS  mandatory
            DESCRIPTION
                "vcg Gfp Tx EXI"
            ::= { ge8WanVcgGfpParaEntry 6 }

        ge8VcgGfpRxUpi  OBJECT-TYPE
            SYNTAX  INTEGER (0..255)
            ACCESS  read-write
            STATUS  mandatory
            DESCRIPTION
                "vcg Gfp Rx UPI"
            ::= { ge8WanVcgGfpParaEntry 7 }

        ge8VcgGfpTxUpi  OBJECT-TYPE
            SYNTAX  INTEGER (0..255)
            ACCESS  read-write
            STATUS  mandatory
            DESCRIPTION
                "vcg Gfp Tx UPI"
            ::= { ge8WanVcgGfpParaEntry 8 }

        ge8VcgGfpDelta  OBJECT-TYPE
            SYNTAX  INTEGER (1..4)
            ACCESS  read-write
            STATUS  mandatory
            DESCRIPTION
                "vcg Gfp DELTA"
            ::= { ge8WanVcgGfpParaEntry 9 }

        ge8VcgGfpTxPfi  OBJECT-TYPE
            SYNTAX  INTEGER (0..1)
            ACCESS  read-write
            STATUS  mandatory
            DESCRIPTION
                "vcg Gfp Tx PFI"
            ::= { ge8WanVcgGfpParaEntry 10 }

        ge8VcgGfpRxDescramble  OBJECT-TYPE
            SYNTAX  INTEGER {
                    disable(1),
                    enable(2)
                }
            ACCESS  read-write
            STATUS  mandatory
            DESCRIPTION
                "vcg Gfp Rx Descramble"
            ::= { ge8WanVcgGfpParaEntry 11 }

        ge8VcgGfpTxScramble  OBJECT-TYPE
            SYNTAX  INTEGER {
                    disable(1),
                    enable(2)
                }
            ACCESS  read-write
            STATUS  mandatory
            DESCRIPTION
                "vcg Gfp Tx Scramble"
            ::= { ge8WanVcgGfpParaEntry 12 }

        ge8VcgGfpRxPayloadFcsCheck  OBJECT-TYPE
            SYNTAX  INTEGER {
                    disable(1),
                    enable(2)
                }
            ACCESS  read-write
            STATUS  mandatory
            DESCRIPTION
                "vcg Gfp Rx Payload FCS Check"
            ::= { ge8WanVcgGfpParaEntry 13 }

        ge8VcgGfpTxPayloadFcsInsert  OBJECT-TYPE
            SYNTAX  INTEGER {
                    disable(1),
                    enable(2)
                }
            ACCESS  read-write
            STATUS  mandatory
            DESCRIPTION
                "vcg Gfp Tx Payload FCS Insert"
            ::= { ge8WanVcgGfpParaEntry 14 }

        ge8VcgGfpRxPtiCheck  OBJECT-TYPE
            SYNTAX  INTEGER {
                    disable(1),
                    enable(2)
                }
            ACCESS  read-write
            STATUS  mandatory
            DESCRIPTION
                "vcg Gfp Rx PTI Check"
            ::= { ge8WanVcgGfpParaEntry 15 }

        ge8VcgGfpRxUpiCheck  OBJECT-TYPE
            SYNTAX  INTEGER {
                    disable(1),
                    enable(2)
                }
            ACCESS  read-write
            STATUS  mandatory
            DESCRIPTION
                "vcg Gfp Rx UPI Check"
            ::= { ge8WanVcgGfpParaEntry 16 }

        ge8VcgGfpTxRxFcsMode  OBJECT-TYPE
            SYNTAX  INTEGER {
                    crc32(1),
                    crc16(2)
                }
            ACCESS  read-write
            STATUS  mandatory
            DESCRIPTION
                "vcg Gfp Tx/Rx Payload FCS mode"
            ::= { ge8WanVcgGfpParaEntry 17 }


--
-- ge8WanVcgLapsParaTable
--
        ge8WanVcgLapsParaTable  OBJECT-TYPE
            SYNTAX  SEQUENCE OF Ge8WanVcgLapsParaEntry
            ACCESS  not-accessible
            STATUS  mandatory
            DESCRIPTION
                "vcg Laps parameter configuration"
            ::= { ge8VcgProfileSetup 4 }

        ge8WanVcgLapsParaEntry  OBJECT-TYPE
            SYNTAX  Ge8WanVcgLapsParaEntry
            ACCESS  not-accessible
            STATUS  mandatory
            DESCRIPTION
                "vcg Laps parameter configuration entry"
            INDEX { ge8VcgLapsUnitIndex , ge8VcgLapsProfileIndex }
            ::= { ge8WanVcgLapsParaTable 1 }

        Ge8WanVcgLapsParaEntry ::= SEQUENCE {
            ge8VcgLapsUnitIndex            UnitID,
            ge8VcgLapsProfileIndex         INTEGER,
            ge8VcgLapsRxAddress            INTEGER,
            ge8VcgLapsTxAddress            INTEGER,
            ge8VcgLapsRxControl            INTEGER,
            ge8VcgLapsTxControl            INTEGER,
            ge8VcgLapsRxSapiMsb            INTEGER,
            ge8VcgLapsTxSapiMsb            INTEGER,
            ge8VcgLapsRxSapiLsb            INTEGER,
            ge8VcgLapsTxSapiLsb            INTEGER,
            ge8VcgLapsRxDescramble         INTEGER,
            ge8VcgLapsTxScramble           INTEGER,
            ge8VcgLapsRxPayloadFcsCheck    INTEGER,
            ge8VcgLapsTxPayloadFcsIns      INTEGER,
            ge8VcgLapsRxAddressCheck       INTEGER,
            ge8VcgLapsRxControlCheck       INTEGER,
            ge8VcgLapsRxSapiCheck          INTEGER,
            ge8VcgLapsTxRxFcsMode          INTEGER
        }

        ge8VcgLapsUnitIndex  OBJECT-TYPE
            SYNTAX  UnitID
            ACCESS  read-only
            STATUS  mandatory
            DESCRIPTION
                "vcg unit index: 1~8 "
            ::= { ge8WanVcgLapsParaEntry 1 }

        ge8VcgLapsProfileIndex  OBJECT-TYPE
            SYNTAX  INTEGER (1..8)
            ACCESS  read-only
            STATUS  mandatory
            DESCRIPTION
                "vcg port index "
            ::= { ge8WanVcgLapsParaEntry 2 }

        ge8VcgLapsRxAddress  OBJECT-TYPE
            SYNTAX  INTEGER (0..255)
            ACCESS  read-write
            STATUS  mandatory
            DESCRIPTION
                "vcg Laps Rx Address"
            ::= { ge8WanVcgLapsParaEntry 3 }

        ge8VcgLapsTxAddress  OBJECT-TYPE
            SYNTAX  INTEGER (0..255)
            ACCESS  read-write
            STATUS  mandatory
            DESCRIPTION
                "vcg Laps Tx Address"
            ::= { ge8WanVcgLapsParaEntry 4 }

        ge8VcgLapsRxControl  OBJECT-TYPE
            SYNTAX  INTEGER (0..255)
            ACCESS  read-write
            STATUS  mandatory
            DESCRIPTION
                "vcg Laps Rx Control"
            ::= { ge8WanVcgLapsParaEntry 5 }

        ge8VcgLapsTxControl  OBJECT-TYPE
            SYNTAX  INTEGER (0..255)
            ACCESS  read-write
            STATUS  mandatory
            DESCRIPTION
                "vcg Laps Tx Control"
            ::= { ge8WanVcgLapsParaEntry 6 }

        ge8VcgLapsRxSapiMsb  OBJECT-TYPE
            SYNTAX  INTEGER (0..255)
            ACCESS  read-write
            STATUS  mandatory
            DESCRIPTION
                "vcg Laps Rx SAPI MSB"
            ::= { ge8WanVcgLapsParaEntry 7 }

        ge8VcgLapsTxSapiMsb  OBJECT-TYPE
            SYNTAX  INTEGER (0..255)
            ACCESS  read-write
            STATUS  mandatory
            DESCRIPTION
                "vcg Laps Tx SAPI MSB"
            ::= { ge8WanVcgLapsParaEntry 8 }

        ge8VcgLapsRxSapiLsb  OBJECT-TYPE
            SYNTAX  INTEGER (0..255)
            ACCESS  read-write
            STATUS  mandatory
            DESCRIPTION
                "vcg Laps Rx SAPI LSB"
            ::= { ge8WanVcgLapsParaEntry 9 }

        ge8VcgLapsTxSapiLsb  OBJECT-TYPE
            SYNTAX  INTEGER (0..255)
            ACCESS  read-write
            STATUS  mandatory
            DESCRIPTION
                "vcg Laps Tx SAPI LSB"
            ::= { ge8WanVcgLapsParaEntry 10 }

        ge8VcgLapsRxDescramble  OBJECT-TYPE
            SYNTAX  INTEGER {
                    disable(1),
                    enable(2)
                }
            ACCESS  read-write
            STATUS  mandatory
            DESCRIPTION
                "vcg Laps Rx Descramble"
            ::= { ge8WanVcgLapsParaEntry 11 }

        ge8VcgLapsTxScramble  OBJECT-TYPE
            SYNTAX  INTEGER {
                    disable(1),
                    enable(2)
                }
            ACCESS  read-write
            STATUS  mandatory
            DESCRIPTION
                "vcg Laps Tx Scramble"
            ::= { ge8WanVcgLapsParaEntry 12 }

        ge8VcgLapsRxPayloadFcsCheck  OBJECT-TYPE
            SYNTAX  INTEGER {
                    disable(1),
                    enable(2)
                }
            ACCESS  read-write
            STATUS  mandatory
            DESCRIPTION
                "vcg Laps Rx Payload FCS Check"
            ::= { ge8WanVcgLapsParaEntry 13 }

        ge8VcgLapsTxPayloadFcsIns  OBJECT-TYPE
            SYNTAX  INTEGER {
                    disable(1),
                    enable(2)
                }
            ACCESS  read-write
            STATUS  mandatory
            DESCRIPTION
                "vcg Laps Tx Payload FCS Insert"
            ::= { ge8WanVcgLapsParaEntry 14 }

        ge8VcgLapsRxAddressCheck  OBJECT-TYPE
            SYNTAX  INTEGER {
                    disable(1),
                    enable(2)
                }
            ACCESS  read-write
            STATUS  mandatory
            DESCRIPTION
                "vcg Laps Rx Address Check"
            ::= { ge8WanVcgLapsParaEntry 15 }

        ge8VcgLapsRxControlCheck  OBJECT-TYPE
            SYNTAX  INTEGER {
                    disable(1),
                    enable(2)
                }
            ACCESS  read-write
            STATUS  mandatory
            DESCRIPTION
                "vcg Laps Rx Control Check"
            ::= { ge8WanVcgLapsParaEntry 16 }

        ge8VcgLapsRxSapiCheck  OBJECT-TYPE
            SYNTAX  INTEGER {
                    disable(1),
                    enable(2)
                }
            ACCESS  read-write
            STATUS  mandatory
            DESCRIPTION
                "vcg Laps Rx SAPI Check"
            ::= { ge8WanVcgLapsParaEntry 17 }

        ge8VcgLapsTxRxFcsMode  OBJECT-TYPE
            SYNTAX  INTEGER {
                    crc32(1),
                    crc16(2)
                }
            ACCESS  read-write
            STATUS  mandatory
            DESCRIPTION
                "vcg Laps Tx/Rx Payload FCS Mode"
            ::= { ge8WanVcgLapsParaEntry 18 }


--
-- ge8WanVcgBcpParaTable
--
        ge8WanVcgBcpParaTable  OBJECT-TYPE
            SYNTAX  SEQUENCE OF Ge8WanVcgBcpParaEntry
            ACCESS  not-accessible
            STATUS  mandatory
            DESCRIPTION
                "vcg Bcp parameter configuration"
            ::= { ge8VcgProfileSetup 5 }

        ge8WanVcgBcpParaEntry  OBJECT-TYPE
            SYNTAX  Ge8WanVcgBcpParaEntry
            ACCESS  not-accessible
            STATUS  mandatory
            DESCRIPTION
                "vcg Bcp parameter configuration entry"
            INDEX { ge8VcgBcpUnitIndex , ge8VcgBcpProfileIndex }
            ::= { ge8WanVcgBcpParaTable 1 }

        Ge8WanVcgBcpParaEntry ::= SEQUENCE {
            ge8VcgBcpUnitIndex             UnitID,
            ge8VcgBcpProfileIndex          INTEGER,
            ge8VcgBcpRxAddress             INTEGER,
            ge8VcgBcpTxAddress             INTEGER,
            ge8VcgBcpRxControl             INTEGER,
            ge8VcgBcpTxControl             INTEGER,
            ge8VcgBcpRxProtocolMsb         INTEGER,
            ge8VcgBcpTxProtocolMsb         INTEGER,
            ge8VcgBcpRxProtocolLsb         INTEGER,
            ge8VcgBcpTxProtocolLsb         INTEGER,
            ge8VcgBcpRxDescramble          INTEGER,
            ge8VcgBcpTxScramble            INTEGER,
            ge8VcgBcpRxPayloadFcsCheck     INTEGER,
            ge8VcgBcpTxPayloadFcsIns       INTEGER,
            ge8VcgBcpRxAddressCheck        INTEGER,
            ge8VcgBcpRxControlCheck        INTEGER,
            ge8VcgBcpRxProtocolCheck       INTEGER,
            ge8VcgBcpTxRxFcsMode           INTEGER,
            ge8VcgBcpRxBitF                INTEGER,
            ge8VcgBcpTxBitF                INTEGER,
            ge8VcgBcpRxBitZ                INTEGER,
            ge8VcgBcpTxBitZ                INTEGER,
            ge8VcgBcpRxPads                INTEGER,
            ge8VcgBcpTxPads                INTEGER,
            ge8VcgBcpRxMacType             INTEGER,
            ge8VcgBcpTxMacType             INTEGER,
            ge8VcgBcpRxBcpFlagCheck        INTEGER,
            ge8VcgBcpRxMacTypeCheck        INTEGER
        }

        ge8VcgBcpUnitIndex  OBJECT-TYPE
            SYNTAX  UnitID
            ACCESS  read-only
            STATUS  mandatory
            DESCRIPTION
                "vcg unit index: 1~8 "
            ::= { ge8WanVcgBcpParaEntry 1 }

        ge8VcgBcpProfileIndex  OBJECT-TYPE
            SYNTAX  INTEGER (1..8)
            ACCESS  read-only
            STATUS  mandatory
            DESCRIPTION
                "vcg port index "
            ::= { ge8WanVcgBcpParaEntry 2 }

        ge8VcgBcpRxAddress  OBJECT-TYPE
            SYNTAX  INTEGER (0..255)
            ACCESS  read-write
            STATUS  mandatory
            DESCRIPTION
                "vcg Bcp Rx Address"
            ::= { ge8WanVcgBcpParaEntry 3 }

        ge8VcgBcpTxAddress  OBJECT-TYPE
            SYNTAX  INTEGER (0..255)
            ACCESS  read-write
            STATUS  mandatory
            DESCRIPTION
                "vcg Bcp Tx Address"
            ::= { ge8WanVcgBcpParaEntry 4 }

        ge8VcgBcpRxControl  OBJECT-TYPE
            SYNTAX  INTEGER (0..255)
            ACCESS  read-write
            STATUS  mandatory
            DESCRIPTION
                "vcg Bcp Rx Control"
            ::= { ge8WanVcgBcpParaEntry 5 }

        ge8VcgBcpTxControl  OBJECT-TYPE
            SYNTAX  INTEGER (0..255)
            ACCESS  read-write
            STATUS  mandatory
            DESCRIPTION
                "vcg Bcp Tx Control"
            ::= { ge8WanVcgBcpParaEntry 6 }

        ge8VcgBcpRxProtocolMsb  OBJECT-TYPE
            SYNTAX  INTEGER (0..255)
            ACCESS  read-write
            STATUS  mandatory
            DESCRIPTION
                "vcg Bcp Rx Protocol MSB"
            ::= { ge8WanVcgBcpParaEntry 7 }

        ge8VcgBcpTxProtocolMsb  OBJECT-TYPE
            SYNTAX  INTEGER (0..255)
            ACCESS  read-write
            STATUS  mandatory
            DESCRIPTION
                "vcg Bcp Tx Protocol MSB"
            ::= { ge8WanVcgBcpParaEntry 8 }

        ge8VcgBcpRxProtocolLsb  OBJECT-TYPE
            SYNTAX  INTEGER (0..255)
            ACCESS  read-write
            STATUS  mandatory
            DESCRIPTION
                "vcg Bcp Rx Protocol LSB"
            ::= { ge8WanVcgBcpParaEntry 9 }

        ge8VcgBcpTxProtocolLsb  OBJECT-TYPE
            SYNTAX  INTEGER (0..255)
            ACCESS  read-write
            STATUS  mandatory
            DESCRIPTION
                "vcg Bcp Tx Protocol LSB"
            ::= { ge8WanVcgBcpParaEntry 10 }

        ge8VcgBcpRxDescramble  OBJECT-TYPE
            SYNTAX  INTEGER {
                    disable(1),
                    enable(2)
                }
            ACCESS  read-write
            STATUS  mandatory
            DESCRIPTION
                "vcg Bcp Rx Descramble"
            ::= { ge8WanVcgBcpParaEntry 11 }

        ge8VcgBcpTxScramble  OBJECT-TYPE
            SYNTAX  INTEGER {
                    disable(1),
                    enable(2)
                }
            ACCESS  read-write
            STATUS  mandatory
            DESCRIPTION
                "vcg Bcp Tx Scramble"
            ::= { ge8WanVcgBcpParaEntry 12 }

        ge8VcgBcpRxPayloadFcsCheck  OBJECT-TYPE
            SYNTAX  INTEGER {
                    disable(1),
                    enable(2)
                }
            ACCESS  read-write
            STATUS  mandatory
            DESCRIPTION
                "vcg Bcp Rx Payload FCS Check"
            ::= { ge8WanVcgBcpParaEntry 13 }

        ge8VcgBcpTxPayloadFcsIns  OBJECT-TYPE
            SYNTAX  INTEGER {
                    disable(1),
                    enable(2)
                }
            ACCESS  read-write
            STATUS  mandatory
            DESCRIPTION
                "vcg Bcp Tx Payload FCS Insert"
            ::= { ge8WanVcgBcpParaEntry 14 }

        ge8VcgBcpRxAddressCheck  OBJECT-TYPE
            SYNTAX  INTEGER {
                    disable(1),
                    enable(2)
                }
            ACCESS  read-write
            STATUS  mandatory
            DESCRIPTION
                "vcg Bcp Rx Address Check"
            ::= { ge8WanVcgBcpParaEntry 15 }

        ge8VcgBcpRxControlCheck  OBJECT-TYPE
            SYNTAX  INTEGER {
                    disable(1),
                    enable(2)
                }
            ACCESS  read-write
            STATUS  mandatory
            DESCRIPTION
                "vcg Bcp Rx Control Check"
            ::= { ge8WanVcgBcpParaEntry 16 }

        ge8VcgBcpRxProtocolCheck  OBJECT-TYPE
            SYNTAX  INTEGER {
                    disable(1),
                    enable(2)
                }
            ACCESS  read-write
            STATUS  mandatory
            DESCRIPTION
                "vcg Bcp Rx Protocol Check"
            ::= { ge8WanVcgBcpParaEntry 17 }

        ge8VcgBcpTxRxFcsMode  OBJECT-TYPE
            SYNTAX  INTEGER {
                    crc32(1),
                    crc16(2)
                }
            ACCESS  read-write
            STATUS  mandatory
            DESCRIPTION
                "vcg Bcp Tx/Rx Payload FCS Mode"
            ::= { ge8WanVcgBcpParaEntry 18 }

        ge8VcgBcpRxBitF  OBJECT-TYPE
            SYNTAX  INTEGER {
                    bit0(1),
                    bit1(2)
                }
            ACCESS  read-write
            STATUS  mandatory
            DESCRIPTION
                "vcg Bcp Rx Bit F"
            ::= { ge8WanVcgBcpParaEntry 19 }

        ge8VcgBcpTxBitF  OBJECT-TYPE
            SYNTAX  INTEGER {
                    bit0(1),
                    bit1(2)
                }
            ACCESS  read-write
            STATUS  mandatory
            DESCRIPTION
                "vcg Bcp Tx Bit F"
            ::= { ge8WanVcgBcpParaEntry 20 }

        ge8VcgBcpRxBitZ  OBJECT-TYPE
            SYNTAX  INTEGER {
                    bit0(1),
                    bit1(2)
                }
            ACCESS  read-write
            STATUS  mandatory
            DESCRIPTION
                "vcg Bcp Rx Bit Z"
            ::= { ge8WanVcgBcpParaEntry 21 }

        ge8VcgBcpTxBitZ  OBJECT-TYPE
            SYNTAX  INTEGER {
                    bit0(1),
                    bit1(2)
                }
            ACCESS  read-write
            STATUS  mandatory
            DESCRIPTION
                "vcg Bcp Tx Bit Z"
            ::= { ge8WanVcgBcpParaEntry 22 }

        ge8VcgBcpRxPads  OBJECT-TYPE
            SYNTAX  INTEGER (0..15)
            ACCESS  read-write
            STATUS  mandatory
            DESCRIPTION
                "vcg Bcp Rx Pads"
            ::= { ge8WanVcgBcpParaEntry 23 }

        ge8VcgBcpTxPads  OBJECT-TYPE
            SYNTAX  INTEGER (0..15)
            ACCESS  read-write
            STATUS  mandatory
            DESCRIPTION
                "vcg Bcp Tx Pads"
            ::= { ge8WanVcgBcpParaEntry 24 }

        ge8VcgBcpRxMacType  OBJECT-TYPE
            SYNTAX  INTEGER (0..255)
            ACCESS  read-write
            STATUS  mandatory
            DESCRIPTION
                "vcg Bcp Rx MAC Type"
            ::= { ge8WanVcgBcpParaEntry 25 }

        ge8VcgBcpTxMacType  OBJECT-TYPE
            SYNTAX  INTEGER (0..255)
            ACCESS  read-write
            STATUS  mandatory
            DESCRIPTION
                "vcg Bcp Tx MAC Type"
            ::= { ge8WanVcgBcpParaEntry 26 }

        ge8VcgBcpRxBcpFlagCheck  OBJECT-TYPE
            SYNTAX  INTEGER {
                    disable(1),
                    enable(2)
                }
            ACCESS  read-write
            STATUS  mandatory
            DESCRIPTION
                "vcg Bcp Rx BCP Flag Check"
            ::= { ge8WanVcgBcpParaEntry 27 }

        ge8VcgBcpRxMacTypeCheck  OBJECT-TYPE
            SYNTAX  INTEGER {
                    disable(1),
                    enable(2)
                }
            ACCESS  read-write
            STATUS  mandatory
            DESCRIPTION
                "vcg Bcp Rx MAC Type Check"
            ::= { ge8WanVcgBcpParaEntry 28 }


--
--  ge8LinkSetupGroup
--
    ge8LinkSetupGroup       OBJECT IDENTIFIER ::= { ge8EosCard 5 }


--
--  ge8LinkAlarmSetTable
--
        ge8LinkAlarmSetTable  OBJECT-TYPE
            SYNTAX  SEQUENCE OF  Ge8LinkAlarmSetEntry
            ACCESS  not-accessible
            STATUS  mandatory
            DESCRIPTION
                "The 8GESW  LinkDown Alarm Setup Table."
            ::= { ge8LinkSetupGroup 1 }

        ge8LinkAlarmSetEntry  OBJECT-TYPE
            SYNTAX  Ge8LinkAlarmSetEntry
            ACCESS  not-accessible
            STATUS  mandatory
            DESCRIPTION
                "An entry in The 8GESW  LinkDown Alarm Setup Table."
            INDEX { ge8LinkAlarmSetUnit , ge8LinkAlarmSetPort }
            ::= { ge8LinkAlarmSetTable 1 }

        Ge8LinkAlarmSetEntry ::= SEQUENCE {
            ge8LinkAlarmSetUnit        UnitID,
            ge8LinkAlarmSetPort        INTEGER,
            ge8LinkAlarmSetAlarm       INTEGER,
            ge8LinkAlarmSetRelay       INTEGER,
            ge8LinkAlarmSetSvrity      Severity
        }

        ge8LinkAlarmSetUnit  OBJECT-TYPE
            SYNTAX  UnitID
            ACCESS  read-only
            STATUS  mandatory
            DESCRIPTION
                "unit index"
            ::= { ge8LinkAlarmSetEntry 1 }

        ge8LinkAlarmSetPort  OBJECT-TYPE
            SYNTAX  INTEGER {
                    lan1(1),
                    lan2(2),
                    lan3(3),
                    lan4(4),
                    lan5(5),
                    lan6(6),
                    lan7(7),
                    lan8(8),
                    sfp(9)
                }
            ACCESS  read-only
            STATUS  mandatory
            DESCRIPTION
                "LAN port index"
            ::= { ge8LinkAlarmSetEntry 2 }

        ge8LinkAlarmSetAlarm  OBJECT-TYPE
            SYNTAX  INTEGER {
                    disable(1),
                    enable(2)
                }
            ACCESS  read-write
            STATUS  mandatory
            DESCRIPTION
                "LinkDown Alarm Mask"
            ::= { ge8LinkAlarmSetEntry 3 }

        ge8LinkAlarmSetRelay  OBJECT-TYPE
            SYNTAX  INTEGER {
                    disable(1),
                    enable(2)
                }
            ACCESS  read-write
            STATUS  mandatory
            DESCRIPTION
                "LinkDown Alarm Relay"
            ::= { ge8LinkAlarmSetEntry 4 }

        ge8LinkAlarmSetSvrity  OBJECT-TYPE
            SYNTAX  Severity
            ACCESS  read-write
            STATUS  mandatory
            DESCRIPTION
                "LinkDown Alarm Severity"
            ::= { ge8LinkAlarmSetEntry 5 }


--
--  ge8LinkConfigTable
--
        ge8LinkConfigTable  OBJECT-TYPE
            SYNTAX  SEQUENCE OF  Ge8LinkConfigEntry
            ACCESS  not-accessible
            STATUS  mandatory
            DESCRIPTION
                "The 8GESW  Link Config Table."
            ::= { ge8LinkSetupGroup 2 }

        ge8LinkConfigEntry  OBJECT-TYPE
            SYNTAX  Ge8LinkConfigEntry
            ACCESS  not-accessible
            STATUS  mandatory
            DESCRIPTION
                "An entry in The 8GESW  Link Config Table."
            INDEX { ge8LinkCfgUnit , ge8LinkCfgPort }
            ::= { ge8LinkConfigTable 1 }

        Ge8LinkConfigEntry ::= SEQUENCE {
            ge8LinkCfgUnit               UnitID,
            ge8LinkCfgPort               Ge8LanPort,
            ge8LinkCfgConfig             INTEGER
        }

        ge8LinkCfgUnit  OBJECT-TYPE
            SYNTAX  UnitID
            ACCESS  read-only
            STATUS  mandatory
            DESCRIPTION
                "unit index"
            ::= { ge8LinkConfigEntry 1 }

        ge8LinkCfgPort  OBJECT-TYPE
            SYNTAX  Ge8LanPort
            ACCESS  read-only
            STATUS  mandatory
            DESCRIPTION
                "LAN port index"
            ::= { ge8LinkConfigEntry 2 }

        ge8LinkCfgConfig  OBJECT-TYPE
            SYNTAX  INTEGER {
--                    powerDown(1),
                    autoNegotiation(2),
                    fullDuplex1000M(3),
--                    halfDuplex1000M(4),
                    fullDuplex100M(5),
                    halfDuplex100M(6),
                    fullDuplex10M(7),
                    halfDuplex10M(8),
                    optical100fx(9)
                }
            ACCESS  read-write
            STATUS  mandatory
            DESCRIPTION
                "Link Config"
            ::= { ge8LinkConfigEntry 3 }


--
--  ge8CustomInfoTable
--
        ge8CustomInfoTable  OBJECT-TYPE
            SYNTAX  SEQUENCE OF  Ge8CustomInfoEntry
            ACCESS  not-accessible
            STATUS  mandatory
            DESCRIPTION
                "The 8GESW  Customer Information Table."
            ::= { ge8LinkSetupGroup 3 }

        ge8CustomInfoEntry  OBJECT-TYPE
            SYNTAX  Ge8CustomInfoEntry
            ACCESS  not-accessible
            STATUS  mandatory
            DESCRIPTION
                "An entry in The 8GESW  Customer Information Table."
            INDEX { ge8CustomInfoUnit , ge8CustomInfoPort }
            ::= { ge8CustomInfoTable 1 }

        Ge8CustomInfoEntry ::= SEQUENCE {
            ge8CustomInfoUnit            UnitID,
            ge8CustomInfoPort            Ge8LanPort,
            ge8CustomInfoInformation     DisplayString
        }

        ge8CustomInfoUnit  OBJECT-TYPE
            SYNTAX  UnitID
            ACCESS  read-only
            STATUS  mandatory
            DESCRIPTION
                "unit index"
            ::= { ge8CustomInfoEntry 1 }

        ge8CustomInfoPort  OBJECT-TYPE
            SYNTAX  Ge8LanPort
            ACCESS  read-only
            STATUS  mandatory
            DESCRIPTION
                "LAN port index"
            ::= { ge8CustomInfoEntry 2 }

        ge8CustomInfoInformation  OBJECT-TYPE
            SYNTAX  DisplayString (SIZE (1..20))
            ACCESS  read-write
            STATUS  mandatory
            DESCRIPTION
                "Customer Information"
            ::= { ge8CustomInfoEntry 3 }


--
--  ge8FailPropagationTable
--
        ge8FailPropagationTable  OBJECT-TYPE
            SYNTAX  SEQUENCE OF  Ge8FailPropagationEntry
            ACCESS  not-accessible
            STATUS  mandatory
            DESCRIPTION
                "The 8GESW  Link fail propagation Table."
            ::= { ge8LinkSetupGroup 4 }

        ge8FailPropagationEntry  OBJECT-TYPE
            SYNTAX  Ge8FailPropagationEntry
            ACCESS  not-accessible
            STATUS  mandatory
            DESCRIPTION
                "An entry in The 8GESW  fail propagation Table."
            INDEX { ge8FailPropUnit }
            ::= { ge8FailPropagationTable 1 }

        Ge8FailPropagationEntry ::= SEQUENCE {
            ge8FailPropUnit              UnitID,
            ge8FailPropWanLost           INTEGER,
            ge8FailPropRemoteLinkDown    INTEGER,
            ge8FailPropRemoteGuard       INTEGER
        }

        ge8FailPropUnit  OBJECT-TYPE
            SYNTAX  UnitID
            ACCESS  read-only
            STATUS  mandatory
            DESCRIPTION
                "unit index"
            ::= { ge8FailPropagationEntry 1 }

        ge8FailPropWanLost  OBJECT-TYPE
            SYNTAX  INTEGER {
                    disable(1),
                    enable(2)
                }
            ACCESS  read-write
            STATUS  mandatory
            DESCRIPTION
                "WAN(VCG) Lost Propagation"
            ::= { ge8FailPropagationEntry 2 }

        ge8FailPropRemoteLinkDown  OBJECT-TYPE
            SYNTAX  INTEGER {
                    disable(1),
                    enable(2)
                }
            ACCESS  read-write
            STATUS  mandatory
            DESCRIPTION
                "Remote Link Down Propagation"
            ::= { ge8FailPropagationEntry 3 }

        ge8FailPropRemoteGuard  OBJECT-TYPE
            SYNTAX  INTEGER {
                    second1(1),
                    second2(2),
                    second3(3),
                    second4(4),
                    second5(5)
                }
            ACCESS  read-write
            STATUS  mandatory
            DESCRIPTION
                "Remote Link Down Guard Time"
            ::= { ge8FailPropagationEntry 4 }

--
--  ge8LinkIFGTable
--
        ge8LinkIFGTable  OBJECT-TYPE
            SYNTAX  SEQUENCE OF  Ge8LinkIFGEntry
            ACCESS  not-accessible
            STATUS  mandatory
            DESCRIPTION
                "The 8GESW  Link IFG Table."
            ::= { ge8LinkSetupGroup 5 }

        ge8LinkIFGEntry  OBJECT-TYPE
            SYNTAX  Ge8LinkIFGEntry
            ACCESS  not-accessible
            STATUS  mandatory
            DESCRIPTION
                "An entry in The 8GESW  Link IFG Table."
            INDEX { ge8LinkIFGUnit , ge8LinkIFGPort }
            ::= { ge8LinkIFGTable 1 }

        Ge8LinkIFGEntry ::= SEQUENCE {
            ge8LinkIFGUnit               UnitID,
            ge8LinkIFGPort               Ge8LanPort,
            ge8LinkIFGSize               INTEGER
        }

        ge8LinkIFGUnit  OBJECT-TYPE
            SYNTAX  UnitID
            ACCESS  read-only
            STATUS  mandatory
            DESCRIPTION
                "unit index"
            ::= { ge8LinkIFGEntry 1 }

        ge8LinkIFGPort  OBJECT-TYPE
            SYNTAX  Ge8LanPort
            ACCESS  read-only
            STATUS  mandatory
            DESCRIPTION
                "LAN port index"
            ::= { ge8LinkIFGEntry 2 }

        ge8LinkIFGSize  OBJECT-TYPE
            SYNTAX  INTEGER {
                    bitTimes80(1),
                    bitTimes88(2),
                    bitTimes96(3)
                }
            ACCESS  read-write
            STATUS  mandatory
            DESCRIPTION
                "Link IFG Size"
            ::= { ge8LinkIFGEntry 3 }


--
--  8GESW  ALS/APSD Setup Table
--
        ge8AlsSetupTable  OBJECT-TYPE
            SYNTAX  SEQUENCE OF Ge8AlsSetupEntry
            ACCESS  not-accessible
            STATUS  mandatory
            DESCRIPTION
                "Line ALS/APSD setup table"
            ::= { ge8LinkSetupGroup 6 }

        ge8AlsSetupEntry  OBJECT-TYPE
            SYNTAX  Ge8AlsSetupEntry
            ACCESS  not-accessible
            STATUS  mandatory
            DESCRIPTION
                "An entry in the line ALS/APSD setup table"
            INDEX { ge8AlsUnit }
            ::= { ge8AlsSetupTable 1 }

        Ge8AlsSetupEntry ::= SEQUENCE {
            ge8AlsUnit                 UnitID,
            ge8AlsEnable               INTEGER,
            ge8AlsPulseTime            INTEGER,
--            ge8AlsP1PowerDown          INTEGER,
--            ge8AlsP2PowerDown          INTEGER,
--            ge8AlsP3PowerDown          INTEGER,
--            ge8AlsP4PowerDown          INTEGER,
            ge8AlsP1ManualRestart      INTEGER,
            ge8AlsP2ManualRestart      INTEGER,
            ge8AlsP3ManualRestart      INTEGER,
            ge8AlsP4ManualRestart      INTEGER
        }

        ge8AlsUnit  OBJECT-TYPE
            SYNTAX  UnitID
            ACCESS  read-only
            STATUS  mandatory
            DESCRIPTION
                "unit 1 to 8."
            ::= { ge8AlsSetupEntry 1 }

        ge8AlsEnable  OBJECT-TYPE
            SYNTAX  INTEGER{
                    off(1),
                    on(2)
                }
            ACCESS  read-write
            STATUS  mandatory
            DESCRIPTION
                "8GESW  ALS enable setup"
            ::= { ge8AlsSetupEntry 2 }

        ge8AlsPulseTime  OBJECT-TYPE
            SYNTAX  INTEGER (60..300)
            ACCESS  read-write
            STATUS  mandatory
            DESCRIPTION
                "8GESW  ALS Pulse repetition time for automatic restart(sec) setup"
            ::= { ge8AlsSetupEntry 3 }

--        ge8AlsP1PowerDown  OBJECT-TYPE
--            SYNTAX  INTEGER{
--                    off(1),
--                    on(2)
--                }
--            ACCESS  read-write
--            STATUS  mandatory
--            DESCRIPTION
--                "8GESW  P1 power down setup"
--            ::= { ge8AlsSetupEntry 4 }
--
--        ge8AlsP2PowerDown  OBJECT-TYPE
--            SYNTAX  INTEGER{
--                    off(1),
--                    on(2)
--                }
--            ACCESS  read-write
--            STATUS  mandatory
--            DESCRIPTION
--                "8GESW  P2 power down setup"
--            ::= { ge8AlsSetupEntry 5 }
--
--        ge8AlsP3PowerDown  OBJECT-TYPE
--            SYNTAX  INTEGER{
--                    off(1),
--                    on(2)
--                }
--            ACCESS  read-write
--            STATUS  mandatory
--            DESCRIPTION
--                "8GESW  P3 power down setup"
--            ::= { ge8AlsSetupEntry 6 }
--
--        ge8AlsP4PowerDown  OBJECT-TYPE
--            SYNTAX  INTEGER{
--                    off(1),
--                    on(2)
--                }
--            ACCESS  read-write
--            STATUS  mandatory
--            DESCRIPTION
--                "8GESW  P4 power down setup"
--            ::= { ge8AlsSetupEntry 7 }

        ge8AlsP1ManualRestart  OBJECT-TYPE
            SYNTAX  INTEGER{
                    off(1),
                    on(2)
                }
            ACCESS  read-write
            STATUS  mandatory
            DESCRIPTION
                "8GESW  P1 ALS manual restart setup"
            ::= { ge8AlsSetupEntry 8 }

        ge8AlsP2ManualRestart  OBJECT-TYPE
            SYNTAX  INTEGER{
                    off(1),
                    on(2)
                }
            ACCESS  read-write
            STATUS  mandatory
            DESCRIPTION
                "8GESW  P2 ALS manual restart setup"
            ::= { ge8AlsSetupEntry 9 }

        ge8AlsP3ManualRestart  OBJECT-TYPE
            SYNTAX  INTEGER{
                    off(1),
                    on(2)
                }
            ACCESS  read-write
            STATUS  mandatory
            DESCRIPTION
                "8GESW  P3 ALS manual restart setup"
            ::= { ge8AlsSetupEntry 10 }

        ge8AlsP4ManualRestart  OBJECT-TYPE
            SYNTAX  INTEGER{
                    off(1),
                    on(2)
                }
            ACCESS  read-write
            STATUS  mandatory
            DESCRIPTION
                "8GESW  P4 ALS manual restart setup"
            ::= { ge8AlsSetupEntry 11 }



--
--  ge8AlarmStatusGroup
--
    ge8AlarmStatusGroup     OBJECT IDENTIFIER ::= { ge8EosCard 6 }


--
--  ge8HpStsAlmStatusTable
--
        ge8HpStsAlmStatusTable  OBJECT-TYPE
            SYNTAX  SEQUENCE OF  Ge8HpStsAlmStatusEntry
            ACCESS  not-accessible
            STATUS  mandatory
            DESCRIPTION
                "The 8GESW  HO-path/STS-path alm status table."
            ::= { ge8AlarmStatusGroup 1 }

        ge8HpStsAlmStatusEntry  OBJECT-TYPE
            SYNTAX  Ge8HpStsAlmStatusEntry
            ACCESS  not-accessible
            STATUS  mandatory
            DESCRIPTION
                "An entry in HO-path/STS-path alm status table."
            INDEX { ge8HpStsAlmStUnit , ge8HpStsAlmStPort , ge8HpStsAlmStChannel }
            ::= { ge8HpStsAlmStatusTable 1 }

        Ge8HpStsAlmStatusEntry ::= SEQUENCE {
            ge8HpStsAlmStUnit            UnitID,
            ge8HpStsAlmStPort            GeVcgNum,
            ge8HpStsAlmStChannel         ChannelNum,
            ge8HpStsAlmStLOP             AlmStatus,
            ge8HpStsAlmStAIS             AlmStatus,
            ge8HpStsAlmStUNEQ            AlmStatus,
            ge8HpStsAlmStRdiS            AlmStatus,
            ge8HpStsAlmStRdiC            AlmStatus,
            ge8HpStsAlmStRdiP            AlmStatus,
            ge8HpStsAlmStBIP             AlmStatus,
            ge8HpStsAlmStREI             AlmStatus
        }

        ge8HpStsAlmStUnit  OBJECT-TYPE
            SYNTAX  UnitID
            ACCESS  read-only
            STATUS  mandatory
            DESCRIPTION
                "unit index"
            ::= { ge8HpStsAlmStatusEntry 1 }

        ge8HpStsAlmStPort  OBJECT-TYPE
            SYNTAX  GeVcgNum
            ACCESS  read-only
            STATUS  mandatory
            DESCRIPTION
                "vcg port index"
            ::= { ge8HpStsAlmStatusEntry 2 }

        ge8HpStsAlmStChannel  OBJECT-TYPE
            SYNTAX  ChannelNum
            ACCESS  read-only
            STATUS  mandatory
            DESCRIPTION
                "Channel index"
            ::= { ge8HpStsAlmStatusEntry 3 }

        ge8HpStsAlmStLOP  OBJECT-TYPE
            SYNTAX  AlmStatus
            ACCESS  read-only
            STATUS  mandatory
            DESCRIPTION
                "Alarm Status"
            ::= { ge8HpStsAlmStatusEntry 4 }

        ge8HpStsAlmStAIS  OBJECT-TYPE
            SYNTAX  AlmStatus
            ACCESS  read-only
            STATUS  mandatory
            DESCRIPTION
                "Alarm Status"
            ::= { ge8HpStsAlmStatusEntry 5 }

        ge8HpStsAlmStUNEQ  OBJECT-TYPE
            SYNTAX  AlmStatus
            ACCESS  read-only
            STATUS  mandatory
            DESCRIPTION
                "Alarm Status"
            ::= { ge8HpStsAlmStatusEntry 6 }

        ge8HpStsAlmStRdiS  OBJECT-TYPE
            SYNTAX  AlmStatus
            ACCESS  read-only
            STATUS  mandatory
            DESCRIPTION
                "Alarm Status"
            ::= { ge8HpStsAlmStatusEntry 7 }

        ge8HpStsAlmStRdiC  OBJECT-TYPE
            SYNTAX  AlmStatus
            ACCESS  read-only
            STATUS  mandatory
            DESCRIPTION
                "Alarm Status"
            ::= { ge8HpStsAlmStatusEntry 8 }

        ge8HpStsAlmStRdiP  OBJECT-TYPE
            SYNTAX  AlmStatus
            ACCESS  read-only
            STATUS  mandatory
            DESCRIPTION
                "Alarm Status"
            ::= { ge8HpStsAlmStatusEntry 9 }

        ge8HpStsAlmStBIP  OBJECT-TYPE
            SYNTAX  AlmStatus
            ACCESS  read-only
            STATUS  mandatory
            DESCRIPTION
                "Alarm Status"
            ::= { ge8HpStsAlmStatusEntry 10 }

        ge8HpStsAlmStREI  OBJECT-TYPE
            SYNTAX  AlmStatus
            ACCESS  read-only
            STATUS  mandatory
            DESCRIPTION
                "Alarm Status"
            ::= { ge8HpStsAlmStatusEntry 11 }


--
--  ge8LpVtAlmStatusTable
--
        ge8LpVtAlmStatusTable  OBJECT-TYPE
            SYNTAX  SEQUENCE OF  Ge8LpVtAlmStatusEntry
            ACCESS  not-accessible
            STATUS  mandatory
            DESCRIPTION
                "The 8GESW  LO-path/VT-path alm status table."
            ::= { ge8AlarmStatusGroup 2 }

        ge8LpVtAlmStatusEntry  OBJECT-TYPE
            SYNTAX  Ge8LpVtAlmStatusEntry
            ACCESS  not-accessible
            STATUS  mandatory
            DESCRIPTION
                "An entry in LO-path/VT-path alm status table."
            INDEX { ge8LpVtAlmStUnit , ge8LpVtAlmStPort , ge8LpVtAlmStChannel }
            ::= { ge8LpVtAlmStatusTable 1 }

        Ge8LpVtAlmStatusEntry ::= SEQUENCE {
            ge8LpVtAlmStUnit             UnitID,
            ge8LpVtAlmStPort             GeVcgNum,
            ge8LpVtAlmStChannel          ChannelNum,
            ge8LpVtAlmStLOP              AlmStatus,
            ge8LpVtAlmStAIS              AlmStatus,
            ge8LpVtAlmStUNEQ             AlmStatus,
            ge8LpVtAlmStRdiS             AlmStatus,
            ge8LpVtAlmStRdiC             AlmStatus,
            ge8LpVtAlmStRdiP             AlmStatus,
            ge8LpVtAlmStBIP              AlmStatus,
            ge8LpVtAlmStREI              AlmStatus
        }

        ge8LpVtAlmStUnit  OBJECT-TYPE
            SYNTAX  UnitID
            ACCESS  read-only
            STATUS  mandatory
            DESCRIPTION
                "unit index"
            ::= { ge8LpVtAlmStatusEntry 1 }

        ge8LpVtAlmStPort  OBJECT-TYPE
            SYNTAX  GeVcgNum
            ACCESS  read-only
            STATUS  mandatory
            DESCRIPTION
                "vcg port index"
            ::= { ge8LpVtAlmStatusEntry 2 }

        ge8LpVtAlmStChannel  OBJECT-TYPE
            SYNTAX  ChannelNum
            ACCESS  read-only
            STATUS  mandatory
            DESCRIPTION
                "Channel index"
            ::= { ge8LpVtAlmStatusEntry 3 }

        ge8LpVtAlmStLOP  OBJECT-TYPE
            SYNTAX  AlmStatus
            ACCESS  read-only
            STATUS  mandatory
            DESCRIPTION
                "Alarm Status"
            ::= { ge8LpVtAlmStatusEntry 4 }

        ge8LpVtAlmStAIS  OBJECT-TYPE
            SYNTAX  AlmStatus
            ACCESS  read-only
            STATUS  mandatory
            DESCRIPTION
                "Alarm Status"
            ::= { ge8LpVtAlmStatusEntry 5 }

        ge8LpVtAlmStUNEQ  OBJECT-TYPE
            SYNTAX  AlmStatus
            ACCESS  read-only
            STATUS  mandatory
            DESCRIPTION
                "Alarm Status"
            ::= { ge8LpVtAlmStatusEntry 6 }

        ge8LpVtAlmStRdiS  OBJECT-TYPE
            SYNTAX  AlmStatus
            ACCESS  read-only
            STATUS  mandatory
            DESCRIPTION
                "Alarm Status"
            ::= { ge8LpVtAlmStatusEntry 7 }

        ge8LpVtAlmStRdiC  OBJECT-TYPE
            SYNTAX  AlmStatus
            ACCESS  read-only
            STATUS  mandatory
            DESCRIPTION
                "Alarm Status"
            ::= { ge8LpVtAlmStatusEntry 8 }

        ge8LpVtAlmStRdiP  OBJECT-TYPE
            SYNTAX  AlmStatus
            ACCESS  read-only
            STATUS  mandatory
            DESCRIPTION
                "Alarm Status"
            ::= { ge8LpVtAlmStatusEntry 9 }

        ge8LpVtAlmStBIP  OBJECT-TYPE
            SYNTAX  AlmStatus
            ACCESS  read-only
            STATUS  mandatory
            DESCRIPTION
                "Alarm Status"
            ::= { ge8LpVtAlmStatusEntry 10 }

        ge8LpVtAlmStREI  OBJECT-TYPE
            SYNTAX  AlmStatus
            ACCESS  read-only
            STATUS  mandatory
            DESCRIPTION
                "Alarm Status"
            ::= { ge8LpVtAlmStatusEntry 11 }


--
--  ge8LinkDownAlmStatTable
--
        ge8LinkDownAlmStatTable  OBJECT-TYPE
            SYNTAX  SEQUENCE OF  Ge8LinkDownAlmStatEntry
            ACCESS  not-accessible
            STATUS  mandatory
            DESCRIPTION
                "The 8GESW  LinkDown alm status table."
            ::= { ge8AlarmStatusGroup 3 }

        ge8LinkDownAlmStatEntry  OBJECT-TYPE
            SYNTAX  Ge8LinkDownAlmStatEntry
            ACCESS  not-accessible
            STATUS  mandatory
            DESCRIPTION
                "An entry in LinkDown alm status table."
            INDEX { ge8LinkDownAlmStUnit , ge8LinkDownAlmStPort }
            ::= { ge8LinkDownAlmStatTable 1 }

        Ge8LinkDownAlmStatEntry ::= SEQUENCE {
            ge8LinkDownAlmStUnit         UnitID,
            ge8LinkDownAlmStPort         Ge8LanPort,
            ge8LinkDownAlmStAlarm        AlmStatus
        }

        ge8LinkDownAlmStUnit  OBJECT-TYPE
            SYNTAX  UnitID
            ACCESS  read-only
            STATUS  mandatory
            DESCRIPTION
                "unit index"
            ::= { ge8LinkDownAlmStatEntry 1 }

        ge8LinkDownAlmStPort  OBJECT-TYPE
            SYNTAX  Ge8LanPort
            ACCESS  read-only
            STATUS  mandatory
            DESCRIPTION
                "LAN port index"
            ::= { ge8LinkDownAlmStatEntry 2 }

        ge8LinkDownAlmStAlarm  OBJECT-TYPE
            SYNTAX  AlmStatus
            ACCESS  read-only
            STATUS  mandatory
            DESCRIPTION
                "Alarm Status"
            ::= { ge8LinkDownAlmStatEntry 3 }


--
--  8GESW  Current Active Alarm Summary Table
--
        ge8CurrActAlmSumTable  OBJECT-TYPE
            SYNTAX  SEQUENCE OF Ge8CurrActAlmSumEntry
            ACCESS  not-accessible
            STATUS  mandatory
            DESCRIPTION
                "8GESW  Current Active Alarm Summary Table."
            ::= { ge8AlarmStatusGroup 4 }

        ge8CurrActAlmSumEntry  OBJECT-TYPE
            SYNTAX  Ge8CurrActAlmSumEntry
            ACCESS  not-accessible
            STATUS  mandatory
            DESCRIPTION
                "8GESW  current active alarm summary entry"
            INDEX { ge8AlmSumUnit , ge8AlmSumIndex }
            ::= { ge8CurrActAlmSumTable 1 }

        Ge8CurrActAlmSumEntry ::= SEQUENCE {
            ge8AlmSumUnit                UnitID,
            ge8AlmSumIndex               INTEGER,
            ge8AlmSumString              DisplayString,
            ge8AlmSumUnitNum             CardID,
            ge8AlmSumCardModel           CardModel,
            ge8AlmSumPortNum             GeCAASPortID,
            ge8AlmSumChannel             ChannelNum,
            ge8AlmSumAlmNum              AlarmNum,
            ge8AlmVC43STS31Type          Au4Au3Type,
            ge8AlmTU1xVTxType            Tu1xVtxType,
            ge8AlmSumStatus              AlmStatus,
            ge8AlmSumSeverity            Severity
        }

        ge8AlmSumUnit  OBJECT-TYPE
            SYNTAX  UnitID
            ACCESS  read-only
            STATUS  mandatory
            DESCRIPTION
                "Unit 1 to 8"
            ::= { ge8CurrActAlmSumEntry 1 }

        ge8AlmSumIndex  OBJECT-TYPE
            SYNTAX  INTEGER (1..999)
            ACCESS  read-only
            STATUS  mandatory
            DESCRIPTION
                "Select Alarm Summary Index"
            ::= { ge8CurrActAlmSumEntry 2 }

        ge8AlmSumString  OBJECT-TYPE
            SYNTAX  DisplayString
            ACCESS  read-only
            STATUS  mandatory
            DESCRIPTION
                "Alarm Summary String"
            ::= { ge8CurrActAlmSumEntry 3 }

        ge8AlmSumUnitNum  OBJECT-TYPE
            SYNTAX  CardID
            ACCESS  read-only
            STATUS  mandatory
            DESCRIPTION
                "Xcu or Unit 1~8"
            ::= { ge8CurrActAlmSumEntry 4 }

        ge8AlmSumCardModel  OBJECT-TYPE
            SYNTAX  CardModel
            ACCESS  read-only
            STATUS  mandatory
            DESCRIPTION
                "Card Model"
            ::= { ge8CurrActAlmSumEntry 5 }

        ge8AlmSumPortNum  OBJECT-TYPE
            SYNTAX  GeCAASPortID
            ACCESS  read-only
            STATUS  mandatory
            DESCRIPTION
                "vcg port index"
            ::= { ge8CurrActAlmSumEntry 6 }

        ge8AlmSumChannel  OBJECT-TYPE
            SYNTAX  ChannelNum
            ACCESS  read-only
            STATUS  mandatory
            DESCRIPTION
                "Channel index"
            ::= { ge8CurrActAlmSumEntry 7 }

        ge8AlmSumAlmNum  OBJECT-TYPE
            SYNTAX  AlarmNum
            ACCESS  read-only
            STATUS  mandatory
            DESCRIPTION
                "Alarm Num"
            ::= { ge8CurrActAlmSumEntry 8 }

        ge8AlmVC43STS31Type  OBJECT-TYPE
            SYNTAX  Au4Au3Type
            ACCESS  read-only
            STATUS  mandatory
            DESCRIPTION
                "AU4 or AU3 type"
            ::= { ge8CurrActAlmSumEntry 9 }

        ge8AlmTU1xVTxType  OBJECT-TYPE
            SYNTAX  Tu1xVtxType
            ACCESS  read-only
            STATUS  mandatory
            DESCRIPTION
                "Tu1x type"
            ::= { ge8CurrActAlmSumEntry 10 }

        ge8AlmSumStatus  OBJECT-TYPE
            SYNTAX  AlmStatus
            ACCESS  read-only
            STATUS  mandatory
            DESCRIPTION
                "The Status of Alarm"
            ::= { ge8CurrActAlmSumEntry 11 }

        ge8AlmSumSeverity  OBJECT-TYPE
            SYNTAX  Severity
            ACCESS  read-only
            STATUS  mandatory
            DESCRIPTION
                "Alarm Severity"
            ::= { ge8CurrActAlmSumEntry 12 }


--
-- ge8PerformanceGroup
--
    ge8PerformanceGroup     OBJECT IDENTIFIER ::= { ge8EosCard 7 }


--
-- ge8PerfThreshGroup
--
    ge8PerfThreshGroup      OBJECT IDENTIFIER ::= { ge8PerformanceGroup 1 }


--
-- ge8TcaMaskTable
--
        ge8TcaMaskTable  OBJECT-TYPE
            SYNTAX  SEQUENCE OF Ge8TcaMaskEntry
            ACCESS  not-accessible
            STATUS  mandatory
            DESCRIPTION
                "8GESW  performance TCA mask table"
            ::= { ge8PerfThreshGroup 1 }

        ge8TcaMaskEntry  OBJECT-TYPE
            SYNTAX  Ge8TcaMaskEntry
            ACCESS  not-accessible
            STATUS  mandatory
            DESCRIPTION
                "8GESW  performance TCA mask entry"
            INDEX { ge8TcaMaskUnit }
            ::= { ge8TcaMaskTable 1 }

        Ge8TcaMaskEntry ::= SEQUENCE {
            ge8TcaMaskUnit               UnitID,
            ge8TcaMaskHpSts              INTEGER,
            ge8TcaMaskFarEndHpSts        INTEGER,
            ge8TcaMaskLpVtV5             INTEGER,
            ge8TcaMaskFarEndLpVtV5       INTEGER,
            ge8TcaMaskLpVtB3             INTEGER,
            ge8TcaMaskFarEndLpVtB3       INTEGER
        }

        ge8TcaMaskUnit  OBJECT-TYPE
            SYNTAX  UnitID
            ACCESS  read-only
            STATUS  mandatory
            DESCRIPTION
                "unit index: 1~8 "
            ::= { ge8TcaMaskEntry 1 }

        ge8TcaMaskHpSts  OBJECT-TYPE
            SYNTAX  INTEGER {
                    disable(1),
                    enable(2)
                }
            ACCESS  read-write
            STATUS  mandatory
            DESCRIPTION
                "HP/STS TCA Mask"
            ::= { ge8TcaMaskEntry 2 }

        ge8TcaMaskFarEndHpSts  OBJECT-TYPE
            SYNTAX  INTEGER {
                    disable(1),
                    enable(2)
                }
            ACCESS  read-write
            STATUS  mandatory
            DESCRIPTION
                "FarEnd HP/STS TCA Mask"
            ::= { ge8TcaMaskEntry 3 }

        ge8TcaMaskLpVtV5  OBJECT-TYPE
            SYNTAX  INTEGER {
                    disable(1),
                    enable(2)
                }
            ACCESS  read-write
            STATUS  mandatory
            DESCRIPTION
                "LP/VT V5 TCA Mask"
            ::= { ge8TcaMaskEntry 4 }

        ge8TcaMaskFarEndLpVtV5  OBJECT-TYPE
            SYNTAX  INTEGER {
                    disable(1),
                    enable(2)
                }
            ACCESS  read-write
            STATUS  mandatory
            DESCRIPTION
                "FarEnd LP/VT V5 TCA Mask"
            ::= { ge8TcaMaskEntry 5 }

        ge8TcaMaskLpVtB3  OBJECT-TYPE
            SYNTAX  INTEGER {
                    disable(1),
                    enable(2)
                }
            ACCESS  read-write
            STATUS  mandatory
            DESCRIPTION
                "LP/VT B3 TCA Mask"
            ::= { ge8TcaMaskEntry 6 }

        ge8TcaMaskFarEndLpVtB3  OBJECT-TYPE
            SYNTAX  INTEGER {
                    disable(1),
                    enable(2)
                }
            ACCESS  read-write
            STATUS  mandatory
            DESCRIPTION
                "FarEnd LP/VT B3 TCA Mask"
            ::= { ge8TcaMaskEntry 7 }


--
-- ge8TcaSvrityTable
--
        ge8TcaSvrityTable  OBJECT-TYPE
            SYNTAX  SEQUENCE OF Ge8TcaSvrityEntry
            ACCESS  not-accessible
            STATUS  mandatory
            DESCRIPTION
                "8GESW  performance TCA severity table"
            ::= { ge8PerfThreshGroup 2 }

        ge8TcaSvrityEntry  OBJECT-TYPE
            SYNTAX  Ge8TcaSvrityEntry
            ACCESS  not-accessible
            STATUS  mandatory
            DESCRIPTION
                "8GESW  performance TCA severity entry"
            INDEX { ge8TcaSvrityUnit }
            ::= { ge8TcaSvrityTable 1 }

        Ge8TcaSvrityEntry ::= SEQUENCE {
            ge8TcaSvrityUnit             UnitID,
            ge8TcaSvrityHpSts            Severity,
            ge8TcaSvrityFarEndHpSts      Severity,
            ge8TcaSvrityLpVtV5           Severity,
            ge8TcaSvrityFarEndLpVtV5     Severity,
            ge8TcaSvrityLpVtB3           Severity,
            ge8TcaSvrityFarEndLpVtB3     Severity
        }

        ge8TcaSvrityUnit  OBJECT-TYPE
            SYNTAX  UnitID
            ACCESS  read-only
            STATUS  mandatory
            DESCRIPTION
                "unit index: 1~8 "
            ::= { ge8TcaSvrityEntry 1 }

        ge8TcaSvrityHpSts  OBJECT-TYPE
            SYNTAX  Severity
            ACCESS  read-write
            STATUS  mandatory
            DESCRIPTION
                "HP/STS TCA Severity"
            ::= { ge8TcaSvrityEntry 2 }

        ge8TcaSvrityFarEndHpSts  OBJECT-TYPE
            SYNTAX  Severity
            ACCESS  read-write
            STATUS  mandatory
            DESCRIPTION
                "FarEnd HP/STS TCA Severity"
            ::= { ge8TcaSvrityEntry 3 }

        ge8TcaSvrityLpVtV5  OBJECT-TYPE
            SYNTAX  Severity
            ACCESS  read-write
            STATUS  mandatory
            DESCRIPTION
                "LP/VT V5 TCA Severity"
            ::= { ge8TcaSvrityEntry 4 }

        ge8TcaSvrityFarEndLpVtV5  OBJECT-TYPE
            SYNTAX  Severity
            ACCESS  read-write
            STATUS  mandatory
            DESCRIPTION
                "FarEnd LP/VT V5 TCA Severity"
            ::= { ge8TcaSvrityEntry 5 }

        ge8TcaSvrityLpVtB3  OBJECT-TYPE
            SYNTAX  Severity
            ACCESS  read-write
            STATUS  mandatory
            DESCRIPTION
                "LP/VT B3 TCA Severity"
            ::= { ge8TcaSvrityEntry 6 }

        ge8TcaSvrityFarEndLpVtB3  OBJECT-TYPE
            SYNTAX  Severity
            ACCESS  read-write
            STATUS  mandatory
            DESCRIPTION
                "FarEnd LP/VT B3 TCA Severity"
            ::= { ge8TcaSvrityEntry 7 }


--
-- ge8TcaThreshTable
--
        ge8TcaThreshTable  OBJECT-TYPE
            SYNTAX  SEQUENCE OF Ge8TcaThreshEntry
            ACCESS  not-accessible
            STATUS  mandatory
            DESCRIPTION
                "8GESW  performance TCA threshold table"
            ::= { ge8PerfThreshGroup 3 }

        ge8TcaThreshEntry  OBJECT-TYPE
            SYNTAX  Ge8TcaThreshEntry
            ACCESS  not-accessible
            STATUS  mandatory
            DESCRIPTION
                "8GESW  performance TCA threshold entry"
            INDEX { ge8TcaThreshUnit }
            ::= { ge8TcaThreshTable 1 }

        Ge8TcaThreshEntry ::= SEQUENCE {
            ge8TcaThreshUnit             UnitID,
            ge8TcaThreshHpSts            INTEGER,
            ge8TcaThreshFarEndHpSts      INTEGER,
            ge8TcaThreshLpVtV5           INTEGER,
            ge8TcaThreshFarEndLpVtV5     INTEGER,
            ge8TcaThreshLpVtB3           INTEGER,
            ge8TcaThreshFarEndLpVtB3     INTEGER
        }

        ge8TcaThreshUnit  OBJECT-TYPE
            SYNTAX  UnitID
            ACCESS  read-only
            STATUS  mandatory
            DESCRIPTION
                "unit index: 1~8 "
            ::= { ge8TcaThreshEntry 1 }

        ge8TcaThreshHpSts  OBJECT-TYPE
            SYNTAX  INTEGER (1..99999)
            ACCESS  read-write
            STATUS  mandatory
            DESCRIPTION
                "HP/STS TCA Thresh"
            ::= { ge8TcaThreshEntry 2 }

        ge8TcaThreshFarEndHpSts  OBJECT-TYPE
            SYNTAX  INTEGER (1..99999)
            ACCESS  read-write
            STATUS  mandatory
            DESCRIPTION
                "FarEnd HP/STS TCA Thresh"
            ::= { ge8TcaThreshEntry 3 }

        ge8TcaThreshLpVtV5  OBJECT-TYPE
            SYNTAX  INTEGER (1..99999)
            ACCESS  read-write
            STATUS  mandatory
            DESCRIPTION
                "LP/VT V5 TCA Thresh"
            ::= { ge8TcaThreshEntry 4 }

        ge8TcaThreshFarEndLpVtV5  OBJECT-TYPE
            SYNTAX  INTEGER (1..99999)
            ACCESS  read-write
            STATUS  mandatory
            DESCRIPTION
                "FarEnd LP/VT V5 TCA Thresh"
            ::= { ge8TcaThreshEntry 5 }

        ge8TcaThreshLpVtB3  OBJECT-TYPE
            SYNTAX  INTEGER (1..99999)
            ACCESS  read-write
            STATUS  mandatory
            DESCRIPTION
                "LP/VT B3 TCA Thresh"
            ::= { ge8TcaThreshEntry 6 }

        ge8TcaThreshFarEndLpVtB3  OBJECT-TYPE
            SYNTAX  INTEGER (1..99999)
            ACCESS  read-write
            STATUS  mandatory
            DESCRIPTION
                "FarEnd LP/VT B3 TCA Thresh"
            ::= { ge8TcaThreshEntry 7 }


--
--  ge8PerfControlTable
--
        ge8PerfControlTable  OBJECT-TYPE
            SYNTAX  SEQUENCE OF  Ge8PerfControlEntry
            ACCESS  not-accessible
            STATUS  mandatory
            DESCRIPTION
                "8GESW  performance control table "
            ::= { ge8PerformanceGroup 2 }

        ge8PerfControlEntry  OBJECT-TYPE
            SYNTAX  Ge8PerfControlEntry
            ACCESS  not-accessible
            STATUS  mandatory
            DESCRIPTION
                "8GESW  performance control entry"
            INDEX { ge8PerfCtrlUnit }
            ::= { ge8PerfControlTable 1 }

        Ge8PerfControlEntry ::= SEQUENCE {
            ge8PerfCtrlUnit              UnitID,
            ge8PerfCtrlPerfClear         INTEGER
        }

        ge8PerfCtrlUnit  OBJECT-TYPE
            SYNTAX  UnitID
            ACCESS  read-only
            STATUS  mandatory
            DESCRIPTION
                "unit index"
            ::= { ge8PerfControlEntry 1 }

        ge8PerfCtrlPerfClear  OBJECT-TYPE
            SYNTAX  INTEGER {
                    no(1),
                    clear(2)
                }
            ACCESS  read-write
            STATUS  mandatory
            DESCRIPTION
                "Clear performance"
            ::= { ge8PerfControlEntry 2 }


--
--  ge8PerfDisplayGroup
--
    ge8PerfDisplayGroup     OBJECT IDENTIFIER ::= { ge8PerformanceGroup 3 }


--
--  ge8HpStsCurrTable
--
        ge8HpStsCurrTable  OBJECT-TYPE
            SYNTAX  SEQUENCE OF  Ge8HpStsCurrEntry
            ACCESS  not-accessible
            STATUS  mandatory
            DESCRIPTION
                "The 8GESW  B3 Current table."
            ::= { ge8PerfDisplayGroup 1 }

        ge8HpStsCurrEntry  OBJECT-TYPE
            SYNTAX  Ge8HpStsCurrEntry
            ACCESS  not-accessible
            STATUS  mandatory
            DESCRIPTION
                "An entry in the 8GESW  B3 Current table."
            INDEX { ge8HpStsCurrUnit , ge8HpStsCurrPort , ge8HpStsCurrChannel }
            ::= { ge8HpStsCurrTable 1 }

        Ge8HpStsCurrEntry ::= SEQUENCE {
            ge8HpStsCurrUnit             UnitID,
            ge8HpStsCurrPort             GeVcgNum,
            ge8HpStsCurrChannel          ChannelNum,
            ge8HpStsCurrEBs              Counter32,
            ge8HpStsCurrBBEs             Counter32,
            ge8HpStsCurrESs              Counter32,
            ge8HpStsCurrBESs             Counter32,
            ge8HpStsCurrSESs             Counter32,
            ge8HpStsCurrUASs             Counter32,
            ge8HpStsCurr24HValid15M      Counter32,
            ge8HpStsCurr7DayValidDay     Counter32,
            ge8HpStsCurr15MTimeElaps     Counter32,
            ge8HpStsCurrDayValid15M      Counter32
        }

        ge8HpStsCurrUnit  OBJECT-TYPE
            SYNTAX  UnitID
            ACCESS  read-only
            STATUS  mandatory
            DESCRIPTION
                "unit index"
            ::= { ge8HpStsCurrEntry 1 }

        ge8HpStsCurrPort  OBJECT-TYPE
            SYNTAX  GeVcgNum
            ACCESS  read-only
            STATUS  mandatory
            DESCRIPTION
                "vcg port index"
            ::= { ge8HpStsCurrEntry 2 }

        ge8HpStsCurrChannel  OBJECT-TYPE
            SYNTAX  ChannelNum
            ACCESS  read-only
            STATUS  mandatory
            DESCRIPTION
                "Channel index"
            ::= { ge8HpStsCurrEntry 3 }

        ge8HpStsCurrEBs  OBJECT-TYPE
            SYNTAX  Counter32
            ACCESS  read-only
            STATUS  mandatory
            DESCRIPTION
                "B3(BIP-8) Error Block"
            ::= { ge8HpStsCurrEntry 4 }

        ge8HpStsCurrBBEs  OBJECT-TYPE
            SYNTAX  Counter32
            ACCESS  read-only
            STATUS  mandatory
            DESCRIPTION
                "B3(BIP-8) Background Block Error"
            ::= { ge8HpStsCurrEntry 5 }

        ge8HpStsCurrESs  OBJECT-TYPE
            SYNTAX  Counter32
            ACCESS  read-only
            STATUS  mandatory
            DESCRIPTION
                "B3(BIP-8) Error Second"
            ::= { ge8HpStsCurrEntry 6 }

        ge8HpStsCurrBESs  OBJECT-TYPE
            SYNTAX  Counter32
            ACCESS  read-only
            STATUS  mandatory
            DESCRIPTION
                "B3(BIP-8) Background Error Second"
            ::= { ge8HpStsCurrEntry 7 }

        ge8HpStsCurrSESs  OBJECT-TYPE
            SYNTAX  Counter32
            ACCESS  read-only
            STATUS  mandatory
            DESCRIPTION
                "B3(BIP-8) Severly Error Second"
            ::= { ge8HpStsCurrEntry 8 }

        ge8HpStsCurrUASs  OBJECT-TYPE
            SYNTAX  Counter32
            ACCESS  read-only
            STATUS  mandatory
            DESCRIPTION
                "B3(BIP-8) Unavailable Second"
            ::= { ge8HpStsCurrEntry 9 }

        ge8HpStsCurr24HValid15M  OBJECT-TYPE
            SYNTAX  Counter32
            ACCESS  read-only
            STATUS  mandatory
            DESCRIPTION
                "B3(BIP-8) Valid 15-Min Interval"
            ::= { ge8HpStsCurrEntry 10 }

        ge8HpStsCurr7DayValidDay  OBJECT-TYPE
            SYNTAX  Counter32
            ACCESS  read-only
            STATUS  mandatory
            DESCRIPTION
                "B3(BIP-8) Valid 1-Day Interval"
            ::= { ge8HpStsCurrEntry 11 }

        ge8HpStsCurr15MTimeElaps  OBJECT-TYPE
            SYNTAX  Counter32
            ACCESS  read-only
            STATUS  mandatory
            DESCRIPTION
                "B3(BIP-8) Current 15-MIN Time Elapsed"
            ::= { ge8HpStsCurrEntry 12 }

        ge8HpStsCurrDayValid15M  OBJECT-TYPE
            SYNTAX  Counter32
            ACCESS  read-only
            STATUS  mandatory
            DESCRIPTION
                "B3(BIP-8) Current Day Time Elapsed"
            ::= { ge8HpStsCurrEntry 13 }


--
--  ge8HpStsIntvTable
--
        ge8HpStsIntvTable  OBJECT-TYPE
            SYNTAX  SEQUENCE OF  Ge8HpStsIntvEntry
            ACCESS  not-accessible
            STATUS  mandatory
            DESCRIPTION
                "The 8GESW  B3 Interval table."
            ::= { ge8PerfDisplayGroup 2 }

        ge8HpStsIntvEntry  OBJECT-TYPE
            SYNTAX  Ge8HpStsIntvEntry
            ACCESS  not-accessible
            STATUS  mandatory
            DESCRIPTION
                "An entry in the 8GESW  B3 Interval table."
            INDEX { ge8HpStsIntvUnit , ge8HpStsIntvPort ,
                    ge8HpStsIntvChannel , ge8HpStsIntvNumber }
            ::= { ge8HpStsIntvTable 1 }

        Ge8HpStsIntvEntry ::= SEQUENCE {
            ge8HpStsIntvUnit             UnitID,
            ge8HpStsIntvPort             GeVcgNum,
            ge8HpStsIntvChannel          ChannelNum,
            ge8HpStsIntvNumber           INTEGER,
            ge8HpStsIntvEBs              Counter32,
            ge8HpStsIntvBBEs             Counter32,
            ge8HpStsIntvESs              Counter32,
            ge8HpStsIntvBESs             Counter32,
            ge8HpStsIntvSESs             Counter32,
            ge8HpStsIntvUASs             Counter32
        }

        ge8HpStsIntvUnit  OBJECT-TYPE
            SYNTAX  UnitID
            ACCESS  read-only
            STATUS  mandatory
            DESCRIPTION
                "unit index"
            ::= { ge8HpStsIntvEntry 1 }

        ge8HpStsIntvPort  OBJECT-TYPE
            SYNTAX  GeVcgNum
            ACCESS  read-only
            STATUS  mandatory
            DESCRIPTION
                "vcg port index"
            ::= { ge8HpStsIntvEntry 2 }

        ge8HpStsIntvChannel  OBJECT-TYPE
            SYNTAX  ChannelNum
            ACCESS  read-only
            STATUS  mandatory
            DESCRIPTION
                "Channel index"
            ::= { ge8HpStsIntvEntry 3 }

        ge8HpStsIntvNumber  OBJECT-TYPE
            SYNTAX  INTEGER (1..96)
            ACCESS  read-only
            STATUS  mandatory
            DESCRIPTION
                "A number between 1 and 96"
            ::= { ge8HpStsIntvEntry 4 }

        ge8HpStsIntvEBs  OBJECT-TYPE
            SYNTAX  Counter32
            ACCESS  read-only
            STATUS  mandatory
            DESCRIPTION
                "B3(BIP-8) Error Block"
            ::= { ge8HpStsIntvEntry 5 }

        ge8HpStsIntvBBEs  OBJECT-TYPE
            SYNTAX  Counter32
            ACCESS  read-only
            STATUS  mandatory
            DESCRIPTION
                "B3(BIP-8) Background Block Error"
            ::= { ge8HpStsIntvEntry 6 }

        ge8HpStsIntvESs  OBJECT-TYPE
            SYNTAX  Counter32
            ACCESS  read-only
            STATUS  mandatory
            DESCRIPTION
                "B3(BIP-8) Error Second"
            ::= { ge8HpStsIntvEntry 7 }

        ge8HpStsIntvBESs  OBJECT-TYPE
            SYNTAX  Counter32
            ACCESS  read-only
            STATUS  mandatory
            DESCRIPTION
                "B3(BIP-8) Background Error Second"
            ::= { ge8HpStsIntvEntry 8 }

        ge8HpStsIntvSESs  OBJECT-TYPE
            SYNTAX  Counter32
            ACCESS  read-only
            STATUS  mandatory
            DESCRIPTION
                "B3(BIP-8) Severly Error Second"
            ::= { ge8HpStsIntvEntry 9 }

        ge8HpStsIntvUASs  OBJECT-TYPE
            SYNTAX  Counter32
            ACCESS  read-only
            STATUS  mandatory
            DESCRIPTION
                "B3(BIP-8) Unavailable Second"
            ::= { ge8HpStsIntvEntry 10 }


--
--  ge8HpSts7DaysTable
--
        ge8HpSts7DaysTable  OBJECT-TYPE
            SYNTAX  SEQUENCE OF  Ge8HpSts7DaysEntry
            ACCESS  not-accessible
            STATUS  mandatory
            DESCRIPTION
                "The 8GESW  B3 7 days table."
            ::= { ge8PerfDisplayGroup 3 }

        ge8HpSts7DaysEntry  OBJECT-TYPE
            SYNTAX  Ge8HpSts7DaysEntry
            ACCESS  not-accessible
            STATUS  mandatory
            DESCRIPTION
                "An entry in the 8GESW  B3 7 days table."
            INDEX { ge8HpSts7DaysUnit , ge8HpSts7DaysPort ,
                    ge8HpSts7DaysChannel , ge8HpSts7DaysNumber }
            ::= { ge8HpSts7DaysTable 1 }

        Ge8HpSts7DaysEntry ::= SEQUENCE {
            ge8HpSts7DaysUnit            UnitID,
            ge8HpSts7DaysPort            GeVcgNum,
            ge8HpSts7DaysChannel         ChannelNum,
            ge8HpSts7DaysNumber          INTEGER,
            ge8HpSts7DaysDate            DisplayString,
            ge8HpSts7DaysEBs             Counter32,
            ge8HpSts7DaysBBEs            Counter32,
            ge8HpSts7DaysESs             Counter32,
            ge8HpSts7DaysBESs            Counter32,
            ge8HpSts7DaysSESs            Counter32,
            ge8HpSts7DaysUASs            Counter32
        }

        ge8HpSts7DaysUnit  OBJECT-TYPE
            SYNTAX  UnitID
            ACCESS  read-only
            STATUS  mandatory
            DESCRIPTION
                "unit index"
            ::= { ge8HpSts7DaysEntry 1 }

        ge8HpSts7DaysPort  OBJECT-TYPE
            SYNTAX  GeVcgNum
            ACCESS  read-only
            STATUS  mandatory
            DESCRIPTION
                "vcg port index"
            ::= { ge8HpSts7DaysEntry 2 }

        ge8HpSts7DaysChannel  OBJECT-TYPE
            SYNTAX  ChannelNum
            ACCESS  read-only
            STATUS  mandatory
            DESCRIPTION
                "Channel index"
            ::= { ge8HpSts7DaysEntry 3 }

        ge8HpSts7DaysNumber  OBJECT-TYPE
            SYNTAX  INTEGER (1..7)
            ACCESS  read-only
            STATUS  mandatory
            DESCRIPTION
                "A number between 1 and 7"
            ::= { ge8HpSts7DaysEntry 4 }

        ge8HpSts7DaysDate  OBJECT-TYPE
            SYNTAX  DisplayString
            ACCESS  read-only
            STATUS  mandatory
            DESCRIPTION
                "Date"
            ::= { ge8HpSts7DaysEntry 5 }

        ge8HpSts7DaysEBs  OBJECT-TYPE
            SYNTAX  Counter32
            ACCESS  read-only
            STATUS  mandatory
            DESCRIPTION
                "B3(BIP-8) Error Block"
            ::= { ge8HpSts7DaysEntry 6 }

        ge8HpSts7DaysBBEs  OBJECT-TYPE
            SYNTAX  Counter32
            ACCESS  read-only
            STATUS  mandatory
            DESCRIPTION
                "B3(BIP-8) Background Block Error"
            ::= { ge8HpSts7DaysEntry 7 }

        ge8HpSts7DaysESs  OBJECT-TYPE
            SYNTAX  Counter32
            ACCESS  read-only
            STATUS  mandatory
            DESCRIPTION
                "B3(BIP-8) Error Second"
            ::= { ge8HpSts7DaysEntry 8 }

        ge8HpSts7DaysBESs  OBJECT-TYPE
            SYNTAX  Counter32
            ACCESS  read-only
            STATUS  mandatory
            DESCRIPTION
                "B3(BIP-8) Background Error Second"
            ::= { ge8HpSts7DaysEntry 9 }

        ge8HpSts7DaysSESs  OBJECT-TYPE
            SYNTAX  Counter32
            ACCESS  read-only
            STATUS  mandatory
            DESCRIPTION
                "B3(BIP-8) Severly Error Second"
            ::= { ge8HpSts7DaysEntry 10 }

        ge8HpSts7DaysUASs  OBJECT-TYPE
            SYNTAX  Counter32
            ACCESS  read-only
            STATUS  mandatory
            DESCRIPTION
                "B3(BIP-8) Unavailable Second"
            ::= { ge8HpSts7DaysEntry 11 }


--
--  ge8HpStsTotalTable
--
        ge8HpStsTotalTable  OBJECT-TYPE
            SYNTAX  SEQUENCE OF  Ge8HpStsTotalEntry
            ACCESS  not-accessible
            STATUS  mandatory
            DESCRIPTION
                "The 8GESW  B3 Total table."
            ::= { ge8PerfDisplayGroup 4 }

        ge8HpStsTotalEntry  OBJECT-TYPE
            SYNTAX  Ge8HpStsTotalEntry
            ACCESS  not-accessible
            STATUS  mandatory
            DESCRIPTION
                "An entry in the 8GESW  B3 Total table."
            INDEX { ge8HpStsTotalUnit , ge8HpStsTotalPort , ge8HpStsTotalChannel }
            ::= { ge8HpStsTotalTable 1 }

        Ge8HpStsTotalEntry ::= SEQUENCE {
            ge8HpStsTotalUnit            UnitID,
            ge8HpStsTotalPort            GeVcgNum,
            ge8HpStsTotalChannel         ChannelNum,
            ge8HpStsTotalEBs             Counter32,
            ge8HpStsTotalBBEs            Counter32,
            ge8HpStsTotalESs             Counter32,
            ge8HpStsTotalBESs            Counter32,
            ge8HpStsTotalSESs            Counter32,
            ge8HpStsTotalUASs            Counter32
        }

        ge8HpStsTotalUnit  OBJECT-TYPE
            SYNTAX  UnitID
            ACCESS  read-only
            STATUS  mandatory
            DESCRIPTION
                "unit index"
            ::= { ge8HpStsTotalEntry 1 }

        ge8HpStsTotalPort  OBJECT-TYPE
            SYNTAX  GeVcgNum
            ACCESS  read-only
            STATUS  mandatory
            DESCRIPTION
                "vcg port index"
            ::= { ge8HpStsTotalEntry 2 }

        ge8HpStsTotalChannel  OBJECT-TYPE
            SYNTAX  ChannelNum
            ACCESS  read-only
            STATUS  mandatory
            DESCRIPTION
                "Channel index"
            ::= { ge8HpStsTotalEntry 3 }

        ge8HpStsTotalEBs  OBJECT-TYPE
            SYNTAX  Counter32
            ACCESS  read-only
            STATUS  mandatory
            DESCRIPTION
                "B3(BIP-8) Error Block"
            ::= { ge8HpStsTotalEntry 4 }

        ge8HpStsTotalBBEs  OBJECT-TYPE
            SYNTAX  Counter32
            ACCESS  read-only
            STATUS  mandatory
            DESCRIPTION
                "B3(BIP-8) Background Block Error"
            ::= { ge8HpStsTotalEntry 5 }

        ge8HpStsTotalESs  OBJECT-TYPE
            SYNTAX  Counter32
            ACCESS  read-only
            STATUS  mandatory
            DESCRIPTION
                "B3(BIP-8) Error Second"
            ::= { ge8HpStsTotalEntry 6 }

        ge8HpStsTotalBESs  OBJECT-TYPE
            SYNTAX  Counter32
            ACCESS  read-only
            STATUS  mandatory
            DESCRIPTION
                "B3(BIP-8) Background Error Second"
            ::= { ge8HpStsTotalEntry 7 }

        ge8HpStsTotalSESs  OBJECT-TYPE
            SYNTAX  Counter32
            ACCESS  read-only
            STATUS  mandatory
            DESCRIPTION
                "B3(BIP-8) Severly Error Second"
            ::= { ge8HpStsTotalEntry 8 }

        ge8HpStsTotalUASs  OBJECT-TYPE
            SYNTAX  Counter32
            ACCESS  read-only
            STATUS  mandatory
            DESCRIPTION
                "B3(BIP-8) Unavailable Second"
            ::= { ge8HpStsTotalEntry 9 }


--
--  ge8FarEndHpStsCurrTable
--
        ge8FarEndHpStsCurrTable  OBJECT-TYPE
            SYNTAX  SEQUENCE OF  Ge8FarEndHpStsCurrEntry
            ACCESS  not-accessible
            STATUS  mandatory
            DESCRIPTION
                "The 8GESW  HP-REI/REI-P Current table."
            ::= { ge8PerfDisplayGroup 5 }

        ge8FarEndHpStsCurrEntry  OBJECT-TYPE
            SYNTAX  Ge8FarEndHpStsCurrEntry
            ACCESS  not-accessible
            STATUS  mandatory
            DESCRIPTION
                "An entry in the 8GESW  HP-REI/REI-P Current table."
            INDEX { ge8FrHpStsCurrUnit , ge8FrHpStsCurrPort , ge8FrHpStsCurrChannel }
            ::= { ge8FarEndHpStsCurrTable 1 }

        Ge8FarEndHpStsCurrEntry ::= SEQUENCE {
            ge8FrHpStsCurrUnit           UnitID,
            ge8FrHpStsCurrPort           GeVcgNum,
            ge8FrHpStsCurrChannel        ChannelNum,
            ge8FrHpStsCurrEBs            Counter32,
            ge8FrHpStsCurrBBEs           Counter32,
            ge8FrHpStsCurrESs            Counter32,
            ge8FrHpStsCurrBESs           Counter32,
            ge8FrHpStsCurrSESs           Counter32,
            ge8FrHpStsCurrUASs           Counter32,
            ge8FrHpStsCurr24HValid15M    Counter32,
            ge8FrHpStsCurr7DayValidDay   Counter32,
            ge8FrHpStsCurr15MTimeElaps   Counter32,
            ge8FrHpStsCurrDayValid15M    Counter32
        }

        ge8FrHpStsCurrUnit  OBJECT-TYPE
            SYNTAX  UnitID
            ACCESS  read-only
            STATUS  mandatory
            DESCRIPTION
                "unit index"
            ::= { ge8FarEndHpStsCurrEntry 1 }

        ge8FrHpStsCurrPort  OBJECT-TYPE
            SYNTAX  GeVcgNum
            ACCESS  read-only
            STATUS  mandatory
            DESCRIPTION
                "vcg port index"
            ::= { ge8FarEndHpStsCurrEntry 2 }

        ge8FrHpStsCurrChannel  OBJECT-TYPE
            SYNTAX  ChannelNum
            ACCESS  read-only
            STATUS  mandatory
            DESCRIPTION
                "Channel index"
            ::= { ge8FarEndHpStsCurrEntry 3 }

        ge8FrHpStsCurrEBs  OBJECT-TYPE
            SYNTAX  Counter32
            ACCESS  read-only
            STATUS  mandatory
            DESCRIPTION
                "HP-REI/REI-P(BIP-8) Error Block"
            ::= { ge8FarEndHpStsCurrEntry 4 }

        ge8FrHpStsCurrBBEs  OBJECT-TYPE
            SYNTAX  Counter32
            ACCESS  read-only
            STATUS  mandatory
            DESCRIPTION
                "HP-REI/REI-P(BIP-8) Background Block Error"
            ::= { ge8FarEndHpStsCurrEntry 5 }

        ge8FrHpStsCurrESs  OBJECT-TYPE
            SYNTAX  Counter32
            ACCESS  read-only
            STATUS  mandatory
            DESCRIPTION
                "HP-REI/REI-P(BIP-8) Error Second"
            ::= { ge8FarEndHpStsCurrEntry 6 }

        ge8FrHpStsCurrBESs  OBJECT-TYPE
            SYNTAX  Counter32
            ACCESS  read-only
            STATUS  mandatory
            DESCRIPTION
                "HP-REI/REI-P(BIP-8) Background Error Second"
            ::= { ge8FarEndHpStsCurrEntry 7 }

        ge8FrHpStsCurrSESs  OBJECT-TYPE
            SYNTAX  Counter32
            ACCESS  read-only
            STATUS  mandatory
            DESCRIPTION
                "HP-REI/REI-P(BIP-8) Severly Error Second"
            ::= { ge8FarEndHpStsCurrEntry 8 }

        ge8FrHpStsCurrUASs  OBJECT-TYPE
            SYNTAX  Counter32
            ACCESS  read-only
            STATUS  mandatory
            DESCRIPTION
                "HP-REI/REI-P(BIP-8) Unavailable Second"
            ::= { ge8FarEndHpStsCurrEntry 9 }

        ge8FrHpStsCurr24HValid15M  OBJECT-TYPE
            SYNTAX  Counter32
            ACCESS  read-only
            STATUS  mandatory
            DESCRIPTION
                "HP-REI/REI-P(BIP-8) Valid 15-Min Interval"
            ::= { ge8FarEndHpStsCurrEntry 10 }

        ge8FrHpStsCurr7DayValidDay  OBJECT-TYPE
            SYNTAX  Counter32
            ACCESS  read-only
            STATUS  mandatory
            DESCRIPTION
                "HP-REI/REI-P(BIP-8) Valid 1-Day Interval"
            ::= { ge8FarEndHpStsCurrEntry 11 }

        ge8FrHpStsCurr15MTimeElaps  OBJECT-TYPE
            SYNTAX  Counter32
            ACCESS  read-only
            STATUS  mandatory
            DESCRIPTION
                "HP-REI/REI-P(BIP-8) Current 15-MIN Time Elapsed"
            ::= { ge8FarEndHpStsCurrEntry 12 }

        ge8FrHpStsCurrDayValid15M  OBJECT-TYPE
            SYNTAX  Counter32
            ACCESS  read-only
            STATUS  mandatory
            DESCRIPTION
                "HP-REI/REI-P(BIP-8) Current Day Time Elapsed"
            ::= { ge8FarEndHpStsCurrEntry 13 }


--
--  ge8FarEndHpStsIntvTable Interval Table
--
        ge8FarEndHpStsIntvTable  OBJECT-TYPE
            SYNTAX  SEQUENCE OF  Ge8FarEndHpStsIntvEntry
            ACCESS  not-accessible
            STATUS  mandatory
            DESCRIPTION
                "The 8GESW  HP-REI/REI-P Interval table."
            ::= { ge8PerfDisplayGroup 6 }

        ge8FarEndHpStsIntvEntry  OBJECT-TYPE
            SYNTAX  Ge8FarEndHpStsIntvEntry
            ACCESS  not-accessible
            STATUS  mandatory
            DESCRIPTION
                "An entry in the 8GESW  HP-REI/REI-P Interval table."
            INDEX { ge8FrHpStsIntvUnit , ge8FrHpStsIntvPort ,
                    ge8FrHpStsIntvChannel , ge8FrHpStsIntvNumber }
            ::= { ge8FarEndHpStsIntvTable 1 }

        Ge8FarEndHpStsIntvEntry ::= SEQUENCE {
            ge8FrHpStsIntvUnit           UnitID,
            ge8FrHpStsIntvPort           GeVcgNum,
            ge8FrHpStsIntvChannel        ChannelNum,
            ge8FrHpStsIntvNumber         INTEGER,
            ge8FrHpStsIntvEBs            Counter32,
            ge8FrHpStsIntvBBEs           Counter32,
            ge8FrHpStsIntvESs            Counter32,
            ge8FrHpStsIntvBESs           Counter32,
            ge8FrHpStsIntvSESs           Counter32,
            ge8FrHpStsIntvUASs           Counter32
        }

        ge8FrHpStsIntvUnit  OBJECT-TYPE
            SYNTAX  UnitID
            ACCESS  read-only
            STATUS  mandatory
            DESCRIPTION
                "unit index"
            ::= { ge8FarEndHpStsIntvEntry 1 }

        ge8FrHpStsIntvPort  OBJECT-TYPE
            SYNTAX  GeVcgNum
            ACCESS  read-only
            STATUS  mandatory
            DESCRIPTION
                "vcg port index"
            ::= { ge8FarEndHpStsIntvEntry 2 }

        ge8FrHpStsIntvChannel  OBJECT-TYPE
            SYNTAX  ChannelNum
            ACCESS  read-only
            STATUS  mandatory
            DESCRIPTION
                "Channel index"
            ::= { ge8FarEndHpStsIntvEntry 3 }

        ge8FrHpStsIntvNumber  OBJECT-TYPE
            SYNTAX  INTEGER (1..96)
            ACCESS  read-only
            STATUS  mandatory
            DESCRIPTION
                "A number between 1 and 96"
            ::= { ge8FarEndHpStsIntvEntry 4 }

        ge8FrHpStsIntvEBs  OBJECT-TYPE
            SYNTAX  Counter32
            ACCESS  read-only
            STATUS  mandatory
            DESCRIPTION
                "HP-REI/REI-P(BIP-8) Error Block"
            ::= { ge8FarEndHpStsIntvEntry 5 }

        ge8FrHpStsIntvBBEs  OBJECT-TYPE
            SYNTAX  Counter32
            ACCESS  read-only
            STATUS  mandatory
            DESCRIPTION
                "HP-REI/REI-P(BIP-8) Background Block Error"
            ::= { ge8FarEndHpStsIntvEntry 6 }

        ge8FrHpStsIntvESs  OBJECT-TYPE
            SYNTAX  Counter32
            ACCESS  read-only
            STATUS  mandatory
            DESCRIPTION
                "HP-REI/REI-P(BIP-8) Error Second"
            ::= { ge8FarEndHpStsIntvEntry 7 }

        ge8FrHpStsIntvBESs  OBJECT-TYPE
            SYNTAX  Counter32
            ACCESS  read-only
            STATUS  mandatory
            DESCRIPTION
                "HP-REI/REI-P(BIP-8) Background Error Second"
            ::= { ge8FarEndHpStsIntvEntry 8 }

        ge8FrHpStsIntvSESs  OBJECT-TYPE
            SYNTAX  Counter32
            ACCESS  read-only
            STATUS  mandatory
            DESCRIPTION
                "HP-REI/REI-P(BIP-8) Severly Error Second"
            ::= { ge8FarEndHpStsIntvEntry 9 }

        ge8FrHpStsIntvUASs  OBJECT-TYPE
            SYNTAX  Counter32
            ACCESS  read-only
            STATUS  mandatory
            DESCRIPTION
                "HP-REI/REI-P(BIP-8) Unavailable Second"
            ::= { ge8FarEndHpStsIntvEntry 10 }


--
--  ge8FarEndHpSts7DaysTable
--
        ge8FarEndHpSts7DaysTable  OBJECT-TYPE
            SYNTAX  SEQUENCE OF  Ge8FarEndHpSts7DaysEntry
            ACCESS  not-accessible
            STATUS  mandatory
            DESCRIPTION
                "The 8GESW  HP-REI/REI-P 7 days table."
            ::= { ge8PerfDisplayGroup 7 }

        ge8FarEndHpSts7DaysEntry  OBJECT-TYPE
            SYNTAX  Ge8FarEndHpSts7DaysEntry
            ACCESS  not-accessible
            STATUS  mandatory
            DESCRIPTION
                "An entry in the 8GESW  HP-REI/REI-P 7 days table."
            INDEX { ge8FrHpSts7DaysUnit , ge8FrHpSts7DaysPort ,
                    ge8FrHpSts7DaysChannel , ge8FrHpSts7DaysNumber }
            ::= { ge8FarEndHpSts7DaysTable 1 }

        Ge8FarEndHpSts7DaysEntry ::= SEQUENCE {
            ge8FrHpSts7DaysUnit          UnitID,
            ge8FrHpSts7DaysPort          GeVcgNum,
            ge8FrHpSts7DaysChannel       ChannelNum,
            ge8FrHpSts7DaysNumber        INTEGER,
            ge8FrHpSts7DaysDate          DisplayString,
            ge8FrHpSts7DaysEBs           Counter32,
            ge8FrHpSts7DaysBBEs          Counter32,
            ge8FrHpSts7DaysESs           Counter32,
            ge8FrHpSts7DaysBESs          Counter32,
            ge8FrHpSts7DaysSESs          Counter32,
            ge8FrHpSts7DaysUASs          Counter32
        }

        ge8FrHpSts7DaysUnit  OBJECT-TYPE
            SYNTAX  UnitID
            ACCESS  read-only
            STATUS  mandatory
            DESCRIPTION
                "unit index"
            ::= { ge8FarEndHpSts7DaysEntry 1 }

        ge8FrHpSts7DaysPort  OBJECT-TYPE
            SYNTAX  GeVcgNum
            ACCESS  read-only
            STATUS  mandatory
            DESCRIPTION
                "vcg port index"
            ::= { ge8FarEndHpSts7DaysEntry 2 }

        ge8FrHpSts7DaysChannel  OBJECT-TYPE
            SYNTAX  ChannelNum
            ACCESS  read-only
            STATUS  mandatory
            DESCRIPTION
                "Channel index"
            ::= { ge8FarEndHpSts7DaysEntry 3 }

        ge8FrHpSts7DaysNumber  OBJECT-TYPE
            SYNTAX  INTEGER (1..7)
            ACCESS  read-only
            STATUS  mandatory
            DESCRIPTION
                "A number between 1 and 7"
            ::= { ge8FarEndHpSts7DaysEntry 4 }

        ge8FrHpSts7DaysDate  OBJECT-TYPE
            SYNTAX  DisplayString
            ACCESS  read-only
            STATUS  mandatory
            DESCRIPTION
                "Date"
            ::= { ge8FarEndHpSts7DaysEntry 5 }

        ge8FrHpSts7DaysEBs  OBJECT-TYPE
            SYNTAX  Counter32
            ACCESS  read-only
            STATUS  mandatory
            DESCRIPTION
                "HP-REI/REI-P(BIP-8) Error Block"
            ::= { ge8FarEndHpSts7DaysEntry 6 }

        ge8FrHpSts7DaysBBEs  OBJECT-TYPE
            SYNTAX  Counter32
            ACCESS  read-only
            STATUS  mandatory
            DESCRIPTION
                "HP-REI/REI-P(BIP-8) Background Block Error"
            ::= { ge8FarEndHpSts7DaysEntry 7 }

        ge8FrHpSts7DaysESs  OBJECT-TYPE
            SYNTAX  Counter32
            ACCESS  read-only
            STATUS  mandatory
            DESCRIPTION
                "HP-REI/REI-P(BIP-8) Error Second"
            ::= { ge8FarEndHpSts7DaysEntry 8 }

        ge8FrHpSts7DaysBESs  OBJECT-TYPE
            SYNTAX  Counter32
            ACCESS  read-only
            STATUS  mandatory
            DESCRIPTION
                "HP-REI/REI-P(BIP-8) Background Error Second"
            ::= { ge8FarEndHpSts7DaysEntry 9 }

        ge8FrHpSts7DaysSESs  OBJECT-TYPE
            SYNTAX  Counter32
            ACCESS  read-only
            STATUS  mandatory
            DESCRIPTION
                "HP-REI/REI-P(BIP-8) Severly Error Second"
            ::= { ge8FarEndHpSts7DaysEntry 10 }

        ge8FrHpSts7DaysUASs  OBJECT-TYPE
            SYNTAX  Counter32
            ACCESS  read-only
            STATUS  mandatory
            DESCRIPTION
                "HP-REI/REI-P(BIP-8) Unavailable Second"
            ::= { ge8FarEndHpSts7DaysEntry 11 }


--
--  ge8FarEndHpStsTotalTable
--
        ge8FarEndHpStsTotalTable  OBJECT-TYPE
            SYNTAX  SEQUENCE OF  Ge8FarEndHpStsTotalEntry
            ACCESS  not-accessible
            STATUS  mandatory
            DESCRIPTION
                "The 8GESW  HP-REI/REI-P Total table."
            ::= { ge8PerfDisplayGroup 8 }

        ge8FarEndHpStsTotalEntry  OBJECT-TYPE
            SYNTAX  Ge8FarEndHpStsTotalEntry
            ACCESS  not-accessible
            STATUS  mandatory
            DESCRIPTION
                "An entry in the 8GESW  HP-REI/REI-P Total table."
            INDEX { ge8FrHpStsTotalUnit , ge8FrHpStsTotalPort , ge8FrHpStsTotalChannel }
            ::= { ge8FarEndHpStsTotalTable 1 }

        Ge8FarEndHpStsTotalEntry ::= SEQUENCE {
            ge8FrHpStsTotalUnit          UnitID,
            ge8FrHpStsTotalPort          GeVcgNum,
            ge8FrHpStsTotalChannel       ChannelNum,
            ge8FrHpStsTotalEBs           Counter32,
            ge8FrHpStsTotalBBEs          Counter32,
            ge8FrHpStsTotalESs           Counter32,
            ge8FrHpStsTotalBESs          Counter32,
            ge8FrHpStsTotalSESs          Counter32,
            ge8FrHpStsTotalUASs          Counter32
        }

        ge8FrHpStsTotalUnit  OBJECT-TYPE
            SYNTAX  UnitID
            ACCESS  read-only
            STATUS  mandatory
            DESCRIPTION
                "unit index"
            ::= { ge8FarEndHpStsTotalEntry 1 }

        ge8FrHpStsTotalPort  OBJECT-TYPE
            SYNTAX  GeVcgNum
            ACCESS  read-only
            STATUS  mandatory
            DESCRIPTION
                "vcg port index"
            ::= { ge8FarEndHpStsTotalEntry 2 }

        ge8FrHpStsTotalChannel  OBJECT-TYPE
            SYNTAX  ChannelNum
            ACCESS  read-only
            STATUS  mandatory
            DESCRIPTION
                "Channel index"
            ::= { ge8FarEndHpStsTotalEntry 3 }

        ge8FrHpStsTotalEBs  OBJECT-TYPE
            SYNTAX  Counter32
            ACCESS  read-only
            STATUS  mandatory
            DESCRIPTION
                "HP-REI/REI-P(BIP-8) Error Block"
            ::= { ge8FarEndHpStsTotalEntry 4 }

        ge8FrHpStsTotalBBEs  OBJECT-TYPE
            SYNTAX  Counter32
            ACCESS  read-only
            STATUS  mandatory
            DESCRIPTION
                "HP-REI/REI-P(BIP-8) Background Block Error"
            ::= { ge8FarEndHpStsTotalEntry 5 }

        ge8FrHpStsTotalESs  OBJECT-TYPE
            SYNTAX  Counter32
            ACCESS  read-only
            STATUS  mandatory
            DESCRIPTION
                "HP-REI/REI-P(BIP-8) Error Second"
            ::= { ge8FarEndHpStsTotalEntry 6 }

        ge8FrHpStsTotalBESs  OBJECT-TYPE
            SYNTAX  Counter32
            ACCESS  read-only
            STATUS  mandatory
            DESCRIPTION
                "HP-REI/REI-P(BIP-8) Background Error Second"
            ::= { ge8FarEndHpStsTotalEntry 7 }

        ge8FrHpStsTotalSESs  OBJECT-TYPE
            SYNTAX  Counter32
            ACCESS  read-only
            STATUS  mandatory
            DESCRIPTION
                "HP-REI/REI-P(BIP-8) Severly Error Second"
            ::= { ge8FarEndHpStsTotalEntry 8 }

        ge8FrHpStsTotalUASs  OBJECT-TYPE
            SYNTAX  Counter32
            ACCESS  read-only
            STATUS  mandatory
            DESCRIPTION
                "HP-REI/REI-P(BIP-8) Unavailable Second"
            ::= { ge8FarEndHpStsTotalEntry 9 }


--
--  ge8LpVtCurrTable
--
        ge8LpVtCurrTable  OBJECT-TYPE
            SYNTAX  SEQUENCE OF  Ge8LpVtCurrEntry
            ACCESS  not-accessible
            STATUS  mandatory
            DESCRIPTION
                "The 8GESW  LP-BIP Current table."
            ::= { ge8PerfDisplayGroup 9 }

        ge8LpVtCurrEntry  OBJECT-TYPE
            SYNTAX  Ge8LpVtCurrEntry
            ACCESS  not-accessible
            STATUS  mandatory
            DESCRIPTION
                "An entry in the 8GESW  LP-BIP Current table."
            INDEX { ge8LpVtCurrUnit , ge8LpVtCurrPort , ge8LpVtCurrChannel }
            ::= { ge8LpVtCurrTable 1 }

        Ge8LpVtCurrEntry ::= SEQUENCE {
            ge8LpVtCurrUnit              UnitID,
            ge8LpVtCurrPort              GeVcgNum,
            ge8LpVtCurrChannel           ChannelNum,
            ge8LpVtCurrEBs               Counter32,
            ge8LpVtCurrBBEs              Counter32,
            ge8LpVtCurrESs               Counter32,
            ge8LpVtCurrBESs              Counter32,
            ge8LpVtCurrSESs              Counter32,
            ge8LpVtCurrUASs              Counter32,
            ge8LpVtCurr24HValid15M       Counter32,
            ge8LpVtCurr7DayValidDay      Counter32,
            ge8LpVtCurr15MTimeElaps      Counter32,
            ge8LpVtCurrDayValid15M       Counter32
        }

        ge8LpVtCurrUnit  OBJECT-TYPE
            SYNTAX  UnitID
            ACCESS  read-only
            STATUS  mandatory
            DESCRIPTION
                "unit index"
            ::= { ge8LpVtCurrEntry 1 }

        ge8LpVtCurrPort  OBJECT-TYPE
            SYNTAX  GeVcgNum
            ACCESS  read-only
            STATUS  mandatory
            DESCRIPTION
                "vcg port index"
            ::= { ge8LpVtCurrEntry 2 }

        ge8LpVtCurrChannel  OBJECT-TYPE
            SYNTAX  ChannelNum
            ACCESS  read-only
            STATUS  mandatory
            DESCRIPTION
                "Channel index"
            ::= { ge8LpVtCurrEntry 3 }

        ge8LpVtCurrEBs  OBJECT-TYPE
            SYNTAX  Counter32
            ACCESS  read-only
            STATUS  mandatory
            DESCRIPTION
                "LP-BIP Error Block"
            ::= { ge8LpVtCurrEntry 4 }

        ge8LpVtCurrBBEs  OBJECT-TYPE
            SYNTAX  Counter32
            ACCESS  read-only
            STATUS  mandatory
            DESCRIPTION
                "LP-BIP Background Block Error"
            ::= { ge8LpVtCurrEntry 5 }

        ge8LpVtCurrESs  OBJECT-TYPE
            SYNTAX  Counter32
            ACCESS  read-only
            STATUS  mandatory
            DESCRIPTION
                "LP-BIP Error Second"
            ::= { ge8LpVtCurrEntry 6 }

        ge8LpVtCurrBESs  OBJECT-TYPE
            SYNTAX  Counter32
            ACCESS  read-only
            STATUS  mandatory
            DESCRIPTION
                "LP-BIP Background Error Second"
            ::= { ge8LpVtCurrEntry 7 }

        ge8LpVtCurrSESs  OBJECT-TYPE
            SYNTAX  Counter32
            ACCESS  read-only
            STATUS  mandatory
            DESCRIPTION
                "LP-BIP Severly Error Second"
            ::= { ge8LpVtCurrEntry 8 }

        ge8LpVtCurrUASs  OBJECT-TYPE
            SYNTAX  Counter32
            ACCESS  read-only
            STATUS  mandatory
            DESCRIPTION
                "LP-BIP Unavailable Second"
            ::= { ge8LpVtCurrEntry 9 }

        ge8LpVtCurr24HValid15M  OBJECT-TYPE
            SYNTAX  Counter32
            ACCESS  read-only
            STATUS  mandatory
            DESCRIPTION
                "LP-BIP Valid 15-Min Interval"
            ::= { ge8LpVtCurrEntry 10 }

        ge8LpVtCurr7DayValidDay  OBJECT-TYPE
            SYNTAX  Counter32
            ACCESS  read-only
            STATUS  mandatory
            DESCRIPTION
                "LP-BIP Valid 1-Day Interval"
            ::= { ge8LpVtCurrEntry 11 }

        ge8LpVtCurr15MTimeElaps  OBJECT-TYPE
            SYNTAX  Counter32
            ACCESS  read-only
            STATUS  mandatory
            DESCRIPTION
                "LP-BIP Current 15-MIN Time Elapsed"
            ::= { ge8LpVtCurrEntry 12 }

        ge8LpVtCurrDayValid15M  OBJECT-TYPE
            SYNTAX  Counter32
            ACCESS  read-only
            STATUS  mandatory
            DESCRIPTION
                "LP-BIP Current Day Time Elapsed"
            ::= { ge8LpVtCurrEntry 13 }


--
--  ge8LpVtIntvTable
--
        ge8LpVtIntvTable  OBJECT-TYPE
            SYNTAX  SEQUENCE OF  Ge8LpVtIntvEntry
            ACCESS  not-accessible
            STATUS  mandatory
            DESCRIPTION
                "The 8GESW  LP-BIP Interval table."
            ::= { ge8PerfDisplayGroup 10 }

        ge8LpVtIntvEntry  OBJECT-TYPE
            SYNTAX  Ge8LpVtIntvEntry
            ACCESS  not-accessible
            STATUS  mandatory
            DESCRIPTION
                "An entry in the 8GESW  LP-BIP Interval table."
            INDEX { ge8LpVtIntvUnit , ge8LpVtIntvPort ,
                    ge8LpVtIntvChannel , ge8LpVtIntvNumber }
            ::= { ge8LpVtIntvTable 1 }

        Ge8LpVtIntvEntry ::= SEQUENCE {
            ge8LpVtIntvUnit              UnitID,
            ge8LpVtIntvPort              GeVcgNum,
            ge8LpVtIntvChannel           ChannelNum,
            ge8LpVtIntvNumber            INTEGER,
            ge8LpVtIntvEBs               Counter32,
            ge8LpVtIntvBBEs              Counter32,
            ge8LpVtIntvESs               Counter32,
            ge8LpVtIntvBESs              Counter32,
            ge8LpVtIntvSESs              Counter32,
            ge8LpVtIntvUASs              Counter32
        }

        ge8LpVtIntvUnit  OBJECT-TYPE
            SYNTAX  UnitID
            ACCESS  read-only
            STATUS  mandatory
            DESCRIPTION
                "unit index"
            ::= { ge8LpVtIntvEntry 1 }

        ge8LpVtIntvPort  OBJECT-TYPE
            SYNTAX  GeVcgNum
            ACCESS  read-only
            STATUS  mandatory
            DESCRIPTION
                "vcg port index"
            ::= { ge8LpVtIntvEntry 2 }

        ge8LpVtIntvChannel  OBJECT-TYPE
            SYNTAX  ChannelNum
            ACCESS  read-only
            STATUS  mandatory
            DESCRIPTION
                "Channel index"
            ::= { ge8LpVtIntvEntry 3 }

        ge8LpVtIntvNumber  OBJECT-TYPE
            SYNTAX  INTEGER (1..96)
            ACCESS  read-only
            STATUS  mandatory
            DESCRIPTION
                "A number between 1 and 96"
            ::= { ge8LpVtIntvEntry 4 }

        ge8LpVtIntvEBs  OBJECT-TYPE
            SYNTAX  Counter32
            ACCESS  read-only
            STATUS  mandatory
            DESCRIPTION
                "LP-BIP Error Block"
            ::= { ge8LpVtIntvEntry 5 }

        ge8LpVtIntvBBEs  OBJECT-TYPE
            SYNTAX  Counter32
            ACCESS  read-only
            STATUS  mandatory
            DESCRIPTION
                "LP-BIP Background Block Error"
            ::= { ge8LpVtIntvEntry 6 }

        ge8LpVtIntvESs  OBJECT-TYPE
            SYNTAX  Counter32
            ACCESS  read-only
            STATUS  mandatory
            DESCRIPTION
                "LP-BIP Error Second"
            ::= { ge8LpVtIntvEntry 7 }

        ge8LpVtIntvBESs  OBJECT-TYPE
            SYNTAX  Counter32
            ACCESS  read-only
            STATUS  mandatory
            DESCRIPTION
                "LP-BIP Background Error Second"
            ::= { ge8LpVtIntvEntry 8 }

        ge8LpVtIntvSESs  OBJECT-TYPE
            SYNTAX  Counter32
            ACCESS  read-only
            STATUS  mandatory
            DESCRIPTION
                "LP-BIP Severly Error Second"
            ::= { ge8LpVtIntvEntry 9 }

        ge8LpVtIntvUASs  OBJECT-TYPE
            SYNTAX  Counter32
            ACCESS  read-only
            STATUS  mandatory
            DESCRIPTION
                "LP-BIP Unavailable Second"
            ::= { ge8LpVtIntvEntry 10 }


--
--  ge8LpVt7DaysTable
--
        ge8LpVt7DaysTable  OBJECT-TYPE
            SYNTAX  SEQUENCE OF  Ge8LpVt7DaysEntry
            ACCESS  not-accessible
            STATUS  mandatory
            DESCRIPTION
                "The 8GESW  LP-BIP 7 days table."
            ::= { ge8PerfDisplayGroup 11 }

        ge8LpVt7DaysEntry  OBJECT-TYPE
            SYNTAX  Ge8LpVt7DaysEntry
            ACCESS  not-accessible
            STATUS  mandatory
            DESCRIPTION
                "An entry in the 8GESW  LP-BIP 7 days table."
            INDEX { ge8LpVt7DaysUnit , ge8LpVt7DaysPort ,
                    ge8LpVt7DaysChannel , ge8LpVt7DaysNumber }
            ::= { ge8LpVt7DaysTable 1 }

        Ge8LpVt7DaysEntry ::= SEQUENCE {
            ge8LpVt7DaysUnit             UnitID,
            ge8LpVt7DaysPort             GeVcgNum,
            ge8LpVt7DaysChannel          ChannelNum,
            ge8LpVt7DaysNumber           INTEGER,
            ge8LpVt7DaysDate             DisplayString,
            ge8LpVt7DaysEBs              Counter32,
            ge8LpVt7DaysBBEs             Counter32,
            ge8LpVt7DaysESs              Counter32,
            ge8LpVt7DaysBESs             Counter32,
            ge8LpVt7DaysSESs             Counter32,
            ge8LpVt7DaysUASs             Counter32
        }

        ge8LpVt7DaysUnit  OBJECT-TYPE
            SYNTAX  UnitID
            ACCESS  read-only
            STATUS  mandatory
            DESCRIPTION
                "unit index"
            ::= { ge8LpVt7DaysEntry 1 }

        ge8LpVt7DaysPort  OBJECT-TYPE
            SYNTAX  GeVcgNum
            ACCESS  read-only
            STATUS  mandatory
            DESCRIPTION
                "vcg port index"
            ::= { ge8LpVt7DaysEntry 2 }

        ge8LpVt7DaysChannel  OBJECT-TYPE
            SYNTAX  ChannelNum
            ACCESS  read-only
            STATUS  mandatory
            DESCRIPTION
                "Channel index"
            ::= { ge8LpVt7DaysEntry 3 }

        ge8LpVt7DaysNumber  OBJECT-TYPE
            SYNTAX  INTEGER (1..7)
            ACCESS  read-only
            STATUS  mandatory
            DESCRIPTION
                "A number between 1 and 7"
            ::= { ge8LpVt7DaysEntry 4 }

        ge8LpVt7DaysDate  OBJECT-TYPE
            SYNTAX  DisplayString
            ACCESS  read-only
            STATUS  mandatory
            DESCRIPTION
                "Date"
            ::= { ge8LpVt7DaysEntry 5 }

        ge8LpVt7DaysEBs  OBJECT-TYPE
            SYNTAX  Counter32
            ACCESS  read-only
            STATUS  mandatory
            DESCRIPTION
                "LP-BIP Error Block"
            ::= { ge8LpVt7DaysEntry 6 }

        ge8LpVt7DaysBBEs  OBJECT-TYPE
            SYNTAX  Counter32
            ACCESS  read-only
            STATUS  mandatory
            DESCRIPTION
                "LP-BIP Background Block Error"
            ::= { ge8LpVt7DaysEntry 7 }

        ge8LpVt7DaysESs  OBJECT-TYPE
            SYNTAX  Counter32
            ACCESS  read-only
            STATUS  mandatory
            DESCRIPTION
                "LP-BIP Error Second"
            ::= { ge8LpVt7DaysEntry 8 }

        ge8LpVt7DaysBESs  OBJECT-TYPE
            SYNTAX  Counter32
            ACCESS  read-only
            STATUS  mandatory
            DESCRIPTION
                "LP-BIP Background Error Second"
            ::= { ge8LpVt7DaysEntry 9 }

        ge8LpVt7DaysSESs  OBJECT-TYPE
            SYNTAX  Counter32
            ACCESS  read-only
            STATUS  mandatory
            DESCRIPTION
                "LP-BIP Severly Error Second"
            ::= { ge8LpVt7DaysEntry 10 }

        ge8LpVt7DaysUASs  OBJECT-TYPE
            SYNTAX  Counter32
            ACCESS  read-only
            STATUS  mandatory
            DESCRIPTION
                "LP-BIP Unavailable Second"
            ::= { ge8LpVt7DaysEntry 11 }


--
--  ge8LpVtTotalTable
--
        ge8LpVtTotalTable  OBJECT-TYPE
            SYNTAX  SEQUENCE OF  Ge8LpVtTotalEntry
            ACCESS  not-accessible
            STATUS  mandatory
            DESCRIPTION
                "The 8GESW  LP-BIP Total table."
            ::= { ge8PerfDisplayGroup 12 }

        ge8LpVtTotalEntry  OBJECT-TYPE
            SYNTAX  Ge8LpVtTotalEntry
            ACCESS  not-accessible
            STATUS  mandatory
            DESCRIPTION
                "An entry in the 8GESW  LP-BIP Total table."
            INDEX { ge8LpVtTotalUnit , ge8LpVtTotalPort , ge8LpVtTotalChannel }
            ::= { ge8LpVtTotalTable 1 }

        Ge8LpVtTotalEntry ::= SEQUENCE {
            ge8LpVtTotalUnit             UnitID,
            ge8LpVtTotalPort             GeVcgNum,
            ge8LpVtTotalChannel          ChannelNum,
            ge8LpVtTotalEBs              Counter32,
            ge8LpVtTotalBBEs             Counter32,
            ge8LpVtTotalESs              Counter32,
            ge8LpVtTotalBESs             Counter32,
            ge8LpVtTotalSESs             Counter32,
            ge8LpVtTotalUASs             Counter32
        }

        ge8LpVtTotalUnit  OBJECT-TYPE
            SYNTAX  UnitID
            ACCESS  read-only
            STATUS  mandatory
            DESCRIPTION
                "unit index"
            ::= { ge8LpVtTotalEntry 1 }

        ge8LpVtTotalPort  OBJECT-TYPE
            SYNTAX  GeVcgNum
            ACCESS  read-only
            STATUS  mandatory
            DESCRIPTION
                "vcg port index"
            ::= { ge8LpVtTotalEntry 2 }

        ge8LpVtTotalChannel  OBJECT-TYPE
            SYNTAX  ChannelNum
            ACCESS  read-only
            STATUS  mandatory
            DESCRIPTION
                "Channel index"
            ::= { ge8LpVtTotalEntry 3 }

        ge8LpVtTotalEBs  OBJECT-TYPE
            SYNTAX  Counter32
            ACCESS  read-only
            STATUS  mandatory
            DESCRIPTION
                "LP-BIP Error Block"
            ::= { ge8LpVtTotalEntry 4 }

        ge8LpVtTotalBBEs  OBJECT-TYPE
            SYNTAX  Counter32
            ACCESS  read-only
            STATUS  mandatory
            DESCRIPTION
                "LP-BIP Background Block Error"
            ::= { ge8LpVtTotalEntry 5 }

        ge8LpVtTotalESs  OBJECT-TYPE
            SYNTAX  Counter32
            ACCESS  read-only
            STATUS  mandatory
            DESCRIPTION
                "LP-BIP Error Second"
            ::= { ge8LpVtTotalEntry 6 }

        ge8LpVtTotalBESs  OBJECT-TYPE
            SYNTAX  Counter32
            ACCESS  read-only
            STATUS  mandatory
            DESCRIPTION
                "LP-BIP Background Error Second"
            ::= { ge8LpVtTotalEntry 7 }

        ge8LpVtTotalSESs  OBJECT-TYPE
            SYNTAX  Counter32
            ACCESS  read-only
            STATUS  mandatory
            DESCRIPTION
                "LP-BIP Severly Error Second"
            ::= { ge8LpVtTotalEntry 8 }

        ge8LpVtTotalUASs  OBJECT-TYPE
            SYNTAX  Counter32
            ACCESS  read-only
            STATUS  mandatory
            DESCRIPTION
                "LP-BIP Unavailable Second"
            ::= { ge8LpVtTotalEntry 9 }


--
--  ge8FarEndLpVtCurrTable
--
        ge8FarEndLpVtCurrTable  OBJECT-TYPE
            SYNTAX  SEQUENCE OF  Ge8FarEndLpVtCurrEntry
            ACCESS  not-accessible
            STATUS  mandatory
            DESCRIPTION
                "The 8GESW  LP-REI/REI-V Current table."
            ::= { ge8PerfDisplayGroup 13 }

        ge8FarEndLpVtCurrEntry  OBJECT-TYPE
            SYNTAX  Ge8FarEndLpVtCurrEntry
            ACCESS  not-accessible
            STATUS  mandatory
            DESCRIPTION
                "An entry in the 8GESW  LP-REI/REI-V Current table."
            INDEX { ge8FrLpVtCurrUnit , ge8FrLpVtCurrPort , ge8FrLpVtCurrChannel }
            ::= { ge8FarEndLpVtCurrTable 1 }

        Ge8FarEndLpVtCurrEntry ::= SEQUENCE {
            ge8FrLpVtCurrUnit            UnitID,
            ge8FrLpVtCurrPort            GeVcgNum,
            ge8FrLpVtCurrChannel         ChannelNum,
            ge8FrLpVtCurrEBs             Counter32,
            ge8FrLpVtCurrBBEs            Counter32,
            ge8FrLpVtCurrESs             Counter32,
            ge8FrLpVtCurrBESs            Counter32,
            ge8FrLpVtCurrSESs            Counter32,
            ge8FrLpVtCurrUASs            Counter32,
            ge8FrLpVtCurr24HValid15M     Counter32,
            ge8FrLpVtCurr7DayValidDay    Counter32,
            ge8FrLpVtCurr15MTimeElaps    Counter32,
            ge8FrLpVtCurrDayValid15M     Counter32
        }

        ge8FrLpVtCurrUnit  OBJECT-TYPE
            SYNTAX  UnitID
            ACCESS  read-only
            STATUS  mandatory
            DESCRIPTION
                "unit index"
            ::= { ge8FarEndLpVtCurrEntry 1 }

        ge8FrLpVtCurrPort  OBJECT-TYPE
            SYNTAX  GeVcgNum
            ACCESS  read-only
            STATUS  mandatory
            DESCRIPTION
                "vcg port index"
            ::= { ge8FarEndLpVtCurrEntry 2 }

        ge8FrLpVtCurrChannel  OBJECT-TYPE
            SYNTAX  ChannelNum
            ACCESS  read-only
            STATUS  mandatory
            DESCRIPTION
                "Channel index"
            ::= { ge8FarEndLpVtCurrEntry 3 }

        ge8FrLpVtCurrEBs  OBJECT-TYPE
            SYNTAX  Counter32
            ACCESS  read-only
            STATUS  mandatory
            DESCRIPTION
                "LP-REI/REI-V Error Block"
            ::= { ge8FarEndLpVtCurrEntry 4 }

        ge8FrLpVtCurrBBEs  OBJECT-TYPE
            SYNTAX  Counter32
            ACCESS  read-only
            STATUS  mandatory
            DESCRIPTION
                "LP-REI/REI-V Background Block Error"
            ::= { ge8FarEndLpVtCurrEntry 5 }

        ge8FrLpVtCurrESs  OBJECT-TYPE
            SYNTAX  Counter32
            ACCESS  read-only
            STATUS  mandatory
            DESCRIPTION
                "LP-REI/REI-V Error Second"
            ::= { ge8FarEndLpVtCurrEntry 6 }

        ge8FrLpVtCurrBESs  OBJECT-TYPE
            SYNTAX  Counter32
            ACCESS  read-only
            STATUS  mandatory
            DESCRIPTION
                "LP-REI/REI-V Background Error Second"
            ::= { ge8FarEndLpVtCurrEntry 7 }

        ge8FrLpVtCurrSESs  OBJECT-TYPE
            SYNTAX  Counter32
            ACCESS  read-only
            STATUS  mandatory
            DESCRIPTION
                "LP-REI/REI-V Severly Error Second"
            ::= { ge8FarEndLpVtCurrEntry 8 }

        ge8FrLpVtCurrUASs  OBJECT-TYPE
            SYNTAX  Counter32
            ACCESS  read-only
            STATUS  mandatory
            DESCRIPTION
                "LP-REI/REI-V Unavailable Second"
            ::= { ge8FarEndLpVtCurrEntry 9 }

        ge8FrLpVtCurr24HValid15M  OBJECT-TYPE
            SYNTAX  Counter32
            ACCESS  read-only
            STATUS  mandatory
            DESCRIPTION
                "LP-REI/REI-V Valid 15-Min Interval"
            ::= { ge8FarEndLpVtCurrEntry 10 }

        ge8FrLpVtCurr7DayValidDay  OBJECT-TYPE
            SYNTAX  Counter32
            ACCESS  read-only
            STATUS  mandatory
            DESCRIPTION
                "LP-REI/REI-V Valid 1-Day Interval"
            ::= { ge8FarEndLpVtCurrEntry 11 }

        ge8FrLpVtCurr15MTimeElaps  OBJECT-TYPE
            SYNTAX  Counter32
            ACCESS  read-only
            STATUS  mandatory
            DESCRIPTION
                "LP-REI/REI-V Current 15-MIN Time Elapsed"
            ::= { ge8FarEndLpVtCurrEntry 12 }

        ge8FrLpVtCurrDayValid15M  OBJECT-TYPE
            SYNTAX  Counter32
            ACCESS  read-only
            STATUS  mandatory
            DESCRIPTION
                "LP-REI/REI-V Current Day Time Elapsed"
            ::= { ge8FarEndLpVtCurrEntry 13 }


--
--  ge8FarEndLpVtIntvTable
--
        ge8FarEndLpVtIntvTable  OBJECT-TYPE
            SYNTAX  SEQUENCE OF  Ge8FarEndLpVtIntvEntry
            ACCESS  not-accessible
            STATUS  mandatory
            DESCRIPTION
                "The 8GESW  LP-REI/REI-V Interval table."
            ::= { ge8PerfDisplayGroup 14 }

        ge8FarEndLpVtIntvEntry  OBJECT-TYPE
            SYNTAX  Ge8FarEndLpVtIntvEntry
            ACCESS  not-accessible
            STATUS  mandatory
            DESCRIPTION
                "An entry in the 8GESW  LP-REI/REI-V Interval table."
            INDEX { ge8FrLpVtIntvUnit , ge8FrLpVtIntvPort ,
                    ge8FrLpVtIntvChannel , ge8FrLpVtIntvNumber }
            ::= { ge8FarEndLpVtIntvTable 1 }

        Ge8FarEndLpVtIntvEntry ::= SEQUENCE {
            ge8FrLpVtIntvUnit            UnitID,
            ge8FrLpVtIntvPort            GeVcgNum,
            ge8FrLpVtIntvChannel         ChannelNum,
            ge8FrLpVtIntvNumber          INTEGER,
            ge8FrLpVtIntvEBs             Counter32,
            ge8FrLpVtIntvBBEs            Counter32,
            ge8FrLpVtIntvESs             Counter32,
            ge8FrLpVtIntvBESs            Counter32,
            ge8FrLpVtIntvSESs            Counter32,
            ge8FrLpVtIntvUASs            Counter32
        }

        ge8FrLpVtIntvUnit  OBJECT-TYPE
            SYNTAX  UnitID
            ACCESS  read-only
            STATUS  mandatory
            DESCRIPTION
                "unit index"
            ::= { ge8FarEndLpVtIntvEntry 1 }

        ge8FrLpVtIntvPort  OBJECT-TYPE
            SYNTAX  GeVcgNum
            ACCESS  read-only
            STATUS  mandatory
            DESCRIPTION
                "vcg port index"
            ::= { ge8FarEndLpVtIntvEntry 2 }

        ge8FrLpVtIntvChannel  OBJECT-TYPE
            SYNTAX  ChannelNum
            ACCESS  read-only
            STATUS  mandatory
            DESCRIPTION
                "Channel index"
            ::= { ge8FarEndLpVtIntvEntry 3 }

        ge8FrLpVtIntvNumber  OBJECT-TYPE
            SYNTAX  INTEGER (1..96)
            ACCESS  read-only
            STATUS  mandatory
            DESCRIPTION
                "A number between 1 and 96"
            ::= { ge8FarEndLpVtIntvEntry 4 }

        ge8FrLpVtIntvEBs  OBJECT-TYPE
            SYNTAX  Counter32
            ACCESS  read-only
            STATUS  mandatory
            DESCRIPTION
                "LP-REI/REI-V Error Block"
            ::= { ge8FarEndLpVtIntvEntry 5 }

        ge8FrLpVtIntvBBEs  OBJECT-TYPE
            SYNTAX  Counter32
            ACCESS  read-only
            STATUS  mandatory
            DESCRIPTION
                "LP-REI/REI-V Background Block Error"
            ::= { ge8FarEndLpVtIntvEntry 6 }

        ge8FrLpVtIntvESs  OBJECT-TYPE
            SYNTAX  Counter32
            ACCESS  read-only
            STATUS  mandatory
            DESCRIPTION
                "LP-REI/REI-V Error Second"
            ::= { ge8FarEndLpVtIntvEntry 7 }

        ge8FrLpVtIntvBESs  OBJECT-TYPE
            SYNTAX  Counter32
            ACCESS  read-only
            STATUS  mandatory
            DESCRIPTION
                "LP-REI/REI-V Background Error Second"
            ::= { ge8FarEndLpVtIntvEntry 8 }

        ge8FrLpVtIntvSESs  OBJECT-TYPE
            SYNTAX  Counter32
            ACCESS  read-only
            STATUS  mandatory
            DESCRIPTION
                "LP-REI/REI-V Severly Error Second"
            ::= { ge8FarEndLpVtIntvEntry 9 }

        ge8FrLpVtIntvUASs  OBJECT-TYPE
            SYNTAX  Counter32
            ACCESS  read-only
            STATUS  mandatory
            DESCRIPTION
                "LP-REI/REI-V Unavailable Second"
            ::= { ge8FarEndLpVtIntvEntry 10 }


--
--  ge8FarEndLpVt7DaysTable
--
        ge8FarEndLpVt7DaysTable  OBJECT-TYPE
            SYNTAX  SEQUENCE OF  Ge8FarEndLpVt7DaysEntry
            ACCESS  not-accessible
            STATUS  mandatory
            DESCRIPTION
                "The 8GESW  LP-REI/REI-V 7 days table."
            ::= { ge8PerfDisplayGroup 15 }

        ge8FarEndLpVt7DaysEntry  OBJECT-TYPE
            SYNTAX  Ge8FarEndLpVt7DaysEntry
            ACCESS  not-accessible
            STATUS  mandatory
            DESCRIPTION
                "An entry in the 8GESW  LP-REI/REI-V 7 days table."
            INDEX { ge8FrLpVt7DaysUnit , ge8FrLpVt7DaysPort ,
                    ge8FrLpVt7DaysChannel , ge8FrLpVt7DaysNumber }
            ::= { ge8FarEndLpVt7DaysTable 1 }

        Ge8FarEndLpVt7DaysEntry ::= SEQUENCE {
            ge8FrLpVt7DaysUnit           UnitID,
            ge8FrLpVt7DaysPort           GeVcgNum,
            ge8FrLpVt7DaysChannel        ChannelNum,
            ge8FrLpVt7DaysNumber         INTEGER,
            ge8FrLpVt7DaysDate           DisplayString,
            ge8FrLpVt7DaysEBs            Counter32,
            ge8FrLpVt7DaysBBEs           Counter32,
            ge8FrLpVt7DaysESs            Counter32,
            ge8FrLpVt7DaysBESs           Counter32,
            ge8FrLpVt7DaysSESs           Counter32,
            ge8FrLpVt7DaysUASs           Counter32
        }

        ge8FrLpVt7DaysUnit  OBJECT-TYPE
            SYNTAX  UnitID
            ACCESS  read-only
            STATUS  mandatory
            DESCRIPTION
                "unit index"
            ::= { ge8FarEndLpVt7DaysEntry 1 }

        ge8FrLpVt7DaysPort  OBJECT-TYPE
            SYNTAX  GeVcgNum
            ACCESS  read-only
            STATUS  mandatory
            DESCRIPTION
                "vcg port index"
            ::= { ge8FarEndLpVt7DaysEntry 2 }

        ge8FrLpVt7DaysChannel  OBJECT-TYPE
            SYNTAX  ChannelNum
            ACCESS  read-only
            STATUS  mandatory
            DESCRIPTION
                "Channel index"
            ::= { ge8FarEndLpVt7DaysEntry 3 }

        ge8FrLpVt7DaysNumber  OBJECT-TYPE
            SYNTAX  INTEGER (1..7)
            ACCESS  read-only
            STATUS  mandatory
            DESCRIPTION
                "A number between 1 and 7"
            ::= { ge8FarEndLpVt7DaysEntry 4 }

        ge8FrLpVt7DaysDate  OBJECT-TYPE
            SYNTAX  DisplayString
            ACCESS  read-only
            STATUS  mandatory
            DESCRIPTION
                "Date"
            ::= { ge8FarEndLpVt7DaysEntry 5 }

        ge8FrLpVt7DaysEBs  OBJECT-TYPE
            SYNTAX  Counter32
            ACCESS  read-only
            STATUS  mandatory
            DESCRIPTION
                "LP-REI/REI-V Error Block"
            ::= { ge8FarEndLpVt7DaysEntry 6 }

        ge8FrLpVt7DaysBBEs  OBJECT-TYPE
            SYNTAX  Counter32
            ACCESS  read-only
            STATUS  mandatory
            DESCRIPTION
                "LP-REI/REI-V Background Block Error"
            ::= { ge8FarEndLpVt7DaysEntry 7 }

        ge8FrLpVt7DaysESs  OBJECT-TYPE
            SYNTAX  Counter32
            ACCESS  read-only
            STATUS  mandatory
            DESCRIPTION
                "LP-REI/REI-V Error Second"
            ::= { ge8FarEndLpVt7DaysEntry 8 }

        ge8FrLpVt7DaysBESs  OBJECT-TYPE
            SYNTAX  Counter32
            ACCESS  read-only
            STATUS  mandatory
            DESCRIPTION
                "LP-REI/REI-V Background Error Second"
            ::= { ge8FarEndLpVt7DaysEntry 9 }

        ge8FrLpVt7DaysSESs  OBJECT-TYPE
            SYNTAX  Counter32
            ACCESS  read-only
            STATUS  mandatory
            DESCRIPTION
                "LP-REI/REI-V Severly Error Second"
            ::= { ge8FarEndLpVt7DaysEntry 10 }

        ge8FrLpVt7DaysUASs  OBJECT-TYPE
            SYNTAX  Counter32
            ACCESS  read-only
            STATUS  mandatory
            DESCRIPTION
                "LP-REI/REI-V Unavailable Second"
            ::= { ge8FarEndLpVt7DaysEntry 11 }


--
--  ge8FarEndLpVtTotalTable
--
        ge8FarEndLpVtTotalTable  OBJECT-TYPE
            SYNTAX  SEQUENCE OF  Ge8FarEndLpVtTotalEntry
            ACCESS  not-accessible
            STATUS  mandatory
            DESCRIPTION
                "The 8GESW  LP-REI/REI-V Total table."
            ::= { ge8PerfDisplayGroup 16 }

        ge8FarEndLpVtTotalEntry  OBJECT-TYPE
            SYNTAX  Ge8FarEndLpVtTotalEntry
            ACCESS  not-accessible
            STATUS  mandatory
            DESCRIPTION
                "An entry in the 8GESW  LP-REI/REI-V Total table."
            INDEX { ge8FrLpVtTotalUnit , ge8FrLpVtTotalPort , ge8FrLpVtTotalChannel }
            ::= { ge8FarEndLpVtTotalTable 1 }

        Ge8FarEndLpVtTotalEntry ::= SEQUENCE {
            ge8FrLpVtTotalUnit           UnitID,
            ge8FrLpVtTotalPort           GeVcgNum,
            ge8FrLpVtTotalChannel        ChannelNum,
            ge8FrLpVtTotalEBs            Counter32,
            ge8FrLpVtTotalBBEs           Counter32,
            ge8FrLpVtTotalESs            Counter32,
            ge8FrLpVtTotalBESs           Counter32,
            ge8FrLpVtTotalSESs           Counter32,
            ge8FrLpVtTotalUASs           Counter32
        }

        ge8FrLpVtTotalUnit  OBJECT-TYPE
            SYNTAX  UnitID
            ACCESS  read-only
            STATUS  mandatory
            DESCRIPTION
                "unit index"
            ::= { ge8FarEndLpVtTotalEntry 1 }

        ge8FrLpVtTotalPort  OBJECT-TYPE
            SYNTAX  GeVcgNum
            ACCESS  read-only
            STATUS  mandatory
            DESCRIPTION
                "vcg port index"
            ::= { ge8FarEndLpVtTotalEntry 2 }

        ge8FrLpVtTotalChannel  OBJECT-TYPE
            SYNTAX  ChannelNum
            ACCESS  read-only
            STATUS  mandatory
            DESCRIPTION
                "Channel index"
            ::= { ge8FarEndLpVtTotalEntry 3 }

        ge8FrLpVtTotalEBs  OBJECT-TYPE
            SYNTAX  Counter32
            ACCESS  read-only
            STATUS  mandatory
            DESCRIPTION
                "LP-REI/REI-V Error Block"
            ::= { ge8FarEndLpVtTotalEntry 4 }

        ge8FrLpVtTotalBBEs  OBJECT-TYPE
            SYNTAX  Counter32
            ACCESS  read-only
            STATUS  mandatory
            DESCRIPTION
                "LP-REI/REI-V Background Block Error"
            ::= { ge8FarEndLpVtTotalEntry 5 }

        ge8FrLpVtTotalESs  OBJECT-TYPE
            SYNTAX  Counter32
            ACCESS  read-only
            STATUS  mandatory
            DESCRIPTION
                "LP-REI/REI-V Error Second"
            ::= { ge8FarEndLpVtTotalEntry 6 }

        ge8FrLpVtTotalBESs  OBJECT-TYPE
            SYNTAX  Counter32
            ACCESS  read-only
            STATUS  mandatory
            DESCRIPTION
                "LP-REI/REI-V Background Error Second"
            ::= { ge8FarEndLpVtTotalEntry 7 }

        ge8FrLpVtTotalSESs  OBJECT-TYPE
            SYNTAX  Counter32
            ACCESS  read-only
            STATUS  mandatory
            DESCRIPTION
                "LP-REI/REI-V Severly Error Second"
            ::= { ge8FarEndLpVtTotalEntry 8 }

        ge8FrLpVtTotalUASs  OBJECT-TYPE
            SYNTAX  Counter32
            ACCESS  read-only
            STATUS  mandatory
            DESCRIPTION
                "LP-REI/REI-V Unavailable Second"
            ::= { ge8FarEndLpVtTotalEntry 9 }


--
--  ge8WanVcgStatistic
--
    ge8WanVcgStatistic    OBJECT IDENTIFIER ::= { ge8EosCard 8 }


--
--  ge8GfpStatisticTable
--
        ge8GfpStatisticTable  OBJECT-TYPE
            SYNTAX  SEQUENCE OF  Ge8GfpStatisticEntry
            ACCESS  not-accessible
            STATUS  mandatory
            DESCRIPTION
                "The 8GESW  wan(vcg) GFP statistic table."
            ::= { ge8WanVcgStatistic 1 }

        ge8GfpStatisticEntry  OBJECT-TYPE
            SYNTAX  Ge8GfpStatisticEntry
            ACCESS  not-accessible
            STATUS  mandatory
            DESCRIPTION
                "An entry in the 8GESW  wan(vcg) GFP statistic table."
            INDEX { ge8GfpStUnit , ge8GfpStPort }
            ::= { ge8GfpStatisticTable 1 }

        Ge8GfpStatisticEntry ::= SEQUENCE {
            ge8GfpStUnit                 UnitID,
            ge8GfpStPort                 GeVcgNum,
            ge8GfpStRxFrames             Counter32,
            ge8GfpStRxBytes              Counter32,
            ge8GfpStRxControlFrames      Counter32,
            ge8GfpStRxIdleFrames         Counter32,
            ge8GfpStRxCSFFrames          Counter32,
            ge8GfpStRxDroppedFrames      Counter32,
            ge8GfpStRxErrCHECFrames      Counter32,
            ge8GfpStRxErrTHECFrames      Counter32,
            ge8GfpStRxErrEHECFrames      Counter32,
            ge8GfpStRxErrFCSFrames       Counter32,
            ge8GfpStRxFifoOvfFrames      Counter32,
            ge8GfpStTxFrames             Counter32,
            ge8GfpStTxBytes              Counter32,
            ge8GfpStTxCmfCtrlFrames      Counter32,
            ge8GfpStTxIdleFrames         Counter32
        }

        ge8GfpStUnit  OBJECT-TYPE
            SYNTAX  UnitID
            ACCESS  read-only
            STATUS  mandatory
            DESCRIPTION
                "unit index"
            ::= { ge8GfpStatisticEntry 1 }

        ge8GfpStPort  OBJECT-TYPE
            SYNTAX  GeVcgNum
            ACCESS  read-only
            STATUS  mandatory
            DESCRIPTION
                "vcg port index"
            ::= { ge8GfpStatisticEntry 2 }

        ge8GfpStRxFrames  OBJECT-TYPE
            SYNTAX  Counter32
            ACCESS  read-only
            STATUS  mandatory
            DESCRIPTION
                "WAN(VCG) Rx Frames Counter32"
            ::= { ge8GfpStatisticEntry 3 }

        ge8GfpStRxBytes  OBJECT-TYPE
            SYNTAX  Counter32
            ACCESS  read-only
            STATUS  mandatory
            DESCRIPTION
                "WAN(VCG) Rx Bytes Counter32"
            ::= { ge8GfpStatisticEntry 4 }

        ge8GfpStRxControlFrames  OBJECT-TYPE
            SYNTAX  Counter32
            ACCESS  read-only
            STATUS  mandatory
            DESCRIPTION
                "WAN(VCG) Rx Control Frames Counter32"
            ::= { ge8GfpStatisticEntry 5 }

        ge8GfpStRxIdleFrames  OBJECT-TYPE
            SYNTAX  Counter32
            ACCESS  read-only
            STATUS  mandatory
            DESCRIPTION
                "WAN(VCG) Rx Idle Frames Counter32"
            ::= { ge8GfpStatisticEntry 6 }

        ge8GfpStRxCSFFrames  OBJECT-TYPE
            SYNTAX  Counter32
            ACCESS  read-only
            STATUS  mandatory
            DESCRIPTION
                "WAN(VCG) Rx CSF Frames Counter32"
            ::= { ge8GfpStatisticEntry 7 }

        ge8GfpStRxDroppedFrames  OBJECT-TYPE
            SYNTAX  Counter32
            ACCESS  read-only
            STATUS  mandatory
            DESCRIPTION
                "WAN(VCG) Rx Dropped Frames Counter32"
            ::= { ge8GfpStatisticEntry 8 }

        ge8GfpStRxErrCHECFrames  OBJECT-TYPE
            SYNTAX  Counter32
            ACCESS  read-only
            STATUS  mandatory
            DESCRIPTION
                "WAN(VCG) Rx Error cHEC Frames Counter32"
            ::= { ge8GfpStatisticEntry 9 }

        ge8GfpStRxErrTHECFrames  OBJECT-TYPE
            SYNTAX  Counter32
            ACCESS  read-only
            STATUS  mandatory
            DESCRIPTION
                "WAN(VCG) Rx Error tHEC Frames Counter32"
            ::= { ge8GfpStatisticEntry 10 }

        ge8GfpStRxErrEHECFrames  OBJECT-TYPE
            SYNTAX  Counter32
            ACCESS  read-only
            STATUS  mandatory
            DESCRIPTION
                "WAN(VCG) Rx Error eHEC Frames Counter32"
            ::= { ge8GfpStatisticEntry 11 }

        ge8GfpStRxErrFCSFrames  OBJECT-TYPE
            SYNTAX  Counter32
            ACCESS  read-only
            STATUS  mandatory
            DESCRIPTION
                "WAN(VCG) Rx error FCS Frames Counter32"
            ::= { ge8GfpStatisticEntry 12 }

        ge8GfpStRxFifoOvfFrames  OBJECT-TYPE
            SYNTAX  Counter32
            ACCESS  read-only
            STATUS  mandatory
            DESCRIPTION
                "WAN(VCG) Rx FIFO Overflow Frames Counter32"
            ::= { ge8GfpStatisticEntry 13 }

        ge8GfpStTxFrames  OBJECT-TYPE
            SYNTAX  Counter32
            ACCESS  read-only
            STATUS  mandatory
            DESCRIPTION
                "WAN(VCG) Tx Frames Counter32"
            ::= { ge8GfpStatisticEntry 14 }

        ge8GfpStTxBytes  OBJECT-TYPE
            SYNTAX  Counter32
            ACCESS  read-only
            STATUS  mandatory
            DESCRIPTION
                "WAN(VCG) Tx Bytes Counter32"
            ::= { ge8GfpStatisticEntry 15 }

        ge8GfpStTxCmfCtrlFrames  OBJECT-TYPE
            SYNTAX  Counter32
            ACCESS  read-only
            STATUS  mandatory
            DESCRIPTION
                "WAN(VCG) Tx CMF/Control Frames Counter32"
            ::= { ge8GfpStatisticEntry 16 }

        ge8GfpStTxIdleFrames  OBJECT-TYPE
            SYNTAX  Counter32
            ACCESS  read-only
            STATUS  mandatory
            DESCRIPTION
                "WAN(VCG) Tx Idle Frames Counter32"
            ::= { ge8GfpStatisticEntry 17 }


--
--  ge8LapsStatisticTable
--
        ge8LapsStatisticTable  OBJECT-TYPE
            SYNTAX  SEQUENCE OF  Ge8LapsStatisticEntry
            ACCESS  not-accessible
            STATUS  mandatory
            DESCRIPTION
                "The 8GESW  wan(vcg) LAPS statistic table."
            ::= { ge8WanVcgStatistic 2 }

        ge8LapsStatisticEntry  OBJECT-TYPE
            SYNTAX  Ge8LapsStatisticEntry
            ACCESS  not-accessible
            STATUS  mandatory
            DESCRIPTION
                "An entry in the 8GESW  wan(vcg) LAPS statistic table."
            INDEX { ge8LapsStUnit , ge8LapsStPort }
            ::= { ge8LapsStatisticTable 1 }

        Ge8LapsStatisticEntry ::= SEQUENCE {
            ge8LapsStUnit                UnitID,
            ge8LapsStPort                GeVcgNum,
            ge8LapsStRxFrames            Counter32,
            ge8LapsStRxBytes             Counter32,
            ge8LapsStRxAbortedFrames     Counter32,
            ge8LapsStRxDroppedFrames     Counter32,
            ge8LapsStRxErrFCSFrames      Counter32,
            ge8LapsStRxTransErrFrames    Counter32,
            ge8LapsStRxMaxLenVioFrm      Counter32,
            ge8LapsStRxMinLenVioFrm      Counter32,
            ge8LapsStRxFifoOvfFrames     Counter32,
            ge8LapsStTxFrames            Counter32,
            ge8LapsStTxBytes             Counter32
        }

        ge8LapsStUnit  OBJECT-TYPE
            SYNTAX  UnitID
            ACCESS  read-only
            STATUS  mandatory
            DESCRIPTION
                "unit index"
            ::= { ge8LapsStatisticEntry 1 }

        ge8LapsStPort  OBJECT-TYPE
            SYNTAX  GeVcgNum
            ACCESS  read-only
            STATUS  mandatory
            DESCRIPTION
                "vcg port index"
            ::= { ge8LapsStatisticEntry 2 }

        ge8LapsStRxFrames  OBJECT-TYPE
            SYNTAX  Counter32
            ACCESS  read-only
            STATUS  mandatory
            DESCRIPTION
                "WAN(VCG) Rx Frames Counter32"
            ::= { ge8LapsStatisticEntry 3 }

        ge8LapsStRxBytes  OBJECT-TYPE
            SYNTAX  Counter32
            ACCESS  read-only
            STATUS  mandatory
            DESCRIPTION
                "WAN(VCG) Rx Bytes Counter32"
            ::= { ge8LapsStatisticEntry 4 }

        ge8LapsStRxAbortedFrames  OBJECT-TYPE
            SYNTAX  Counter32
            ACCESS  read-only
            STATUS  mandatory
            DESCRIPTION
                "WAN(VCG) Rx Aborted Frames Counter32"
            ::= { ge8LapsStatisticEntry 5 }

        ge8LapsStRxDroppedFrames  OBJECT-TYPE
            SYNTAX  Counter32
            ACCESS  read-only
            STATUS  mandatory
            DESCRIPTION
                "WAN(VCG) Rx Dropped Frames Counter32"
            ::= { ge8LapsStatisticEntry 6 }

        ge8LapsStRxErrFCSFrames  OBJECT-TYPE
            SYNTAX  Counter32
            ACCESS  read-only
            STATUS  mandatory
            DESCRIPTION
                "WAN(VCG) Rx Erred FCS Frames Counter32"
            ::= { ge8LapsStatisticEntry 7 }

        ge8LapsStRxTransErrFrames  OBJECT-TYPE
            SYNTAX  Counter32
            ACCESS  read-only
            STATUS  mandatory
            DESCRIPTION
                "WAN(VCG) Rx Transparency Erred Frames Counter32"
            ::= { ge8LapsStatisticEntry 8 }

        ge8LapsStRxMaxLenVioFrm  OBJECT-TYPE
            SYNTAX  Counter32
            ACCESS  read-only
            STATUS  mandatory
            DESCRIPTION
                "WAN(VCG) Rx Max Length Violation Frames Counter32"
            ::= { ge8LapsStatisticEntry 9 }

        ge8LapsStRxMinLenVioFrm  OBJECT-TYPE
            SYNTAX  Counter32
            ACCESS  read-only
            STATUS  mandatory
            DESCRIPTION
                "WAN(VCG) Min Length Violation Frames Counter32"
            ::= { ge8LapsStatisticEntry 10 }

        ge8LapsStRxFifoOvfFrames  OBJECT-TYPE
            SYNTAX  Counter32
            ACCESS  read-only
            STATUS  mandatory
            DESCRIPTION
                "WAN(VCG) Rx FIFO Overflow Frames Counter32"
            ::= { ge8LapsStatisticEntry 11 }

        ge8LapsStTxFrames  OBJECT-TYPE
            SYNTAX  Counter32
            ACCESS  read-only
            STATUS  mandatory
            DESCRIPTION
                "WAN(VCG) Tx Frames Counter32"
            ::= { ge8LapsStatisticEntry 12 }

        ge8LapsStTxBytes  OBJECT-TYPE
            SYNTAX  Counter32
            ACCESS  read-only
            STATUS  mandatory
            DESCRIPTION
                "WAN(VCG) Tx Bytes Counter32"
            ::= { ge8LapsStatisticEntry 13 }


--
--  ge8MacStatisticTable
--
        ge8MacStatisticTable  OBJECT-TYPE
            SYNTAX  SEQUENCE OF  Ge8MacStatisticEntry
            ACCESS  not-accessible
            STATUS  mandatory
            DESCRIPTION
                "The 8GESW  wan(vcg) MAC statistic table."
            ::= { ge8WanVcgStatistic 3 }

        ge8MacStatisticEntry  OBJECT-TYPE
            SYNTAX  Ge8MacStatisticEntry
            ACCESS  not-accessible
            STATUS  mandatory
            DESCRIPTION
                "An entry in the 8GESW  wan(vcg) MAC statistic table."
            INDEX { ge8MacStUnit , ge8MacStPort }
            ::= { ge8MacStatisticTable 1 }

        Ge8MacStatisticEntry ::= SEQUENCE {
            ge8MacStUnit                 UnitID,
            ge8MacStPort                 GeVcgNum,
            ge8MacStRxFrames             Counter32,
            ge8MacStRxOctets             Counter32,
            ge8MacStRxTaggedFramesOK     Counter32,
            ge8MacStRxFCSErrors          Counter32,
            ge8MacStRxLayer1Errors       Counter32,
            ge8MacStRxLayer2Errors       Counter32,
            ge8MacStRxFramesTooLong      Counter32,
            ge8MacStRxFramesTooShort     Counter32,
            ge8MacStRxJabbers            Counter32,
            ge8MacStRxPauseCtrlFrmOK     Counter32,
            ge8MacStTxFrames             Counter32,
            ge8MacStTxOctets             Counter32,
            ge8MacStTxTaggedFramesOK     Counter32,
            ge8MacStTxFcsErrors          Counter32,
            ge8MacStFilterMacCtrlFrms    Counter32,
            ge8MacStIngFifoOvfPkts       Counter32,
            ge8MacStIngFifoOvfBytes      Counter32,
            ge8MacStRxDropFrames         Counter32
        }

        ge8MacStUnit  OBJECT-TYPE
            SYNTAX  UnitID
            ACCESS  read-only
            STATUS  mandatory
            DESCRIPTION
                "unit index"
            ::= { ge8MacStatisticEntry 1 }

        ge8MacStPort  OBJECT-TYPE
            SYNTAX  GeVcgNum
            ACCESS  read-only
            STATUS  mandatory
            DESCRIPTION
                "vcg port index"
            ::= { ge8MacStatisticEntry 2 }

        ge8MacStRxFrames  OBJECT-TYPE
            SYNTAX  Counter32
            ACCESS  read-only
            STATUS  mandatory
            DESCRIPTION
                "WAN(VCG) MAC Rx Frames Counter32"
            ::= { ge8MacStatisticEntry 3 }

        ge8MacStRxOctets  OBJECT-TYPE
            SYNTAX  Counter32
            ACCESS  read-only
            STATUS  mandatory
            DESCRIPTION
                "WAN(VCG) MAC Rx Octets Counter32"
            ::= { ge8MacStatisticEntry 4 }

        ge8MacStRxTaggedFramesOK  OBJECT-TYPE
            SYNTAX  Counter32
            ACCESS  read-only
            STATUS  mandatory
            DESCRIPTION
                "WAN(VCG) MAC Rx Tagged Frames OK Counter32"
            ::= { ge8MacStatisticEntry 5 }

        ge8MacStRxFCSErrors  OBJECT-TYPE
            SYNTAX  Counter32
            ACCESS  read-only
            STATUS  mandatory
            DESCRIPTION
                "WAN(VCG) MAC Rx FXS Errors Counter32"
            ::= { ge8MacStatisticEntry 6 }

        ge8MacStRxLayer1Errors  OBJECT-TYPE
            SYNTAX  Counter32
            ACCESS  read-only
            STATUS  mandatory
            DESCRIPTION
                "WAN(VCG) MAC Rx Layer1 Errors Counter32"
            ::= { ge8MacStatisticEntry 7 }

        ge8MacStRxLayer2Errors  OBJECT-TYPE
            SYNTAX  Counter32
            ACCESS  read-only
            STATUS  mandatory
            DESCRIPTION
                "WAN(VCG) MAC Rx Layer2 Errors Counter32"
            ::= { ge8MacStatisticEntry 8 }

        ge8MacStRxFramesTooLong  OBJECT-TYPE
            SYNTAX  Counter32
            ACCESS  read-only
            STATUS  mandatory
            DESCRIPTION
                "WAN(VCG) MAC Rx Frames Too Long Counter32"
            ::= { ge8MacStatisticEntry 9 }

        ge8MacStRxFramesTooShort  OBJECT-TYPE
            SYNTAX  Counter32
            ACCESS  read-only
            STATUS  mandatory
            DESCRIPTION
                "WAN(VCG) MAC Rx Frames Too Short Counter32"
            ::= { ge8MacStatisticEntry 10 }

        ge8MacStRxJabbers  OBJECT-TYPE
            SYNTAX  Counter32
            ACCESS  read-only
            STATUS  mandatory
            DESCRIPTION
                "WAN(VCG) MAC Rx Jabbers Counter32"
            ::= { ge8MacStatisticEntry 11 }

        ge8MacStRxPauseCtrlFrmOK  OBJECT-TYPE
            SYNTAX  Counter32
            ACCESS  read-only
            STATUS  mandatory
            DESCRIPTION
                "WAN(VCG) MAC Rx Pause Control Frames OK Counter32"
            ::= { ge8MacStatisticEntry 12 }

        ge8MacStTxFrames  OBJECT-TYPE
            SYNTAX  Counter32
            ACCESS  read-only
            STATUS  mandatory
            DESCRIPTION
                "WAN(VCG) MAC Tx Frames Counter32"
            ::= { ge8MacStatisticEntry 13 }

        ge8MacStTxOctets  OBJECT-TYPE
            SYNTAX  Counter32
            ACCESS  read-only
            STATUS  mandatory
            DESCRIPTION
                "WAN(VCG) MAC Tx Octets Counter32"
            ::= { ge8MacStatisticEntry 14 }

        ge8MacStTxTaggedFramesOK  OBJECT-TYPE
            SYNTAX  Counter32
            ACCESS  read-only
            STATUS  mandatory
            DESCRIPTION
                "WAN(VCG) MAC Tx Tagged Frames OK Counter32"
            ::= { ge8MacStatisticEntry 15 }

        ge8MacStTxFcsErrors  OBJECT-TYPE
            SYNTAX  Counter32
            ACCESS  read-only
            STATUS  mandatory
            DESCRIPTION
                "WAN(VCG) MAC Tx FCS Errors Counter32"
            ::= { ge8MacStatisticEntry 16 }

        ge8MacStFilterMacCtrlFrms  OBJECT-TYPE
            SYNTAX  Counter32
            ACCESS  read-only
            STATUS  mandatory
            DESCRIPTION
                "WAN(VCG) MAC Filtered MAC Control Frames Counter32"
            ::= { ge8MacStatisticEntry 17 }

        ge8MacStIngFifoOvfPkts  OBJECT-TYPE
            SYNTAX  Counter32
            ACCESS  read-only
            STATUS  mandatory
            DESCRIPTION
                "WAN(VCG) MAC Ingress FIFO Overflow Packets Counter32"
            ::= { ge8MacStatisticEntry 18 }

        ge8MacStIngFifoOvfBytes  OBJECT-TYPE
            SYNTAX  Counter32
            ACCESS  read-only
            STATUS  mandatory
            DESCRIPTION
                "WAN(VCG) MAC Ingress FIFO Overflow Bytes Counter32"
            ::= { ge8MacStatisticEntry 19 }

        ge8MacStRxDropFrames  OBJECT-TYPE
            SYNTAX  Counter32
            ACCESS  read-only
            STATUS  mandatory
            DESCRIPTION
                "WAN(VCG) MAC Drop Frames Counter32"
            ::= { ge8MacStatisticEntry 20 }


--
--  ge8BcpStatisticTable
--
        ge8BcpStatisticTable  OBJECT-TYPE
            SYNTAX  SEQUENCE OF  Ge8BcpStatisticEntry
            ACCESS  not-accessible
            STATUS  mandatory
            DESCRIPTION
                "The 8GESW  wan(vcg) BCP statistic table."
            ::= { ge8WanVcgStatistic 4 }

        ge8BcpStatisticEntry  OBJECT-TYPE
            SYNTAX  Ge8BcpStatisticEntry
            ACCESS  not-accessible
            STATUS  mandatory
            DESCRIPTION
                "An entry in the 8GESW  wan(vcg) BCP statistic table."
            INDEX { ge8BcpStUnit , ge8BcpStPort }
            ::= { ge8BcpStatisticTable 1 }

        Ge8BcpStatisticEntry ::= SEQUENCE {
            ge8BcpStUnit                 UnitID,
            ge8BcpStPort                 GeVcgNum,
            ge8BcpStRxFrames             Counter32,
            ge8BcpStRxBytes              Counter32,
            ge8BcpStRxAbortedFrames      Counter32,
            ge8BcpStRxDroppedFrames      Counter32,
            ge8BcpStRxErrFCSFrames       Counter32,
            ge8BcpStRxTransErrFrames     Counter32,
            ge8BcpStRxMaxLenVioFrm       Counter32,
            ge8BcpStRxMinLenVioFrm       Counter32,
            ge8BcpStRxFifoOvfFrames      Counter32,
            ge8BcpStTxFrames             Counter32,
            ge8BcpStTxBytes              Counter32
        }

        ge8BcpStUnit  OBJECT-TYPE
            SYNTAX  UnitID
            ACCESS  read-only
            STATUS  mandatory
            DESCRIPTION
                "unit index"
            ::= { ge8BcpStatisticEntry 1 }

        ge8BcpStPort  OBJECT-TYPE
            SYNTAX  GeVcgNum
            ACCESS  read-only
            STATUS  mandatory
            DESCRIPTION
                "vcg port index"
            ::= { ge8BcpStatisticEntry 2 }

        ge8BcpStRxFrames  OBJECT-TYPE
            SYNTAX  Counter32
            ACCESS  read-only
            STATUS  mandatory
            DESCRIPTION
                "WAN(VCG) Rx Frames Counter32"
            ::= { ge8BcpStatisticEntry 3 }

        ge8BcpStRxBytes  OBJECT-TYPE
            SYNTAX  Counter32
            ACCESS  read-only
            STATUS  mandatory
            DESCRIPTION
                "WAN(VCG) Rx Bytes Counter32"
            ::= { ge8BcpStatisticEntry 4 }

        ge8BcpStRxAbortedFrames  OBJECT-TYPE
            SYNTAX  Counter32
            ACCESS  read-only
            STATUS  mandatory
            DESCRIPTION
                "WAN(VCG) Rx Aborted Frames Counter32"
            ::= { ge8BcpStatisticEntry 5 }

        ge8BcpStRxDroppedFrames  OBJECT-TYPE
            SYNTAX  Counter32
            ACCESS  read-only
            STATUS  mandatory
            DESCRIPTION
                "WAN(VCG) Rx Dropped Frames Counter32"
            ::= { ge8BcpStatisticEntry 6 }

        ge8BcpStRxErrFCSFrames  OBJECT-TYPE
            SYNTAX  Counter32
            ACCESS  read-only
            STATUS  mandatory
            DESCRIPTION
                "WAN(VCG) Rx Erred FCS Frames Counter32"
            ::= { ge8BcpStatisticEntry 7 }

        ge8BcpStRxTransErrFrames  OBJECT-TYPE
            SYNTAX  Counter32
            ACCESS  read-only
            STATUS  mandatory
            DESCRIPTION
                "WAN(VCG) Rx Transparency Erred Frames Counter32"
            ::= { ge8BcpStatisticEntry 8 }

        ge8BcpStRxMaxLenVioFrm  OBJECT-TYPE
            SYNTAX  Counter32
            ACCESS  read-only
            STATUS  mandatory
            DESCRIPTION
                "WAN(VCG) Rx Max Length Violation Frames Counter32"
            ::= { ge8BcpStatisticEntry 9 }

        ge8BcpStRxMinLenVioFrm  OBJECT-TYPE
            SYNTAX  Counter32
            ACCESS  read-only
            STATUS  mandatory
            DESCRIPTION
                "WAN(VCG) Min Length Violation Frames Counter32"
            ::= { ge8BcpStatisticEntry 10 }

        ge8BcpStRxFifoOvfFrames  OBJECT-TYPE
            SYNTAX  Counter32
            ACCESS  read-only
            STATUS  mandatory
            DESCRIPTION
                "WAN(VCG) Rx FIFO Overflow Frames Counter32"
            ::= { ge8BcpStatisticEntry 11 }

        ge8BcpStTxFrames  OBJECT-TYPE
            SYNTAX  Counter32
            ACCESS  read-only
            STATUS  mandatory
            DESCRIPTION
                "WAN(VCG) Tx Frames Counter32"
            ::= { ge8BcpStatisticEntry 12 }

        ge8BcpStTxBytes  OBJECT-TYPE
            SYNTAX  Counter32
            ACCESS  read-only
            STATUS  mandatory
            DESCRIPTION
                "WAN(VCG) Tx Bytes Counter32"
            ::= { ge8BcpStatisticEntry 13 }


--
--  ge8WanVcgSizeTable
--
        ge8WanVcgSizeTable  OBJECT-TYPE
            SYNTAX  SEQUENCE OF  Ge8WanVcgSizeEntry
            ACCESS  not-accessible
            STATUS  mandatory
            DESCRIPTION
                "The 8GESW  VCG size Table."
            ::= { ge8WanVcgStatistic 5 }

        ge8WanVcgSizeEntry  OBJECT-TYPE
            SYNTAX  Ge8WanVcgSizeEntry
            ACCESS  not-accessible
            STATUS  mandatory
            DESCRIPTION
                "An entry in The 8GESW  VCG size Table."
            INDEX { ge8VcgSizeUnit , ge8VcgSizeVcg }
            ::= { ge8WanVcgSizeTable 1 }

        Ge8WanVcgSizeEntry ::= SEQUENCE {
            ge8VcgSizeUnit               UnitID,
            ge8VcgSizeVcg                GeVcgNum,
            ge8VcgSizeAddChanCount       Counter32,
            ge8VcgSizeDropChanCount      Counter32
        }

        ge8VcgSizeUnit  OBJECT-TYPE
            SYNTAX  UnitID
            ACCESS  read-only
            STATUS  mandatory
            DESCRIPTION
                "unit index"
            ::= { ge8WanVcgSizeEntry 1 }

        ge8VcgSizeVcg  OBJECT-TYPE
            SYNTAX  GeVcgNum
            ACCESS  read-only
            STATUS  mandatory
            DESCRIPTION
                "VCG index"
            ::= { ge8WanVcgSizeEntry 2 }

        ge8VcgSizeAddChanCount  OBJECT-TYPE
            SYNTAX  Counter32
            ACCESS  read-only
            STATUS  mandatory
            DESCRIPTION
                "VCG Add Channel Count"
            ::= { ge8WanVcgSizeEntry 3 }

        ge8VcgSizeDropChanCount  OBJECT-TYPE
            SYNTAX  Counter32
            ACCESS  read-only
            STATUS  mandatory
            DESCRIPTION
                "VCG Drop Channel Count"
            ::= { ge8WanVcgSizeEntry 4 }


--
--  8GESW  card switch table
--
    ge8SwitchGroup          OBJECT IDENTIFIER ::= { ge8EosCard 9 }


--
--  ge8SwStatisticTable
--
        ge8SwStatisticTable  OBJECT-TYPE
            SYNTAX  SEQUENCE OF  Ge8SwStatisticEntry
            ACCESS  not-accessible
            STATUS  mandatory
            DESCRIPTION
                "The 8GESW  Switch Statistic Table."
            ::= { ge8SwitchGroup 1 }

        ge8SwStatisticEntry  OBJECT-TYPE
            SYNTAX  Ge8SwStatisticEntry
            ACCESS  not-accessible
            STATUS  mandatory
            DESCRIPTION
                "An entry in the 8GESW  Switch Statistic Table."
            INDEX { ge8SwStUnit , ge8SwStPort }
            ::= { ge8SwStatisticTable 1 }

        Ge8SwStatisticEntry ::= SEQUENCE {
            ge8SwStUnit                  UnitID,
            ge8SwStPort                  Ge8SwPort,
            ge8SwStGoodOctetsRcv         Counter32,
            ge8SwStBadOctetsRcv          Counter32,
            ge8SwStMacTransmitErr        Counter32,
            ge8SwStGoodPktsRcv           Counter32,
            ge8SwStBadPktsRcv            Counter32,
            ge8SwStBrdcPktsRcv           Counter32,
            ge8SwStMcPktsRcv             Counter32,
            ge8SwStPkts64Octs            Counter32,
            ge8SwStPkts65to127Octs       Counter32,
            ge8SwStPkts128to255Octs      Counter32,
            ge8SwStPkts256to511Octs      Counter32,
            ge8SwStPkts512to1023Octs     Counter32,
            ge8SwStPkts1024toMaxOcts     Counter32,
            ge8SwStGoodOctetsSent        Counter32,
            ge8SwStGoodPktsSent          Counter32,
            ge8SwStExcesCollisions       Counter32,
            ge8SwStMcPktsSent            Counter32,
            ge8SwStBrdcPktsSent          Counter32,
            ge8SwStUnrecogMacCntrRcv     Counter32,
            ge8SwStFcSent                Counter32,
            ge8SwStGoodFcRcv             Counter32,
            ge8SwStDropEvents            Counter32,
            ge8SwStUndersizePkts         Counter32,
            ge8SwStFragmentsPkts         Counter32,
            ge8SwStOversizePkts          Counter32,
            ge8SwStJabberPkts            Counter32,
            ge8SwStMacRcvError           Counter32,
            ge8SwStBadCrc                Counter32,
            ge8SwStCollisions            Counter32,
            ge8SwStLateCollisions        Counter32,
            ge8SwStBadFcRcv              Counter32,
            ge8SwStUcPktsRcv             Counter32,
            ge8SwStUcPktsSent            Counter32,
            ge8SwStMultiplePktsSent      Counter32,
            ge8SwStDeferredPktsSent      Counter32
        }

        ge8SwStUnit  OBJECT-TYPE
            SYNTAX  UnitID
            ACCESS  read-only
            STATUS  mandatory
            DESCRIPTION
                "unit index"
            ::= { ge8SwStatisticEntry 1 }

        ge8SwStPort  OBJECT-TYPE
            SYNTAX  Ge8SwPort
            ACCESS  read-only
            STATUS  mandatory
            DESCRIPTION
                "Port WAN1~4, LAN1~8."
            ::= { ge8SwStatisticEntry 2 }

        ge8SwStGoodOctetsRcv      OBJECT-TYPE
            SYNTAX  Counter32
            ACCESS  read-only
            STATUS  mandatory
            DESCRIPTION
                "goodOctetsRcv       "
            ::= { ge8SwStatisticEntry 3 }

        ge8SwStBadOctetsRcv       OBJECT-TYPE
            SYNTAX  Counter32
            ACCESS  read-only
            STATUS  mandatory
            DESCRIPTION
                "badOctetsRcv        "
            ::= { ge8SwStatisticEntry 4 }

        ge8SwStMacTransmitErr     OBJECT-TYPE
            SYNTAX  Counter32
            ACCESS  read-only
            STATUS  mandatory
            DESCRIPTION
                "macTransmitErr      "
            ::= { ge8SwStatisticEntry 5 }

        ge8SwStGoodPktsRcv        OBJECT-TYPE
            SYNTAX  Counter32
            ACCESS  read-only
            STATUS  mandatory
            DESCRIPTION
                "goodPktsRcv         "
            ::= { ge8SwStatisticEntry 6 }

        ge8SwStBadPktsRcv         OBJECT-TYPE
            SYNTAX  Counter32
            ACCESS  read-only
            STATUS  mandatory
            DESCRIPTION
                "badPktsRcv          "
            ::= { ge8SwStatisticEntry 7 }

        ge8SwStBrdcPktsRcv        OBJECT-TYPE
            SYNTAX  Counter32
            ACCESS  read-only
            STATUS  mandatory
            DESCRIPTION
                "brdcPktsRcv         "
            ::= { ge8SwStatisticEntry 8 }

        ge8SwStMcPktsRcv          OBJECT-TYPE
            SYNTAX  Counter32
            ACCESS  read-only
            STATUS  mandatory
            DESCRIPTION
                "mcPktsRcv           "
            ::= { ge8SwStatisticEntry 9 }

        ge8SwStPkts64Octs         OBJECT-TYPE
            SYNTAX  Counter32
            ACCESS  read-only
            STATUS  mandatory
            DESCRIPTION
                "pkts64Octets        "
            ::= { ge8SwStatisticEntry 10 }

        ge8SwStPkts65to127Octs    OBJECT-TYPE
            SYNTAX  Counter32
            ACCESS  read-only
            STATUS  mandatory
            DESCRIPTION
                "pkts65to127Octets   "
            ::= { ge8SwStatisticEntry 11 }

        ge8SwStPkts128to255Octs   OBJECT-TYPE
            SYNTAX  Counter32
            ACCESS  read-only
            STATUS  mandatory
            DESCRIPTION
                "pkts128to255Octets  "
            ::= { ge8SwStatisticEntry 12 }

        ge8SwStPkts256to511Octs   OBJECT-TYPE
            SYNTAX  Counter32
            ACCESS  read-only
            STATUS  mandatory
            DESCRIPTION
                "pkts256to511Octets  "
            ::= { ge8SwStatisticEntry 13 }

        ge8SwStPkts512to1023Octs  OBJECT-TYPE
            SYNTAX  Counter32
            ACCESS  read-only
            STATUS  mandatory
            DESCRIPTION
                "pkts512to1023Octets "
            ::= { ge8SwStatisticEntry 14 }

        ge8SwStPkts1024toMaxOcts  OBJECT-TYPE
            SYNTAX  Counter32
            ACCESS  read-only
            STATUS  mandatory
            DESCRIPTION
                "pkts1024tomaxOoctets"
            ::= { ge8SwStatisticEntry 15 }

        ge8SwStGoodOctetsSent     OBJECT-TYPE
            SYNTAX  Counter32
            ACCESS  read-only
            STATUS  mandatory
            DESCRIPTION
                "goodOctetsSent      "
            ::= { ge8SwStatisticEntry 16 }

        ge8SwStGoodPktsSent       OBJECT-TYPE
            SYNTAX  Counter32
            ACCESS  read-only
            STATUS  mandatory
            DESCRIPTION
                "goodPktsSent        "
            ::= { ge8SwStatisticEntry 17 }

        ge8SwStExcesCollisions    OBJECT-TYPE
            SYNTAX  Counter32
            ACCESS  read-only
            STATUS  mandatory
            DESCRIPTION
                "excessiveCollisions "
            ::= { ge8SwStatisticEntry 18 }

        ge8SwStMcPktsSent         OBJECT-TYPE
            SYNTAX  Counter32
            ACCESS  read-only
            STATUS  mandatory
            DESCRIPTION
                "mcPktsSent          "
            ::= { ge8SwStatisticEntry 19 }

        ge8SwStBrdcPktsSent       OBJECT-TYPE
            SYNTAX  Counter32
            ACCESS  read-only
            STATUS  mandatory
            DESCRIPTION
                "brdcPktsSent        "
            ::= { ge8SwStatisticEntry 20 }

        ge8SwStUnrecogMacCntrRcv  OBJECT-TYPE
            SYNTAX  Counter32
            ACCESS  read-only
            STATUS  mandatory
            DESCRIPTION
                "unrecogMacCntrRcv   "
            ::= { ge8SwStatisticEntry 21 }

        ge8SwStFcSent             OBJECT-TYPE
            SYNTAX  Counter32
            ACCESS  read-only
            STATUS  mandatory
            DESCRIPTION
                "fcSent              "
            ::= { ge8SwStatisticEntry 22 }

        ge8SwStGoodFcRcv          OBJECT-TYPE
            SYNTAX  Counter32
            ACCESS  read-only
            STATUS  mandatory
            DESCRIPTION
                "goodFcRcv           "
            ::= { ge8SwStatisticEntry 23 }

        ge8SwStDropEvents         OBJECT-TYPE
            SYNTAX  Counter32
            ACCESS  read-only
            STATUS  mandatory
            DESCRIPTION
                "dropEvents          "
            ::= { ge8SwStatisticEntry 24 }

        ge8SwStUndersizePkts      OBJECT-TYPE
            SYNTAX  Counter32
            ACCESS  read-only
            STATUS  mandatory
            DESCRIPTION
                "undersizePkts       "
            ::= { ge8SwStatisticEntry 25 }

        ge8SwStFragmentsPkts      OBJECT-TYPE
            SYNTAX  Counter32
            ACCESS  read-only
            STATUS  mandatory
            DESCRIPTION
                "fragmentsPkts       "
            ::= { ge8SwStatisticEntry 26 }

        ge8SwStOversizePkts       OBJECT-TYPE
            SYNTAX  Counter32
            ACCESS  read-only
            STATUS  mandatory
            DESCRIPTION
                "oversizePkts        "
            ::= { ge8SwStatisticEntry 27 }

        ge8SwStJabberPkts         OBJECT-TYPE
            SYNTAX  Counter32
            ACCESS  read-only
            STATUS  mandatory
            DESCRIPTION
                "jabberPkts          "
            ::= { ge8SwStatisticEntry 28 }

        ge8SwStMacRcvError        OBJECT-TYPE
            SYNTAX  Counter32
            ACCESS  read-only
            STATUS  mandatory
            DESCRIPTION
                "macRcvError         "
            ::= { ge8SwStatisticEntry 29 }

        ge8SwStBadCrc             OBJECT-TYPE
            SYNTAX  Counter32
            ACCESS  read-only
            STATUS  mandatory
            DESCRIPTION
                "badCrc              "
            ::= { ge8SwStatisticEntry 30 }

        ge8SwStCollisions         OBJECT-TYPE
            SYNTAX  Counter32
            ACCESS  read-only
            STATUS  mandatory
            DESCRIPTION
                "collisions          "
            ::= { ge8SwStatisticEntry 31 }

        ge8SwStLateCollisions     OBJECT-TYPE
            SYNTAX  Counter32
            ACCESS  read-only
            STATUS  mandatory
            DESCRIPTION
                "lateCollisions      "
            ::= { ge8SwStatisticEntry 32 }

        ge8SwStBadFcRcv           OBJECT-TYPE
            SYNTAX  Counter32
            ACCESS  read-only
            STATUS  mandatory
            DESCRIPTION
                "badFcRcv            "
            ::= { ge8SwStatisticEntry 33 }

        ge8SwStUcPktsRcv          OBJECT-TYPE
            SYNTAX  Counter32
            ACCESS  read-only
            STATUS  mandatory
            DESCRIPTION
                "ucPktsRcv           "
            ::= { ge8SwStatisticEntry 34 }

        ge8SwStUcPktsSent         OBJECT-TYPE
            SYNTAX  Counter32
            ACCESS  read-only
            STATUS  mandatory
            DESCRIPTION
                "ucPktsSent          "
            ::= { ge8SwStatisticEntry 35 }

        ge8SwStMultiplePktsSent   OBJECT-TYPE
            SYNTAX  Counter32
            ACCESS  read-only
            STATUS  mandatory
            DESCRIPTION
                "multiplePktsSent    "
            ::= { ge8SwStatisticEntry 36 }

        ge8SwStDeferredPktsSent   OBJECT-TYPE
            SYNTAX  Counter32
            ACCESS  read-only
            STATUS  mandatory
            DESCRIPTION
                "deferredPktsSent    "
            ::= { ge8SwStatisticEntry 37 }



--
--  8GESW  card vlan table
--
    ge8VlanGroup           OBJECT IDENTIFIER ::= { ge8SwitchGroup 2 }

    ge8VlanSetupTable    OBJECT IDENTIFIER ::= { ge8VlanGroup 1 }

        ge8VlanTableUnit   OBJECT-TYPE
            SYNTAX  UnitID
            ACCESS  read-write
            STATUS  mandatory
            DESCRIPTION
                " unit"
            ::= { ge8VlanSetupTable 1 }

        ge8VlanTableVlanID   OBJECT-TYPE
            SYNTAX  INTEGER (1..4094)
            ACCESS  read-write
            STATUS  mandatory
            DESCRIPTION
                " Vlan ID"
            ::= { ge8VlanSetupTable 2 }

        ge8VlanTableValid   OBJECT-TYPE
            SYNTAX  INTEGER {
                    noAction(0),
                    invalid(1),
                    valid(2)
                }
            ACCESS  read-write
            STATUS  mandatory
            DESCRIPTION
                "Vlan entry valid/inalid"
            ::= { ge8VlanSetupTable 3 }

        ge8VlanWan1Port   OBJECT-TYPE
            SYNTAX  INTEGER {
                    noAction(0),
                    off(1),
                    on(2)
                }
            ACCESS  read-write
            STATUS  mandatory
            DESCRIPTION
                " Vlan wan1 entry"
            ::= { ge8VlanSetupTable 4 }

        ge8VlanWan2Port   OBJECT-TYPE
            SYNTAX  INTEGER {
                    noAction(0),
                    off(1),
                    on(2)
                }
            ACCESS  read-write
            STATUS  mandatory
            DESCRIPTION
                " Vlan wan2 entry"
            ::= { ge8VlanSetupTable 5 }

        ge8VlanWan3Port   OBJECT-TYPE
            SYNTAX  INTEGER {
                    noAction(0),
                    off(1),
                    on(2)
                }
            ACCESS  read-write
            STATUS  mandatory
            DESCRIPTION
                " Vlan wan3 entry"
            ::= { ge8VlanSetupTable 6 }

        ge8VlanWan4Port   OBJECT-TYPE
            SYNTAX  INTEGER {
                    noAction(0),
                    off(1),
                    on(2)
                }
            ACCESS  read-write
            STATUS  mandatory
            DESCRIPTION
                " Vlan wan4 entry"
            ::= { ge8VlanSetupTable 7 }

        ge8VlanLan1Port   OBJECT-TYPE
            SYNTAX  INTEGER {
                    noAction(0),
                    off(1),
                    on(2)
                }
            ACCESS  read-write
            STATUS  mandatory
            DESCRIPTION
                " Vlan lan1 entry"
            ::= { ge8VlanSetupTable 8 }

        ge8VlanLan2Port   OBJECT-TYPE
            SYNTAX  INTEGER {
                    noAction(0),
                    off(1),
                    on(2)
                }
            ACCESS  read-write
            STATUS  mandatory
            DESCRIPTION
                " Vlan lan2 entry"
            ::= { ge8VlanSetupTable 9 }

        ge8VlanLan3Port   OBJECT-TYPE
            SYNTAX  INTEGER {
                    noAction(0),
                    off(1),
                    on(2)
                }
            ACCESS  read-write
            STATUS  mandatory
            DESCRIPTION
                " Vlan lan3 entry"
            ::= { ge8VlanSetupTable 10 }

        ge8VlanLan4Port   OBJECT-TYPE
            SYNTAX  INTEGER {
                    noAction(0),
                    off(1),
                    on(2)
                }
            ACCESS  read-write
            STATUS  mandatory
            DESCRIPTION
                " Vlan lan4 entry"
            ::= { ge8VlanSetupTable 11 }

        ge8VlanLan5Port   OBJECT-TYPE
            SYNTAX  INTEGER {
                    noAction(0),
                    off(1),
                    on(2)
                }
            ACCESS  read-write
            STATUS  mandatory
            DESCRIPTION
                " Vlan lan5 entry"
            ::= { ge8VlanSetupTable 12 }

        ge8VlanLan6Port   OBJECT-TYPE
            SYNTAX  INTEGER {
                    noAction(0),
                    off(1),
                    on(2)
                }
            ACCESS  read-write
            STATUS  mandatory
            DESCRIPTION
                " Vlan lan6 entry"
            ::= { ge8VlanSetupTable 13 }

        ge8VlanLan7Port   OBJECT-TYPE
            SYNTAX  INTEGER {
                    noAction(0),
                    off(1),
                    on(2)
                }
            ACCESS  read-write
            STATUS  mandatory
            DESCRIPTION
                " Vlan lan7 entry"
            ::= { ge8VlanSetupTable 14 }

        ge8VlanLan8Port   OBJECT-TYPE
            SYNTAX  INTEGER {
                    noAction(0),
                    off(1),
                    on(2)
                }
            ACCESS  read-write
            STATUS  mandatory
            DESCRIPTION
                " Vlan lan8 entry"
            ::= { ge8VlanSetupTable 15 }

        ge8VlanFilterBroadcast   OBJECT-TYPE
            SYNTAX  INTEGER {
                    noAction(0),
                    off(1),
                    on(2)
                }
            ACCESS  read-write
            STATUS  mandatory
            DESCRIPTION
                " Vlan filter broadcast"
            ::= { ge8VlanSetupTable 16 }


        ge8VlanEntryCmd   OBJECT-TYPE
            SYNTAX  INTEGER {
                    get(1),
                    set(2),
                    resultFail(3),
                    resultOk(4)
                }
            ACCESS  read-write
            STATUS  mandatory
            DESCRIPTION
                " command and result for this vlan entry"
            ::= { ge8VlanSetupTable 17 }


--
--  VLAN port association table
--
        ge8VlanPortAssocTable  OBJECT-TYPE
            SYNTAX  SEQUENCE OF Ge8VlanPortAssocEntry
            ACCESS  not-accessible
            STATUS  mandatory
            DESCRIPTION
                "VLAN port association table"
            ::= { ge8VlanGroup 2  }

        ge8VlanPortAssocEntry  OBJECT-TYPE
            SYNTAX  Ge8VlanPortAssocEntry
            ACCESS  not-accessible
            STATUS  mandatory
            DESCRIPTION
                "An entry in the VLAN port association table."
            INDEX { ge8VlanPatUnit , ge8VlanPatVlanId }
            ::= { ge8VlanPortAssocTable 1 }

        Ge8VlanPortAssocEntry ::= SEQUENCE {
            ge8VlanPatUnit                 UnitID,
            ge8VlanPatVlanId               INTEGER,
            ge8VlanPatWan1Port             INTEGER,
            ge8VlanPatWan2Port             INTEGER,
            ge8VlanPatWan3Port             INTEGER,
            ge8VlanPatWan4Port             INTEGER,
            ge8VlanPatLan1Port             INTEGER,
            ge8VlanPatLan2Port             INTEGER,
            ge8VlanPatLan3Port             INTEGER,
            ge8VlanPatLan4Port             INTEGER,
            ge8VlanPatLan5Port             INTEGER,
            ge8VlanPatLan6Port             INTEGER,
            ge8VlanPatLan7Port             INTEGER,
            ge8VlanPatLan8Port             INTEGER,
            ge8VlanPatFilterBroadcast      INTEGER
        }

        ge8VlanPatUnit OBJECT-TYPE
            SYNTAX  UnitID
            ACCESS  read-only
            STATUS  mandatory
            DESCRIPTION
                "Unit"
            ::= {  ge8VlanPortAssocEntry 1 }

        ge8VlanPatVlanId OBJECT-TYPE
            SYNTAX  INTEGER (1..4094)
            ACCESS  read-only
            STATUS  mandatory
            DESCRIPTION
                "vlan ID 1~4094"
            ::= { ge8VlanPortAssocEntry 2 }

        ge8VlanPatWan1Port  OBJECT-TYPE
            SYNTAX  INTEGER {
                    off(1),
                    on(2),
                    notAvailable(100)
                }
            ACCESS  read-only
            STATUS  mandatory
            DESCRIPTION
                "vlan port wan1"
            ::= { ge8VlanPortAssocEntry  3 }

        ge8VlanPatWan2Port  OBJECT-TYPE
            SYNTAX  INTEGER {
                    off(1),
                    on(2),
                    notAvailable(100)
                }
            ACCESS  read-only
            STATUS  mandatory
            DESCRIPTION
                "vlan port wan2"
            ::= { ge8VlanPortAssocEntry  4 }

        ge8VlanPatWan3Port  OBJECT-TYPE
            SYNTAX  INTEGER {
                    off(1),
                    on(2),
                    notAvailable(100)
                }
            ACCESS  read-only
            STATUS  mandatory
            DESCRIPTION
                "vlan port wan3"
            ::= { ge8VlanPortAssocEntry  5 }

        ge8VlanPatWan4Port  OBJECT-TYPE
            SYNTAX  INTEGER {
                    off(1),
                    on(2),
                    notAvailable(100)
                }
            ACCESS  read-only
            STATUS  mandatory
            DESCRIPTION
                "vlan port wan4"
            ::= { ge8VlanPortAssocEntry  6 }

        ge8VlanPatLan1Port  OBJECT-TYPE
            SYNTAX  INTEGER {
                    off(1),
                    on(2),
                    notAvailable(100)
                }
            ACCESS  read-only
            STATUS  mandatory
            DESCRIPTION
                "vlan port lan1"
            ::= { ge8VlanPortAssocEntry  7 }

        ge8VlanPatLan2Port  OBJECT-TYPE
            SYNTAX  INTEGER {
                    off(1),
                    on(2),
                    notAvailable(100)
                }
            ACCESS  read-only
            STATUS  mandatory
            DESCRIPTION
                "vlan port lan2"
            ::= { ge8VlanPortAssocEntry  8 }

        ge8VlanPatLan3Port  OBJECT-TYPE
            SYNTAX  INTEGER {
                    off(1),
                    on(2),
                    notAvailable(100)
                }
            ACCESS  read-only
            STATUS  mandatory
            DESCRIPTION
                "vlan port lan3"
            ::= { ge8VlanPortAssocEntry  9 }

        ge8VlanPatLan4Port  OBJECT-TYPE
            SYNTAX  INTEGER {
                    off(1),
                    on(2),
                    notAvailable(100)
                }
            ACCESS  read-only
            STATUS  mandatory
            DESCRIPTION
                "vlan port lan4"
            ::= { ge8VlanPortAssocEntry  10 }

        ge8VlanPatLan5Port  OBJECT-TYPE
            SYNTAX  INTEGER {
                    off(1),
                    on(2),
                    notAvailable(100)
                }
            ACCESS  read-only
            STATUS  mandatory
            DESCRIPTION
                "vlan port lan5"
            ::= { ge8VlanPortAssocEntry  11 }

        ge8VlanPatLan6Port  OBJECT-TYPE
            SYNTAX  INTEGER {
                    off(1),
                    on(2),
                    notAvailable(100)
                }
            ACCESS  read-only
            STATUS  mandatory
            DESCRIPTION
                "vlan port lan6"
            ::= { ge8VlanPortAssocEntry  12 }

        ge8VlanPatLan7Port  OBJECT-TYPE
            SYNTAX  INTEGER {
                    off(1),
                    on(2),
                    notAvailable(100)
                }
            ACCESS  read-only
            STATUS  mandatory
            DESCRIPTION
                "vlan port lan7"
            ::= { ge8VlanPortAssocEntry  13 }

        ge8VlanPatLan8Port  OBJECT-TYPE
            SYNTAX  INTEGER {
                    off(1),
                    on(2),
                    notAvailable(100)
                }
            ACCESS  read-only
            STATUS  mandatory
            DESCRIPTION
                "vlan port lan8"
            ::= { ge8VlanPortAssocEntry  14 }

        ge8VlanPatFilterBroadcast  OBJECT-TYPE
            SYNTAX  INTEGER {
                    off(1),
                    on(2),
                    notAvailable(100)
                }
            ACCESS  read-only
            STATUS  mandatory
            DESCRIPTION
                "filter broadcast"
            ::= { ge8VlanPortAssocEntry  15 }


--
--  VLAN port configuration
--
        ge8VlanPortCfgTable  OBJECT-TYPE
            SYNTAX  SEQUENCE OF Ge8VlanPortCfgEntry
            ACCESS  not-accessible
            STATUS  mandatory
            DESCRIPTION
                "vlan port configuration table"
            ::= { ge8VlanGroup  3  }

        ge8VlanPortCfgEntry  OBJECT-TYPE
            SYNTAX  Ge8VlanPortCfgEntry
            ACCESS  not-accessible
            STATUS  mandatory
            DESCRIPTION
                "vlan port configuration entry"
            INDEX { ge8VlanPortCfgUnit , ge8VlanPortCfgPort }
            ::= { ge8VlanPortCfgTable 1 }

        Ge8VlanPortCfgEntry ::= SEQUENCE {
            ge8VlanPortCfgUnit         UnitID,
            ge8VlanPortCfgPort         INTEGER,
            ge8VlanPortCfgVlanID       INTEGER,
            ge8VlanPortIngressFilter   INTEGER,
            ge8VlanPortUntagOut        INTEGER
        }

        ge8VlanPortCfgUnit OBJECT-TYPE
            SYNTAX  UnitID
            ACCESS  read-only
            STATUS  mandatory
            DESCRIPTION
                "Unit"
            ::= {  ge8VlanPortCfgEntry 1 }

        ge8VlanPortCfgPort OBJECT-TYPE
            SYNTAX  INTEGER{
                    wan1(1),
                    wan2(2),
                    wan3(3),
                    wan4(4),
                    lan1(5),
                    lan2(6),
                    lan3(7),
                    lan4(8),
                    lan5(9),
                    lan6(10),
                    lan7(11),
                    lan8(12)
                }
            ACCESS  read-only
            STATUS  mandatory
            DESCRIPTION
                "Port WAN1~4, LAN1~8"
            ::= {  ge8VlanPortCfgEntry 2 }

        ge8VlanPortCfgVlanID OBJECT-TYPE
            SYNTAX  INTEGER (1..4094)
            ACCESS  read-write
            STATUS  mandatory
            DESCRIPTION
                "default vlan ID of the port"
            ::= { ge8VlanPortCfgEntry  3 }

        ge8VlanPortIngressFilter  OBJECT-TYPE
            SYNTAX  INTEGER {
                    disable(1),
                    enable(2)
                }
            ACCESS  read-write
            STATUS  mandatory
            DESCRIPTION
                "vlan port ingress filter"
            ::= { ge8VlanPortCfgEntry  4 }

        ge8VlanPortUntagOut  OBJECT-TYPE
            SYNTAX  INTEGER {
                    disable(1),
                    enable(2)
                }
            ACCESS  read-write
            STATUS  mandatory
            DESCRIPTION
                "vlan port tag-out or untag-out"
            ::= { ge8VlanPortCfgEntry  5 }


--
--  ge8VlanTPIDTable
--
        ge8VlanTPIDTable  OBJECT-TYPE
            SYNTAX  SEQUENCE OF  Ge8VlanTPIDEntry
            ACCESS  not-accessible
            STATUS  mandatory
            DESCRIPTION
                "The 8GESW  VLAN Tag Protocol ID Table."
            ::= { ge8VlanGroup 4 }

        ge8VlanTPIDEntry  OBJECT-TYPE
            SYNTAX  Ge8VlanTPIDEntry
            ACCESS  not-accessible
            STATUS  mandatory
            DESCRIPTION
                "An entry in The 8GESW  VLAN Tag Protocol ID Table."
            INDEX { ge8VlanTPIDUnit }
            ::= { ge8VlanTPIDTable 1 }

        Ge8VlanTPIDEntry ::= SEQUENCE {
            ge8VlanTPIDUnit            UnitID,
            ge8VlanTPIDTPID            OCTET STRING
        }

        ge8VlanTPIDUnit  OBJECT-TYPE
            SYNTAX  UnitID
            ACCESS  read-only
            STATUS  mandatory
            DESCRIPTION
                "unit index"
            ::= { ge8VlanTPIDEntry 1 }

        ge8VlanTPIDTPID  OBJECT-TYPE
            SYNTAX  OCTET STRING(SIZE(2))
            ACCESS  read-write
            STATUS  mandatory
            DESCRIPTION
                "VLAN Tag Protocol ID"
            ::= { ge8VlanTPIDEntry 2 }


--
--  ge8PortmapTable
--
        ge8PortmapTable  OBJECT-TYPE
            SYNTAX  SEQUENCE OF  Ge8PortmapEntry
            ACCESS  not-accessible
            STATUS  mandatory
            DESCRIPTION
                "The 8GESW  Port Map Table."
            ::= { ge8SwitchGroup 3 }

        ge8PortmapEntry  OBJECT-TYPE
            SYNTAX  Ge8PortmapEntry
            ACCESS  not-accessible
            STATUS  mandatory
            DESCRIPTION
                "An entry in The 8GESW  Port Map Table."
            INDEX { ge8PortMapUnit , ge8PortMapWan }
            ::= { ge8PortmapTable 1 }

        Ge8PortmapEntry ::= SEQUENCE {
            ge8PortMapUnit               UnitID,
            ge8PortMapWan                Ge8SwPort,
            ge8PortMapLan                Ge8LanPort
        }

        ge8PortMapUnit  OBJECT-TYPE
            SYNTAX  UnitID
            ACCESS  read-only
            STATUS  mandatory
            DESCRIPTION
                "unit index"
            ::= { ge8PortmapEntry 1 }

        ge8PortMapWan  OBJECT-TYPE
            SYNTAX  Ge8SwPort
            ACCESS  read-only
            STATUS  mandatory
            DESCRIPTION
                "LAN port index"
            ::= { ge8PortmapEntry 2 }

        ge8PortMapLan  OBJECT-TYPE
            SYNTAX  Ge8LanPort
            ACCESS  read-write
            STATUS  mandatory
            DESCRIPTION
                "Port Map to Wan to Lan"
            ::= { ge8PortmapEntry 3 }

--
--   ge8PortTrunkTable
--
        ge8PortTrunkTable  OBJECT-TYPE
            SYNTAX  SEQUENCE OF  Ge8PortTrunkEntry
            ACCESS  not-accessible
            STATUS  mandatory
            DESCRIPTION
                "The 8GESW  Port Trunk Table."
            ::= { ge8SwitchGroup 4 }

        ge8PortTrunkEntry  OBJECT-TYPE
            SYNTAX  Ge8PortTrunkEntry
            ACCESS  not-accessible
            STATUS  mandatory
            DESCRIPTION
                "An entry in the 8GESW  Port Trunk Table."
            INDEX { ge8TrunkUnit , ge8TrunkGroup }
            ::= { ge8PortTrunkTable 1 }

        Ge8PortTrunkEntry ::= SEQUENCE {
            ge8TrunkUnit                 UnitID,
            ge8TrunkGroup                INTEGER,
            ge8TrunkMemberLeaderPort     INTEGER,
            ge8TrunkWan1                 INTEGER,
            ge8TrunkWan2                 INTEGER,
            ge8TrunkWan3                 INTEGER,
            ge8TrunkWan4                 INTEGER,
            ge8TrunkLan1                 INTEGER,
            ge8TrunkLan2                 INTEGER,
            ge8TrunkLan3                 INTEGER,
            ge8TrunkLan4                 INTEGER,
            ge8TrunkLan5                 INTEGER,
            ge8TrunkLan6                 INTEGER,
            ge8TrunkLan7                 INTEGER,
            ge8TrunkLan8                 INTEGER
        }

        ge8TrunkUnit  OBJECT-TYPE
            SYNTAX  UnitID
            ACCESS  read-only
            STATUS  mandatory
            DESCRIPTION
                "unit index"
            ::= { ge8PortTrunkEntry 1 }

        ge8TrunkGroup  OBJECT-TYPE
            SYNTAX  INTEGER {
                    trunk1(1),
                    trunk2(2),
                    trunk3(3),
                    trunk4(4)
                }
            ACCESS  read-only
            STATUS  mandatory
            DESCRIPTION
                "Trunk 1 to 4"
            ::= { ge8PortTrunkEntry 2 }

        ge8TrunkMemberLeaderPort  OBJECT-TYPE
            SYNTAX  INTEGER {
                    none(0),
                    wan1(1),
                    wan2(2),
                    wan3(3),
                    wan4(4),
                    lan1(5),
                    lan2(6),
                    lan3(7),
                    lan4(8),
                    lan5(9),
                    lan6(10),
                    lan7(11),
                    lan8(12)
                }
            ACCESS  read-write
            STATUS  mandatory
            DESCRIPTION
                "Member/Leader Port"
            ::= { ge8PortTrunkEntry 3 }

        ge8TrunkWan1  OBJECT-TYPE
            SYNTAX  INTEGER {
                    off(1),
                    on(2)
                }
            ACCESS  read-write
            STATUS  mandatory
            DESCRIPTION
                "WAN1 Trunk ON/OFF"
            ::= { ge8PortTrunkEntry 4 }

        ge8TrunkWan2  OBJECT-TYPE
            SYNTAX  INTEGER {
                    off(1),
                    on(2)
                }
            ACCESS  read-write
            STATUS  mandatory
            DESCRIPTION
                "WAN2 Trunk ON/OFF"
            ::= { ge8PortTrunkEntry 5 }

        ge8TrunkWan3  OBJECT-TYPE
            SYNTAX  INTEGER {
                    off(1),
                    on(2)
                }
            ACCESS  read-write
            STATUS  mandatory
            DESCRIPTION
                "WAN3 Trunk ON/OFF"
            ::= { ge8PortTrunkEntry 6 }

        ge8TrunkWan4  OBJECT-TYPE
            SYNTAX  INTEGER {
                    off(1),
                    on(2)
                }
            ACCESS  read-write
            STATUS  mandatory
            DESCRIPTION
                "WAN4 Trunk ON/OFF"
            ::= { ge8PortTrunkEntry 7 }

        ge8TrunkLan1  OBJECT-TYPE
            SYNTAX  INTEGER {
                    off(1),
                    on(2)
                }
            ACCESS  read-write
            STATUS  mandatory
            DESCRIPTION
                "LAN1 Trunk ON/OFF"
            ::= { ge8PortTrunkEntry 8 }

        ge8TrunkLan2  OBJECT-TYPE
            SYNTAX  INTEGER {
                    off(1),
                    on(2)
                }
            ACCESS  read-write
            STATUS  mandatory
            DESCRIPTION
                "LAN2 Trunk ON/OFF"
            ::= { ge8PortTrunkEntry 9 }

        ge8TrunkLan3  OBJECT-TYPE
            SYNTAX  INTEGER {
                    off(1),
                    on(2)
                }
            ACCESS  read-write
            STATUS  mandatory
            DESCRIPTION
                "LAN3 Trunk ON/OFF"
            ::= { ge8PortTrunkEntry 10 }

        ge8TrunkLan4  OBJECT-TYPE
            SYNTAX  INTEGER {
                    off(1),
                    on(2)
                }
            ACCESS  read-write
            STATUS  mandatory
            DESCRIPTION
                "LAN4 Trunk ON/OFF"
            ::= { ge8PortTrunkEntry 11 }

        ge8TrunkLan5  OBJECT-TYPE
            SYNTAX  INTEGER {
                    off(1),
                    on(2)
                }
            ACCESS  read-write
            STATUS  mandatory
            DESCRIPTION
                "LAN5 Trunk ON/OFF"
            ::= { ge8PortTrunkEntry 12 }

        ge8TrunkLan6  OBJECT-TYPE
            SYNTAX  INTEGER {
                    off(1),
                    on(2)
                }
            ACCESS  read-write
            STATUS  mandatory
            DESCRIPTION
                "LAN6 Trunk ON/OFF"
            ::= { ge8PortTrunkEntry 13 }

        ge8TrunkLan7  OBJECT-TYPE
            SYNTAX  INTEGER {
                    off(1),
                    on(2)
                }
            ACCESS  read-write
            STATUS  mandatory
            DESCRIPTION
                "LAN7 Trunk ON/OFF"
            ::= { ge8PortTrunkEntry 14 }

        ge8TrunkLan8  OBJECT-TYPE
            SYNTAX  INTEGER {
                    off(1),
                    on(2)
                }
            ACCESS  read-write
            STATUS  mandatory
            DESCRIPTION
                "LAN8 Trunk ON/OFF"
            ::= { ge8PortTrunkEntry 15 }


--
--  ge8StpGroup
--
    ge8StpGroup       OBJECT IDENTIFIER ::= { ge8SwitchGroup 5 }


--
--  ge8MstpBrgInfoTable
--
        ge8MstpBrgInfoTable  OBJECT-TYPE
            SYNTAX  SEQUENCE OF  Ge8MstpBrgInfoEntry
            ACCESS  not-accessible
            STATUS  mandatory
            DESCRIPTION
                "The 8GESW  MSTP bridge info Table."
            ::= { ge8StpGroup 1 }

        ge8MstpBrgInfoEntry  OBJECT-TYPE
            SYNTAX  Ge8MstpBrgInfoEntry
            ACCESS  not-accessible
            STATUS  mandatory
            DESCRIPTION
                "An entry in The 8GESW  MSTP bridge info Table."
            INDEX { ge8MstpBrgUnit }
            ::= { ge8MstpBrgInfoTable 1 }

        Ge8MstpBrgInfoEntry ::= SEQUENCE {
            ge8MstpBrgUnit               UnitID,
            ge8MstpBrgEnable             INTEGER,
            ge8MstpBrgRegion             DisplayString,
            ge8MstpBrgRevision           INTEGER,
            ge8MstpBrgMacAddr            DisplayString,
            ge8MstpBrgPriority           INTEGER,
            ge8MstpBrgMaxAge             INTEGER,
            ge8MstpBrgHelloTime          INTEGER,
            ge8MstpBrgFwdDelay           INTEGER
        }

        ge8MstpBrgUnit  OBJECT-TYPE
            SYNTAX  UnitID
            ACCESS  read-only
            STATUS  mandatory
            DESCRIPTION
                "unit index"
            ::= { ge8MstpBrgInfoEntry 1 }

        ge8MstpBrgEnable  OBJECT-TYPE
            SYNTAX  INTEGER {
                    disable(1),
                    enable(2)
                }
            ACCESS  read-write
            STATUS  mandatory
            DESCRIPTION
                "MSTP enable/disable"
            ::= { ge8MstpBrgInfoEntry 2 }

        ge8MstpBrgRegion  OBJECT-TYPE
            SYNTAX  DisplayString (SIZE (1..36))
            ACCESS  read-write
            STATUS  mandatory
            DESCRIPTION
                "Region Name"
            ::= { ge8MstpBrgInfoEntry 3 }

        ge8MstpBrgRevision  OBJECT-TYPE
            SYNTAX  INTEGER (0..65535)
            ACCESS  read-write
            STATUS  mandatory
            DESCRIPTION
                "Revision"
            ::= { ge8MstpBrgInfoEntry 4 }

        ge8MstpBrgMacAddr  OBJECT-TYPE
            SYNTAX  DisplayString
            ACCESS  read-only
            STATUS  mandatory
            DESCRIPTION
                "Bridge ID MAC ADDR"
            ::= { ge8MstpBrgInfoEntry 5 }

        ge8MstpBrgPriority  OBJECT-TYPE
            SYNTAX  INTEGER {
                    priority0(1),
                    priority4096(2),
                    priority8192(3),
                    priority12288(4),
                    priority16384(5),
                    priority20480(6),
                    priority24576(7),
                    priority28672(8),
                    priority32768(9),
                    priority36864(10),
                    priority40960(11),
                    priority45056(12),
                    priority49152(13),
                    priority53248(14),
                    priority57344(15),
                    priority61440(16)
                }
            ACCESS  read-write
            STATUS  mandatory
            DESCRIPTION
                "Bridge ID Priority"
            ::= { ge8MstpBrgInfoEntry 6 }

        ge8MstpBrgMaxAge  OBJECT-TYPE
            SYNTAX  INTEGER (4..40)
            ACCESS  read-write
            STATUS  mandatory
            DESCRIPTION
                "Bridge Max Age"
            ::= { ge8MstpBrgInfoEntry 7 }

        ge8MstpBrgHelloTime  OBJECT-TYPE
            SYNTAX  INTEGER (1..10)
            ACCESS  read-write
            STATUS  mandatory
            DESCRIPTION
                "Bridge Hello Time"
            ::= { ge8MstpBrgInfoEntry 8 }

        ge8MstpBrgFwdDelay  OBJECT-TYPE
            SYNTAX  INTEGER (4..30)
            ACCESS  read-write
            STATUS  mandatory
            DESCRIPTION
                "Bridge Forward Delay"
            ::= { ge8MstpBrgInfoEntry 9 }


--
--  ge8StpPortEnTable
--
        ge8StpPortEnTable  OBJECT-TYPE
            SYNTAX  SEQUENCE OF  Ge8StpPortEnEntry
            ACCESS  not-accessible
            STATUS  mandatory
            DESCRIPTION
                "The 8GESW  STP port Enable/Disable Table."
            ::= { ge8StpGroup 2 }

        ge8StpPortEnEntry  OBJECT-TYPE
            SYNTAX  Ge8StpPortEnEntry
            ACCESS  not-accessible
            STATUS  mandatory
            DESCRIPTION
                "An entry in The 8GESW  STP port Enable/Disable Table."
            INDEX { ge8StpPortEnUnit , ge8StpPortEnPort }
            ::= { ge8StpPortEnTable 1 }

        Ge8StpPortEnEntry ::= SEQUENCE {
            ge8StpPortEnUnit             UnitID,
            ge8StpPortEnPort             Ge8SwPort,
            ge8StpPortEnEnable           INTEGER
        }

        ge8StpPortEnUnit  OBJECT-TYPE
            SYNTAX  UnitID
            ACCESS  read-only
            STATUS  mandatory
            DESCRIPTION
                "unit index"
            ::= { ge8StpPortEnEntry 1 }

        ge8StpPortEnPort  OBJECT-TYPE
            SYNTAX  Ge8SwPort
            ACCESS  read-only
            STATUS  mandatory
            DESCRIPTION
                "Port WAN1~4, LAN1~8."
            ::= { ge8StpPortEnEntry 2 }

        ge8StpPortEnEnable  OBJECT-TYPE
            SYNTAX  INTEGER {
                    disable(1),
                    enable(2)
                }
            ACCESS  read-write
            STATUS  mandatory
            DESCRIPTION
                "STP port enable/disable"
            ::= { ge8StpPortEnEntry 3 }


--
--  ge8MstpInstance
--

    ge8MstpInstance       OBJECT IDENTIFIER ::= { ge8StpGroup 3 }

    ge8MstpInstanceTable  OBJECT IDENTIFIER ::= { ge8MstpInstance 1 }


        ge8MstpInstanceUnit  OBJECT-TYPE
            SYNTAX  UnitID
            ACCESS  read-write
            STATUS  mandatory
            DESCRIPTION
                "unit index"
            ::= { ge8MstpInstanceTable 1 }

        ge8MstpInstanceInstance  OBJECT-TYPE
            SYNTAX  INTEGER (1..64)
            ACCESS  read-write
            STATUS  mandatory
            DESCRIPTION
                "Mstp Instance 1~64"
            ::= { ge8MstpInstanceTable 2 }

        ge8MstpInstanceSet  OBJECT-TYPE
            SYNTAX  INTEGER {
                    delete(1),
                    add(2)
                }
            ACCESS  read-write
            STATUS  mandatory
            DESCRIPTION
                "Add / Delete Vlan to MSTP Instance"
            ::= { ge8MstpInstanceTable 3 }

        ge8MstpInstanceVlanFrom  OBJECT-TYPE
            SYNTAX  INTEGER (1..4094)
            ACCESS  read-write
            STATUS  mandatory
            DESCRIPTION
                "Add / Delete From Which Vlan For MSTP Instance"
            ::= { ge8MstpInstanceTable 4 }

        ge8MstpInstanceVlanTo  OBJECT-TYPE
            SYNTAX  INTEGER (1..4094)
            ACCESS  read-write
            STATUS  mandatory
            DESCRIPTION
                "Add / Delete To Which Vlan For MSTP Instance"
            ::= { ge8MstpInstanceTable 5 }

        ge8MstpInstanceActive  OBJECT-TYPE
            SYNTAX  INTEGER {
                    none(1),
                    activate(2)
                }
            ACCESS  read-write
            STATUS  mandatory
            DESCRIPTION
                "Active Setting To MSTP Instance"
            ::= { ge8MstpInstanceTable 6 }


--
--  ge8MstpInstPriorTable
--

        ge8MstpInstPriorTable  OBJECT-TYPE
            SYNTAX  SEQUENCE OF  Ge8MstpInstPriorEntry
            ACCESS  not-accessible
            STATUS  mandatory
            DESCRIPTION
                "The 8GESW  MSTP Instance Priority and Display Table."
            ::= { ge8StpGroup 4 }

        ge8MstpInstPriorEntry  OBJECT-TYPE
            SYNTAX  Ge8MstpInstPriorEntry
            ACCESS  not-accessible
            STATUS  mandatory
            DESCRIPTION
                "An entry in The 8GESW  MSTP Instance Priority and Display Table."
            INDEX { ge8MstpInstPriorUnit , ge8MstpInstPriorInstance }
            ::= { ge8MstpInstPriorTable 1 }

        Ge8MstpInstPriorEntry ::= SEQUENCE {
            ge8MstpInstPriorUnit         UnitID,
            ge8MstpInstPriorInstance     INTEGER,
            ge8MstpInstPriorPriority     INTEGER,
            ge8MstpInstPriorVlanMap      DisplayString
        }

        ge8MstpInstPriorUnit  OBJECT-TYPE
            SYNTAX  UnitID
            ACCESS  read-only
            STATUS  mandatory
            DESCRIPTION
                "unit index"
            ::= { ge8MstpInstPriorEntry 1 }

        ge8MstpInstPriorInstance  OBJECT-TYPE
            SYNTAX  INTEGER (1..64)
            ACCESS  read-only
            STATUS  mandatory
            DESCRIPTION
                "Mstp Instance 1~64"
            ::= { ge8MstpInstPriorEntry 2 }

        ge8MstpInstPriorPriority  OBJECT-TYPE
            SYNTAX  INTEGER {
                    priority0(1),
                    priority4096(2),
                    priority8192(3),
                    priority12288(4),
                    priority16384(5),
                    priority20480(6),
                    priority24576(7),
                    priority28672(8),
                    priority32768(9),
                    priority36864(10),
                    priority40960(11),
                    priority45056(12),
                    priority49152(13),
                    priority53248(14),
                    priority57344(15),
                    priority61440(16),
                    notAvailable(30)
                }
            ACCESS  read-write
            STATUS  mandatory
            DESCRIPTION
                "Mstp Instance Priority"
            ::= { ge8MstpInstPriorEntry 3 }

        ge8MstpInstPriorVlanMap  OBJECT-TYPE
            SYNTAX  DisplayString
            ACCESS  read-only
            STATUS  mandatory
            DESCRIPTION
                "Vlan Mapping For Mstp Instance"
            ::= { ge8MstpInstPriorEntry 4 }


--
--  ge8MstpPortInfoTable
--
        ge8MstpPortInfoTable  OBJECT-TYPE
            SYNTAX  SEQUENCE OF  Ge8MstpPortInfoEntry
            ACCESS  not-accessible
            STATUS  mandatory
            DESCRIPTION
                "The 8GESW  MSTP port Info Table."
            ::= { ge8StpGroup 5 }

        ge8MstpPortInfoEntry  OBJECT-TYPE
            SYNTAX  Ge8MstpPortInfoEntry
            ACCESS  not-accessible
            STATUS  mandatory
            DESCRIPTION
                "An entry in The 8GESW  MSTP port Info Table."
            INDEX { ge8MstpPortInfoUnit , ge8MstpPortInfoInstance , ge8MstpPortInfoPort }
            ::= { ge8MstpPortInfoTable 1 }

        Ge8MstpPortInfoEntry ::= SEQUENCE {
            ge8MstpPortInfoUnit          UnitID,
            ge8MstpPortInfoInstance      INTEGER,
            ge8MstpPortInfoPort          Ge8SwPort,
            ge8MstpPortInfoRole          INTEGER,
            ge8MstpPortInfoState         INTEGER,
            ge8MstpPortInfoCost          Gauge32,
            ge8MstpPortInfoCostSet       INTEGER,
            ge8MstpPortInfoPrior         INTEGER,
            ge8MstpPortInfoPriorSet      INTEGER,
            ge8MstpPortInfoEdge          INTEGER,
            ge8MstpPortInfoEdgeSet       INTEGER,
            ge8MstpPortInfoType          INTEGER,
            ge8MstpPortInfoTypeSet       INTEGER,
            ge8MstpPortInfoBoundary      INTEGER
        }

        ge8MstpPortInfoUnit  OBJECT-TYPE
            SYNTAX  UnitID
            ACCESS  read-only
            STATUS  mandatory
            DESCRIPTION
                "unit index"
            ::= { ge8MstpPortInfoEntry 1 }

        ge8MstpPortInfoInstance  OBJECT-TYPE
            SYNTAX  INTEGER (0..64)
            ACCESS  read-only
            STATUS  mandatory
            DESCRIPTION
                "Mstp Instance 0~64"
            ::= { ge8MstpPortInfoEntry 2 }

        ge8MstpPortInfoPort  OBJECT-TYPE
            SYNTAX  Ge8SwPort
            ACCESS  read-only
            STATUS  mandatory
            DESCRIPTION
                "Port WAN1~4, LAN1~8."
            ::= { ge8MstpPortInfoEntry 3 }

        ge8MstpPortInfoRole  OBJECT-TYPE
            SYNTAX  INTEGER {
                    master(1),
                    alternate(2),
                    root(3),
                    designated(4),
                    backup(5),
                    disabled(6),
                    boundary(7)
                }
            ACCESS  read-only
            STATUS  mandatory
            DESCRIPTION
                "MSTP port Role"
            ::= { ge8MstpPortInfoEntry 4 }

        ge8MstpPortInfoState  OBJECT-TYPE
            SYNTAX  INTEGER {
                    disable(1),
                    listening(2),
                    learning(3),
                    forwarding(4),
                    blocking(5)
                }
            ACCESS  read-only
            STATUS  mandatory
            DESCRIPTION
                "MSTP port State"
            ::= { ge8MstpPortInfoEntry 5 }

        ge8MstpPortInfoCost  OBJECT-TYPE
            SYNTAX  Gauge32
            ACCESS  read-only
            STATUS  mandatory
            DESCRIPTION
                "MSTP port Cost"
            ::= { ge8MstpPortInfoEntry 6 }

        ge8MstpPortInfoCostSet  OBJECT-TYPE
            SYNTAX  INTEGER (1..200000000)
            ACCESS  read-write
            STATUS  mandatory
            DESCRIPTION
                "MSTP port Cost Set"
            ::= { ge8MstpPortInfoEntry 7 }

        ge8MstpPortInfoPrior  OBJECT-TYPE
            SYNTAX  INTEGER {
                    priority0(1),
                    priority16(2),
                    priority32(3),
                    priority48(4),
                    priority64(5),
                    priority80(6),
                    priority96(7),
                    priority112(8),
                    priority128(9),
                    priority144(10),
                    priority160(11),
                    priority176(12),
                    priority192(13),
                    priority208(14),
                    priority224(15),
                    priority240(16)
                }
            ACCESS  read-only
            STATUS  mandatory
            DESCRIPTION
                "MSTP port Priority"
            ::= { ge8MstpPortInfoEntry 8 }

        ge8MstpPortInfoPriorSet  OBJECT-TYPE
            SYNTAX  INTEGER {
                    priority0(1),
                    priority16(2),
                    priority32(3),
                    priority48(4),
                    priority64(5),
                    priority80(6),
                    priority96(7),
                    priority112(8),
                    priority128(9),
                    priority144(10),
                    priority160(11),
                    priority176(12),
                    priority192(13),
                    priority208(14),
                    priority224(15),
                    priority240(16)
                }
            ACCESS  read-write
            STATUS  mandatory
            DESCRIPTION
                "MSTP port Priority Set"
            ::= { ge8MstpPortInfoEntry 9 }

        ge8MstpPortInfoEdge  OBJECT-TYPE
            SYNTAX  INTEGER {
                    no(1),
                    yes(2),
                    notAvailable(10)
                }
            ACCESS  read-only
            STATUS  mandatory
            DESCRIPTION
                "MSTP port Edge Port"
            ::= { ge8MstpPortInfoEntry 10 }

        ge8MstpPortInfoEdgeSet  OBJECT-TYPE
            SYNTAX  INTEGER {
                    no(1),
                    yes(2),
                    notAvailable(10)
                }
            ACCESS  read-write
            STATUS  mandatory
            DESCRIPTION
                "MSTP port Edge Port Set"
            ::= { ge8MstpPortInfoEntry 11 }

        ge8MstpPortInfoType  OBJECT-TYPE
            SYNTAX  INTEGER {
                    share(1),
                    pointToPoint(2),
                    auto(3),
                    notAvailable(10)
                }
            ACCESS  read-only
            STATUS  mandatory
            DESCRIPTION
                "MSTP port Link Type"
            ::= { ge8MstpPortInfoEntry 12 }

        ge8MstpPortInfoTypeSet  OBJECT-TYPE
            SYNTAX  INTEGER {
                    share(1),
                    pointToPoint(2),
                    auto(3),
                    notAvailable(10)
                }
            ACCESS  read-write
            STATUS  mandatory
            DESCRIPTION
                "MSTP port Link Type Set"
            ::= { ge8MstpPortInfoEntry 13 }

        ge8MstpPortInfoBoundary  OBJECT-TYPE
            SYNTAX  INTEGER {
                    internal(1),
                    boundStp(2),
                    boundRstp(3),
                    boundMstp(4),
                    notAvailable(10)
                }
            ACCESS  read-only
            STATUS  mandatory
            DESCRIPTION
                "MSTP port Link Type"
            ::= { ge8MstpPortInfoEntry 14 }


--
--  ge8RstpPortInfoTable
--
        ge8RstpPortInfoTable  OBJECT-TYPE
            SYNTAX  SEQUENCE OF  Ge8RstpPortInfoEntry
            ACCESS  not-accessible
            STATUS  mandatory
            DESCRIPTION
                "The 8GESW  RSTP port Info Table."
            ::= { ge8StpGroup 6 }

        ge8RstpPortInfoEntry  OBJECT-TYPE
            SYNTAX  Ge8RstpPortInfoEntry
            ACCESS  not-accessible
            STATUS  mandatory
            DESCRIPTION
                "An entry in The 8GESW  RSTP port Info Table."
            INDEX { ge8RstpPortInfoUnit , ge8RstpPortInfoPort }
            ::= { ge8RstpPortInfoTable 1 }

        Ge8RstpPortInfoEntry ::= SEQUENCE {
            ge8RstpPortInfoUnit          UnitID,
            ge8RstpPortInfoPort          Ge8SwPort,
            ge8RstpPortInfoRole          INTEGER,
            ge8RstpPortInfoState         INTEGER,
            ge8RstpPortInfoCost          Gauge32,
            ge8RstpPortInfoCostSet       INTEGER,
            ge8RstpPortInfoPrior         INTEGER,
            ge8RstpPortInfoPriorSet      INTEGER,
            ge8RstpPortInfoEdge          INTEGER,
            ge8RstpPortInfoEdgeSet       INTEGER,
            ge8RstpPortInfoType          INTEGER,
            ge8RstpPortInfoTypeSet       INTEGER
        }

        ge8RstpPortInfoUnit  OBJECT-TYPE
            SYNTAX  UnitID
            ACCESS  read-only
            STATUS  mandatory
            DESCRIPTION
                "unit index"
            ::= { ge8RstpPortInfoEntry 1 }

        ge8RstpPortInfoPort  OBJECT-TYPE
            SYNTAX  Ge8SwPort
            ACCESS  read-only
            STATUS  mandatory
            DESCRIPTION
                "Port WAN1~4, LAN1~8."
            ::= { ge8RstpPortInfoEntry 2 }

        ge8RstpPortInfoRole  OBJECT-TYPE
            SYNTAX  INTEGER {
                    master(1),
                    alternate(2),
                    root(3),
                    designated(4),
                    backup(5),
                    disabled(6),
                    boundary(7)
                }
            ACCESS  read-only
            STATUS  mandatory
            DESCRIPTION
                "RSTP port Role"
            ::= { ge8RstpPortInfoEntry 3 }

        ge8RstpPortInfoState  OBJECT-TYPE
            SYNTAX  INTEGER {
                    disable(1),
                    listening(2),
                    learning(3),
                    forwarding(4),
                    blocking(5)
                }
            ACCESS  read-only
            STATUS  mandatory
            DESCRIPTION
                "RSTP port State"
            ::= { ge8RstpPortInfoEntry 4 }

        ge8RstpPortInfoCost  OBJECT-TYPE
            SYNTAX  Gauge32
            ACCESS  read-only
            STATUS  mandatory
            DESCRIPTION
                "RSTP port Cost"
            ::= { ge8RstpPortInfoEntry 5 }

        ge8RstpPortInfoCostSet  OBJECT-TYPE
            SYNTAX  INTEGER (1..200000000)
            ACCESS  read-write
            STATUS  mandatory
            DESCRIPTION
                "RSTP port Cost Set"
            ::= { ge8RstpPortInfoEntry 6 }

        ge8RstpPortInfoPrior  OBJECT-TYPE
            SYNTAX  INTEGER {
                    priority0(1),
                    priority16(2),
                    priority32(3),
                    priority48(4),
                    priority64(5),
                    priority80(6),
                    priority96(7),
                    priority112(8),
                    priority128(9),
                    priority144(10),
                    priority160(11),
                    priority176(12),
                    priority192(13),
                    priority208(14),
                    priority224(15),
                    priority240(16)
                }
            ACCESS  read-only
            STATUS  mandatory
            DESCRIPTION
                "RSTP port Priority"
            ::= { ge8RstpPortInfoEntry 7 }

        ge8RstpPortInfoPriorSet  OBJECT-TYPE
            SYNTAX  INTEGER {
                    priority0(1),
                    priority16(2),
                    priority32(3),
                    priority48(4),
                    priority64(5),
                    priority80(6),
                    priority96(7),
                    priority112(8),
                    priority128(9),
                    priority144(10),
                    priority160(11),
                    priority176(12),
                    priority192(13),
                    priority208(14),
                    priority224(15),
                    priority240(16)
                }
            ACCESS  read-write
            STATUS  mandatory
            DESCRIPTION
                "RSTP port Priority Set"
            ::= { ge8RstpPortInfoEntry 8 }

        ge8RstpPortInfoEdge  OBJECT-TYPE
            SYNTAX  INTEGER {
                    no(1),
                    yes(2)
                }
            ACCESS  read-only
            STATUS  mandatory
            DESCRIPTION
                "RSTP port Edge Port"
            ::= { ge8RstpPortInfoEntry 9 }

        ge8RstpPortInfoEdgeSet  OBJECT-TYPE
            SYNTAX  INTEGER {
                    no(1),
                    yes(2)
                }
            ACCESS  read-write
            STATUS  mandatory
            DESCRIPTION
                "RSTP port Edge Port Set"
            ::= { ge8RstpPortInfoEntry 10 }

        ge8RstpPortInfoType  OBJECT-TYPE
            SYNTAX  INTEGER {
                    share(1),
                    pointToPoint(2),
                    auto(3)
                }
            ACCESS  read-only
            STATUS  mandatory
            DESCRIPTION
                "RSTP port Link Type"
            ::= { ge8RstpPortInfoEntry 11 }

        ge8RstpPortInfoTypeSet  OBJECT-TYPE
            SYNTAX  INTEGER {
                    share(1),
                    pointToPoint(2),
                    auto(3)
                }
            ACCESS  read-write
            STATUS  mandatory
            DESCRIPTION
                "RSTP port Link Type Set"
            ::= { ge8RstpPortInfoEntry 12 }


--
--  ge8RstpBrgInfoTable
--
        ge8RstpBrgInfoTable  OBJECT-TYPE
            SYNTAX  SEQUENCE OF  Ge8RstpBrgInfoEntry
            ACCESS  not-accessible
            STATUS  mandatory
            DESCRIPTION
                "The 8GESW  RSTP bridge info Table."
            ::= { ge8StpGroup 7 }

        ge8RstpBrgInfoEntry  OBJECT-TYPE
            SYNTAX  Ge8RstpBrgInfoEntry
            ACCESS  not-accessible
            STATUS  mandatory
            DESCRIPTION
                "An entry in The 8GESW  STP bridge info Table."
            INDEX { ge8RstpBrgUnit }
            ::= { ge8RstpBrgInfoTable 1 }

        Ge8RstpBrgInfoEntry ::= SEQUENCE {
            ge8RstpBrgUnit               UnitID,
            ge8RstpBrgEnable             INTEGER,
            ge8RstpBrgMacAddr            DisplayString,
            ge8RstpBrgPriority           INTEGER,
            ge8RstpBrgMaxAge             INTEGER,
            ge8RstpBrgHelloTime          INTEGER,
            ge8RstpBrgFwdDelay           INTEGER
        }

        ge8RstpBrgUnit  OBJECT-TYPE
            SYNTAX  UnitID
            ACCESS  read-only
            STATUS  mandatory
            DESCRIPTION
                "unit index"
            ::= { ge8RstpBrgInfoEntry 1 }

        ge8RstpBrgEnable  OBJECT-TYPE
            SYNTAX  INTEGER {
                    disable(1),
                    enable(2)
                }
            ACCESS  read-write
            STATUS  mandatory
            DESCRIPTION
                "RSTP enable/disable"
            ::= { ge8RstpBrgInfoEntry 2 }

        ge8RstpBrgMacAddr  OBJECT-TYPE
            SYNTAX  DisplayString
            ACCESS  read-only
            STATUS  mandatory
            DESCRIPTION
                "Bridge ID MAC ADDR"
            ::= { ge8RstpBrgInfoEntry 3 }

        ge8RstpBrgPriority  OBJECT-TYPE
            SYNTAX  INTEGER {
                    priority0(1),
                    priority4096(2),
                    priority8192(3),
                    priority12288(4),
                    priority16384(5),
                    priority20480(6),
                    priority24576(7),
                    priority28672(8),
                    priority32768(9),
                    priority36864(10),
                    priority40960(11),
                    priority45056(12),
                    priority49152(13),
                    priority53248(14),
                    priority57344(15),
                    priority61440(16)
                }
            ACCESS  read-write
            STATUS  mandatory
            DESCRIPTION
                "Bridge ID Priority"
            ::= { ge8RstpBrgInfoEntry 4 }

        ge8RstpBrgMaxAge  OBJECT-TYPE
            SYNTAX  INTEGER (4..40)
            ACCESS  read-write
            STATUS  mandatory
            DESCRIPTION
                "Bridge Max Age"
            ::= { ge8RstpBrgInfoEntry 5 }

        ge8RstpBrgHelloTime  OBJECT-TYPE
            SYNTAX  INTEGER (1..10)
            ACCESS  read-write
            STATUS  mandatory
            DESCRIPTION
                "Bridge Hello Time"
            ::= { ge8RstpBrgInfoEntry 6 }

        ge8RstpBrgFwdDelay  OBJECT-TYPE
            SYNTAX  INTEGER (4..30)
            ACCESS  read-write
            STATUS  mandatory
            DESCRIPTION
                "Bridge Forward Delay"
            ::= { ge8RstpBrgInfoEntry 7 }




--
--  ge8MstpBrgIDTable
--

        ge8MstpBrgIDTable  OBJECT-TYPE
            SYNTAX  SEQUENCE OF  Ge8MstpBrgIDEntry
            ACCESS  not-accessible
            STATUS  mandatory
            DESCRIPTION
                "The 8GESW  MSTP Bridge ID Display Table."
            ::= { ge8StpGroup 8 }

        ge8MstpBrgIDEntry  OBJECT-TYPE
            SYNTAX  Ge8MstpBrgIDEntry
            ACCESS  not-accessible
            STATUS  mandatory
            DESCRIPTION
                "An entry in The 8GESW  MSTP Bridge ID Display Table."
            INDEX { ge8MstpBrgIDUnit, ge8MstpBrgIDInstance }
            ::= { ge8MstpBrgIDTable 1 }

        Ge8MstpBrgIDEntry ::= SEQUENCE {
            ge8MstpBrgIDUnit         UnitID,
            ge8MstpBrgIDInstance     INTEGER,
            ge8MstpBrgIDBrgMacAddr   DisplayString,
            ge8MstpBrgIDBrgPrior     INTEGER,
            ge8MstpBrgIDRootMacAddr  DisplayString,
            ge8MstpBrgIDRootPrior    INTEGER
        }

        ge8MstpBrgIDUnit  OBJECT-TYPE
            SYNTAX  UnitID
            ACCESS  read-only
            STATUS  mandatory
            DESCRIPTION
                "unit index"
            ::= { ge8MstpBrgIDEntry 1 }

        ge8MstpBrgIDInstance  OBJECT-TYPE
            SYNTAX  INTEGER (0..64)
            ACCESS  read-only
            STATUS  mandatory
            DESCRIPTION
                "Mstp Instance 0~64"
            ::= { ge8MstpBrgIDEntry 2 }

        ge8MstpBrgIDBrgMacAddr  OBJECT-TYPE
            SYNTAX  DisplayString
            ACCESS  read-only
            STATUS  mandatory
            DESCRIPTION
                "Bridge ID MAC ADDR"
            ::= { ge8MstpBrgIDEntry 3 }

        ge8MstpBrgIDBrgPrior  OBJECT-TYPE
            SYNTAX  INTEGER {
                    priority0(1),
                    priority4096(2),
                    priority8192(3),
                    priority12288(4),
                    priority16384(5),
                    priority20480(6),
                    priority24576(7),
                    priority28672(8),
                    priority32768(9),
                    priority36864(10),
                    priority40960(11),
                    priority45056(12),
                    priority49152(13),
                    priority53248(14),
                    priority57344(15),
                    priority61440(16)
                }
            ACCESS  read-only
            STATUS  mandatory
            DESCRIPTION
                "Bridge ID Priority"
            ::= { ge8MstpBrgIDEntry 4 }

        ge8MstpBrgIDRootMacAddr  OBJECT-TYPE
            SYNTAX  DisplayString
            ACCESS  read-only
            STATUS  mandatory
            DESCRIPTION
                "Root MAC ADDR"
            ::= { ge8MstpBrgIDEntry 5 }

        ge8MstpBrgIDRootPrior  OBJECT-TYPE
            SYNTAX  INTEGER {
                    priority0(1),
                    priority4096(2),
                    priority8192(3),
                    priority12288(4),
                    priority16384(5),
                    priority20480(6),
                    priority24576(7),
                    priority28672(8),
                    priority32768(9),
                    priority36864(10),
                    priority40960(11),
                    priority45056(12),
                    priority49152(13),
                    priority53248(14),
                    priority57344(15),
                    priority61440(16)
                }
            ACCESS  read-only
            STATUS  mandatory
            DESCRIPTION
                "Root Priority"
            ::= { ge8MstpBrgIDEntry 6 }

--
--   ge8FlowControlTable
--
        ge8FlowControlTable  OBJECT-TYPE
            SYNTAX  SEQUENCE OF  Ge8FlowControlEntry
            ACCESS  not-accessible
            STATUS  mandatory
            DESCRIPTION
                "The 8GESW  Flow Control Table."
            ::= { ge8SwitchGroup 6 }

        ge8FlowControlEntry  OBJECT-TYPE
            SYNTAX  Ge8FlowControlEntry
            ACCESS  not-accessible
            STATUS  mandatory
            DESCRIPTION
                "An entry in the 8GESW  Flow Control Table."
            INDEX { ge8FlowCtrlUnit , ge8FlowCtrlPort }
            ::= { ge8FlowControlTable 1 }

        Ge8FlowControlEntry ::= SEQUENCE {
            ge8FlowCtrlUnit              UnitID,
            ge8FlowCtrlPort              Ge8SwPort,
            ge8FlowCtrlFlowCtrl          INTEGER
        }

        ge8FlowCtrlUnit  OBJECT-TYPE
            SYNTAX  UnitID
            ACCESS  read-only
            STATUS  mandatory
            DESCRIPTION
                "unit index"
            ::= { ge8FlowControlEntry 1 }

        ge8FlowCtrlPort  OBJECT-TYPE
            SYNTAX  Ge8SwPort
            ACCESS  read-only
            STATUS  mandatory
            DESCRIPTION
                "Port WAN1~4, LAN1~8."
            ::= { ge8FlowControlEntry 2 }

        ge8FlowCtrlFlowCtrl  OBJECT-TYPE
            SYNTAX  INTEGER {
                    off(1),
                    on(2)
                }
            ACCESS  read-write
            STATUS  mandatory
            DESCRIPTION
                "Flow Control ON/OFF"
            ::= { ge8FlowControlEntry 3 }


--
--   ge8IgmpSnoop
--
    ge8IgmpSnoop  OBJECT IDENTIFIER ::= { ge8SwitchGroup 7 }


--
--   ge8IgmpSnoopingTable
--
        ge8IgmpSnoopingTable  OBJECT-TYPE
            SYNTAX  SEQUENCE OF  Ge8IgmpSnoopingEntry
            ACCESS  not-accessible
            STATUS  mandatory
            DESCRIPTION
                "The 8GESW  IGMP Snooping Table."
            ::= { ge8IgmpSnoop 1 }

        ge8IgmpSnoopingEntry  OBJECT-TYPE
            SYNTAX  Ge8IgmpSnoopingEntry
            ACCESS  not-accessible
            STATUS  mandatory
            DESCRIPTION
                "An entry in the 8GESW  IGMP Snooping Table."
            INDEX { ge8IgmpSnoopUnit }
            ::= { ge8IgmpSnoopingTable 1 }

        Ge8IgmpSnoopingEntry ::= SEQUENCE {
            ge8IgmpSnoopUnit             UnitID,
            ge8IgmpSnoopEnable           INTEGER,
            ge8IgmpSnoopQueryInterval    INTEGER
        }

        ge8IgmpSnoopUnit  OBJECT-TYPE
            SYNTAX  UnitID
            ACCESS  read-only
            STATUS  mandatory
            DESCRIPTION
                "unit index"
            ::= { ge8IgmpSnoopingEntry 1 }

        ge8IgmpSnoopEnable  OBJECT-TYPE
            SYNTAX  INTEGER {
                    off(1),
                    on(2)
                }
            ACCESS  read-write
            STATUS  mandatory
            DESCRIPTION
                "IGMP Snooping Enable/Disable"
            ::= { ge8IgmpSnoopingEntry 2 }

        ge8IgmpSnoopQueryInterval  OBJECT-TYPE
            SYNTAX  INTEGER (0..65535)
            ACCESS  read-write
            STATUS  mandatory
            DESCRIPTION
                "IGMP Last Query Interval (centi-seconds)"
            ::= { ge8IgmpSnoopingEntry 3 }


--
--   ge8IgmpFastLeaveTable
--
        ge8IgmpFastLeaveTable  OBJECT-TYPE
            SYNTAX  SEQUENCE OF  Ge8IgmpFastLeaveEntry
            ACCESS  not-accessible
            STATUS  mandatory
            DESCRIPTION
                "The 8GESW  IGMP Fast Leave Table."
            ::= { ge8IgmpSnoop 2 }

        ge8IgmpFastLeaveEntry  OBJECT-TYPE
            SYNTAX  Ge8IgmpFastLeaveEntry
            ACCESS  not-accessible
            STATUS  mandatory
            DESCRIPTION
                "An entry in the 8GESW  IGMP Fast Leave Table."
            INDEX { ge8IgmpFastLeaveUnit , ge8IgmpFastLeaveVid }
            ::= { ge8IgmpFastLeaveTable 1 }

        Ge8IgmpFastLeaveEntry ::= SEQUENCE {
            ge8IgmpFastLeaveUnit         UnitID,
            ge8IgmpFastLeaveVid          INTEGER,
            ge8IgmpFastLeaveFastLeave    INTEGER
        }

        ge8IgmpFastLeaveUnit  OBJECT-TYPE
            SYNTAX  UnitID
            ACCESS  read-only
            STATUS  mandatory
            DESCRIPTION
                "unit index"
            ::= { ge8IgmpFastLeaveEntry 1 }

        ge8IgmpFastLeaveVid  OBJECT-TYPE
            SYNTAX  INTEGER (1..4094)
            ACCESS  read-only
            STATUS  mandatory
            DESCRIPTION
                "VID 1 to 4094"
            ::= { ge8IgmpFastLeaveEntry 2 }

        ge8IgmpFastLeaveFastLeave  OBJECT-TYPE
            SYNTAX  INTEGER {
                    off(1),
                    on(2)
                }
            ACCESS  read-write
            STATUS  mandatory
            DESCRIPTION
                "IGMP Fast Leave"
            ::= { ge8IgmpFastLeaveEntry 3 }


--
--   ge8IgmpRouterPortTable
--
        ge8IgmpRouterPortTable  OBJECT-TYPE
            SYNTAX  SEQUENCE OF  Ge8IgmpRouterPortEntry
            ACCESS  not-accessible
            STATUS  mandatory
            DESCRIPTION
                "The 8GESW  IGMP Router Port Table."
            ::= { ge8IgmpSnoop 3 }

        ge8IgmpRouterPortEntry  OBJECT-TYPE
            SYNTAX  Ge8IgmpRouterPortEntry
            ACCESS  not-accessible
            STATUS  mandatory
            DESCRIPTION
                "An entry in the 8GESW  IGMP Router Port Table."
            INDEX { ge8IgmpRtrPrtUnit , ge8IgmpRtrPrtPort }
            ::= { ge8IgmpRouterPortTable 1 }

        Ge8IgmpRouterPortEntry ::= SEQUENCE {
            ge8IgmpRtrPrtUnit            UnitID,
            ge8IgmpRtrPrtPort            Ge8SwPort,
            ge8IgmpRtrPrtRouterPort      INTEGER
        }

        ge8IgmpRtrPrtUnit  OBJECT-TYPE
            SYNTAX  UnitID
            ACCESS  read-only
            STATUS  mandatory
            DESCRIPTION
                "unit index"
            ::= { ge8IgmpRouterPortEntry 1 }

        ge8IgmpRtrPrtPort  OBJECT-TYPE
            SYNTAX  Ge8SwPort
            ACCESS  read-only
            STATUS  mandatory
            DESCRIPTION
                "Port WAN1~4, LAN1~8."
            ::= { ge8IgmpRouterPortEntry 2 }

        ge8IgmpRtrPrtRouterPort  OBJECT-TYPE
            SYNTAX  INTEGER {
                    no(1),
                    yes(2)
                }
            ACCESS  read-write
            STATUS  mandatory
            DESCRIPTION
                "IGMP Router Port"
            ::= { ge8IgmpRouterPortEntry 3 }


--
--   ge8IgmpCrossVlanTable
--
        ge8IgmpCrossVlanTable  OBJECT-TYPE
            SYNTAX  SEQUENCE OF  Ge8IgmpCrossVlanEntry
            ACCESS  not-accessible
            STATUS  mandatory
            DESCRIPTION
                "The 8GESW  IGMP Cross VLAN Table."
            ::= { ge8IgmpSnoop 4 }

        ge8IgmpCrossVlanEntry  OBJECT-TYPE
            SYNTAX  Ge8IgmpCrossVlanEntry
            ACCESS  not-accessible
            STATUS  mandatory
            DESCRIPTION
                "An entry in the 8GESW  IGMP Cross VLAN Table."
            INDEX { ge8IgmpCrossVlanUnit }
            ::= { ge8IgmpCrossVlanTable 1 }

        Ge8IgmpCrossVlanEntry ::= SEQUENCE {
            ge8IgmpCrossVlanUnit         UnitID,
            ge8IgmpCrossVlanEnable       INTEGER,
            ge8IgmpCrossVlanVlanID       INTEGER
        }

        ge8IgmpCrossVlanUnit  OBJECT-TYPE
            SYNTAX  UnitID
            ACCESS  read-only
            STATUS  mandatory
            DESCRIPTION
                "unit index"
            ::= { ge8IgmpCrossVlanEntry 1 }

        ge8IgmpCrossVlanEnable  OBJECT-TYPE
            SYNTAX  INTEGER {
                    off(1),
                    on(2)
                }
            ACCESS  read-write
            STATUS  mandatory
            DESCRIPTION
                "Cross VLAN Enable/Disable"
            ::= { ge8IgmpCrossVlanEntry 2 }

        ge8IgmpCrossVlanVlanID  OBJECT-TYPE
            SYNTAX  INTEGER (0..65535)
            ACCESS  read-write
            STATUS  mandatory
            DESCRIPTION
                "Cross VLAN ID"
            ::= { ge8IgmpCrossVlanEntry 3 }


--
--   ge8IgmpMulticastIpTable
--
        ge8IgmpMulticastIpTable  OBJECT-TYPE
            SYNTAX  SEQUENCE OF  Ge8IgmpMulticastIpEntry
            ACCESS  not-accessible
            STATUS  mandatory
            DESCRIPTION
                "The 8GESW  IGMP Cross VLAN Table."
            ::= { ge8IgmpSnoop 5 }

        ge8IgmpMulticastIpEntry  OBJECT-TYPE
            SYNTAX  Ge8IgmpMulticastIpEntry
            ACCESS  not-accessible
            STATUS  mandatory
            DESCRIPTION
                "An entry in the 8GESW  IGMP Cross VLAN Table."
            INDEX { ge8IgmpMcIpUnit , ge8IgmpMcIpNumber }
            ::= { ge8IgmpMulticastIpTable 1 }

        Ge8IgmpMulticastIpEntry ::= SEQUENCE {
            ge8IgmpMcIpUnit              UnitID,
            ge8IgmpMcIpNumber            INTEGER,
            ge8IgmpMcIpMulticastIp       IpAddress,
            ge8IgmpMcIpWan1              INTEGER,
            ge8IgmpMcIpWan2              INTEGER,
            ge8IgmpMcIpWan3              INTEGER,
            ge8IgmpMcIpWan4              INTEGER,
            ge8IgmpMcIpLan1              INTEGER,
            ge8IgmpMcIpLan2              INTEGER,
            ge8IgmpMcIpLan3              INTEGER,
            ge8IgmpMcIpLan4              INTEGER,
            ge8IgmpMcIpLan5              INTEGER,
            ge8IgmpMcIpLan6              INTEGER,
            ge8IgmpMcIpLan7              INTEGER,
            ge8IgmpMcIpLan8              INTEGER
        }

        ge8IgmpMcIpUnit  OBJECT-TYPE
            SYNTAX  UnitID
            ACCESS  read-only
            STATUS  mandatory
            DESCRIPTION
                "unit index"
            ::= { ge8IgmpMulticastIpEntry 1 }

        ge8IgmpMcIpNumber  OBJECT-TYPE
            SYNTAX  INTEGER (1..32)
            ACCESS  read-only
            STATUS  mandatory
            DESCRIPTION
                "Number 1 to 32"
            ::= { ge8IgmpMulticastIpEntry 2 }

        ge8IgmpMcIpMulticastIp  OBJECT-TYPE
            SYNTAX  IpAddress
            ACCESS  read-write
            STATUS  mandatory
            DESCRIPTION
                "IGMP Multicast IP"
            ::= { ge8IgmpMulticastIpEntry 3 }

        ge8IgmpMcIpWan1  OBJECT-TYPE
            SYNTAX  INTEGER {
                    off(1),
                    on(2)
                }
            ACCESS  read-write
            STATUS  mandatory
            DESCRIPTION
                "Wan1 For IGMP Multicast IP"
            ::= { ge8IgmpMulticastIpEntry 4 }

        ge8IgmpMcIpWan2  OBJECT-TYPE
            SYNTAX  INTEGER {
                    off(1),
                    on(2)
                }
            ACCESS  read-write
            STATUS  mandatory
            DESCRIPTION
                "Wan2 For IGMP Multicast IP"
            ::= { ge8IgmpMulticastIpEntry 5 }

        ge8IgmpMcIpWan3  OBJECT-TYPE
            SYNTAX  INTEGER {
                    off(1),
                    on(2)
                }
            ACCESS  read-write
            STATUS  mandatory
            DESCRIPTION
                "Wan3 For IGMP Multicast IP"
            ::= { ge8IgmpMulticastIpEntry 6 }

        ge8IgmpMcIpWan4  OBJECT-TYPE
            SYNTAX  INTEGER {
                    off(1),
                    on(2)
                }
            ACCESS  read-write
            STATUS  mandatory
            DESCRIPTION
                "Wan4 For IGMP Multicast IP"
            ::= { ge8IgmpMulticastIpEntry 7 }

        ge8IgmpMcIpLan1  OBJECT-TYPE
            SYNTAX  INTEGER {
                    off(1),
                    on(2)
                }
            ACCESS  read-write
            STATUS  mandatory
            DESCRIPTION
                "Lan1 For IGMP Multicast IP"
            ::= { ge8IgmpMulticastIpEntry 8 }

        ge8IgmpMcIpLan2  OBJECT-TYPE
            SYNTAX  INTEGER {
                    off(1),
                    on(2)
                }
            ACCESS  read-write
            STATUS  mandatory
            DESCRIPTION
                "Lan2 For IGMP Multicast IP"
            ::= { ge8IgmpMulticastIpEntry 9 }

        ge8IgmpMcIpLan3  OBJECT-TYPE
            SYNTAX  INTEGER {
                    off(1),
                    on(2)
                }
            ACCESS  read-write
            STATUS  mandatory
            DESCRIPTION
                "Lan3 For IGMP Multicast IP"
            ::= { ge8IgmpMulticastIpEntry 10 }

        ge8IgmpMcIpLan4  OBJECT-TYPE
            SYNTAX  INTEGER {
                    off(1),
                    on(2)
                }
            ACCESS  read-write
            STATUS  mandatory
            DESCRIPTION
                "Lan4 For IGMP Multicast IP"
            ::= { ge8IgmpMulticastIpEntry 11 }

        ge8IgmpMcIpLan5  OBJECT-TYPE
            SYNTAX  INTEGER {
                    off(1),
                    on(2)
                }
            ACCESS  read-write
            STATUS  mandatory
            DESCRIPTION
                "Lan5 For IGMP Multicast IP"
            ::= { ge8IgmpMulticastIpEntry 12 }

        ge8IgmpMcIpLan6  OBJECT-TYPE
            SYNTAX  INTEGER {
                    off(1),
                    on(2)
                }
            ACCESS  read-write
            STATUS  mandatory
            DESCRIPTION
                "Lan6 For IGMP Multicast IP"
            ::= { ge8IgmpMulticastIpEntry 13 }

        ge8IgmpMcIpLan7  OBJECT-TYPE
            SYNTAX  INTEGER {
                    off(1),
                    on(2)
                }
            ACCESS  read-write
            STATUS  mandatory
            DESCRIPTION
                "Lan7 For IGMP Multicast IP"
            ::= { ge8IgmpMulticastIpEntry 14 }

        ge8IgmpMcIpLan8  OBJECT-TYPE
            SYNTAX  INTEGER {
                    off(1),
                    on(2)
                }
            ACCESS  read-write
            STATUS  mandatory
            DESCRIPTION
                "Lan8 For IGMP Multicast IP"
            ::= { ge8IgmpMulticastIpEntry 15 }


--
--   ge8IgmpMcIpRangeTable
--
        ge8IgmpMcIpRangeTable  OBJECT-TYPE
            SYNTAX  SEQUENCE OF  Ge8IgmpMcIpRangeEntry
            ACCESS  not-accessible
            STATUS  mandatory
            DESCRIPTION
                "The 8GESW  IGMP IP Multicast Range Table."
            ::= { ge8IgmpSnoop 6 }

        ge8IgmpMcIpRangeEntry  OBJECT-TYPE
            SYNTAX  Ge8IgmpMcIpRangeEntry
            ACCESS  not-accessible
            STATUS  mandatory
            DESCRIPTION
                "An entry in the 8GESW  IGMP IP Multicast Range Table."
            INDEX { ge8IgmpMcIpRangeUnit , ge8IgmpMcIpRangePort }
            ::= { ge8IgmpMcIpRangeTable 1 }

        Ge8IgmpMcIpRangeEntry ::= SEQUENCE {
            ge8IgmpMcIpRangeUnit         UnitID,
            ge8IgmpMcIpRangePort         Ge8SwPort,
            ge8IgmpMcIpRangeStart        IpAddress,
            ge8IgmpMcIpRangeEnd          IpAddress
        }

        ge8IgmpMcIpRangeUnit  OBJECT-TYPE
            SYNTAX  UnitID
            ACCESS  read-only
            STATUS  mandatory
            DESCRIPTION
                "unit index"
            ::= { ge8IgmpMcIpRangeEntry 1 }

        ge8IgmpMcIpRangePort  OBJECT-TYPE
            SYNTAX  Ge8SwPort
            ACCESS  read-only
            STATUS  mandatory
            DESCRIPTION
                "Port WAN1~4, LAN1~8."
            ::= { ge8IgmpMcIpRangeEntry 2 }

        ge8IgmpMcIpRangeStart  OBJECT-TYPE
            SYNTAX  IpAddress
            ACCESS  read-write
            STATUS  mandatory
            DESCRIPTION
                "Multicast IP Address Start"
            ::= { ge8IgmpMcIpRangeEntry  3 }

        ge8IgmpMcIpRangeEnd  OBJECT-TYPE
            SYNTAX  IpAddress
            ACCESS  read-write
            STATUS  mandatory
            DESCRIPTION
                "Multicast IP Address End"
            ::= { ge8IgmpMcIpRangeEntry  4 }


--
--   ge8IPMulticastTable
--
--        ge8IPMulticastTable  OBJECT-TYPE
--            SYNTAX  SEQUENCE OF  Ge8IPMulticastEntry
--            ACCESS  read-only
--            STATUS  mandatory
--            DESCRIPTION
--                "The 8GESW  IP Multicast Display Table."
--            ::= { ge8IgmpSnoop 7 }
--
--        ge8IPMulticastEntry  OBJECT-TYPE
--            SYNTAX  Ge8IPMulticastEntry
--            ACCESS  read-only
--            STATUS  mandatory
--            DESCRIPTION
--                "An entry in the 8GESW  IP Multicast Display Table."
--            INDEX { ge8IPMulticastUnit, ge8IPMulticastIndex }
--            ::= { ge8IPMulticastTable 1 }
--
--        Ge8IPMulticastEntry ::= SEQUENCE {
--            ge8IPMulticastUnit           UnitID,
--            ge8IPMulticastIndex          Gauge32,
--            ge8IPMulticastVlan           INTEGER,
--            ge8IPMulticastIp             IpAddress,
--            ge8IPMulticastWan1           INTEGER,
--            ge8IPMulticastWan2           INTEGER,
--            ge8IPMulticastWan3           INTEGER,
--            ge8IPMulticastWan4           INTEGER,
--            ge8IPMulticastLan1           INTEGER,
--            ge8IPMulticastLan2           INTEGER,
--            ge8IPMulticastLan3           INTEGER,
--            ge8IPMulticastLan4           INTEGER,
--            ge8IPMulticastLan5           INTEGER,
--            ge8IPMulticastLan6           INTEGER,
--            ge8IPMulticastLan7           INTEGER,
--            ge8IPMulticastLan8           INTEGER
--        }
--
--        ge8IPMulticastUnit  OBJECT-TYPE
--            SYNTAX  UnitID
--            ACCESS  read-only
--            STATUS  mandatory
--            DESCRIPTION
--                "unit index"
--            ::= { ge8IPMulticastEntry 1 }
--
--        ge8IPMulticastIndex  OBJECT-TYPE
--            SYNTAX  Gauge32
--            ACCESS  read-only
--            STATUS  mandatory
--            DESCRIPTION
--                "IP Multicast Display Table Index"
--            ::= { ge8IPMulticastEntry 2 }
--
--        ge8IPMulticastVlan  OBJECT-TYPE
--            SYNTAX  INTEGER (1..4094)
--            ACCESS  read-only
--            STATUS  mandatory
--            DESCRIPTION
--                "IP Multicast VlanID "
--            ::= { ge8IPMulticastEntry 3 }
--
--        ge8IPMulticastIp  OBJECT-TYPE
--            SYNTAX  IpAddress
--            ACCESS  read-only
--            STATUS  mandatory
--            DESCRIPTION
--                "IP Multicast IP address"
--            ::= { ge8IPMulticastEntry 4 }
--
--        ge8IPMulticastWan1  OBJECT-TYPE
--            SYNTAX  INTEGER {
--                    off(1),
--                    on(2)
--                }
--            ACCESS  read-only
--            STATUS  mandatory
--            DESCRIPTION
--                "IP Multicast WAN1 on/off"
--            ::= { ge8IPMulticastEntry 5 }
--
--        ge8IPMulticastWan2  OBJECT-TYPE
--            SYNTAX  INTEGER {
--                    off(1),
--                    on(2)
--                }
--            ACCESS  read-only
--            STATUS  mandatory
--            DESCRIPTION
--                "IP Multicast WAN2 on/off"
--            ::= { ge8IPMulticastEntry 6 }
--
--        ge8IPMulticastWan3  OBJECT-TYPE
--            SYNTAX  INTEGER {
--                    off(1),
--                    on(2)
--                }
--            ACCESS  read-only
--            STATUS  mandatory
--            DESCRIPTION
--                "IP Multicast WAN3 on/off"
--            ::= { ge8IPMulticastEntry 7 }
--
--
--        ge8IPMulticastWan4  OBJECT-TYPE
--            SYNTAX  INTEGER {
--                    off(1),
--                    on(2)
--                }
--            ACCESS  read-only
--            STATUS  mandatory
--            DESCRIPTION
--                "IP Multicast WAN4 on/off"
--            ::= { ge8IPMulticastEntry 8 }
--
--
--        ge8IPMulticastLan1  OBJECT-TYPE
--            SYNTAX  INTEGER {
--                    off(1),
--                    on(2)
--                }
--            ACCESS  read-only
--            STATUS  mandatory
--            DESCRIPTION
--                "IP Multicast LAN1 on/off"
--            ::= { ge8IPMulticastEntry 9 }
--
--        ge8IPMulticastLan2  OBJECT-TYPE
--            SYNTAX  INTEGER {
--                    off(1),
--                    on(2)
--                }
--            ACCESS  read-only
--            STATUS  mandatory
--            DESCRIPTION
--                "IP Multicast LAN2 on/off"
--            ::= { ge8IPMulticastEntry 10 }
--
--        ge8IPMulticastLan3  OBJECT-TYPE
--            SYNTAX  INTEGER {
--                    off(1),
--                    on(2)
--                }
--            ACCESS  read-only
--            STATUS  mandatory
--            DESCRIPTION
--                "IP Multicast LAN3 on/off"
--            ::= { ge8IPMulticastEntry 11 }
--
--
--        ge8IPMulticastLan4  OBJECT-TYPE
--            SYNTAX  INTEGER {
--                    off(1),
--                    on(2)
--                }
--            ACCESS  read-only
--            STATUS  mandatory
--            DESCRIPTION
--                "IP Multicast LAN4 on/off"
--            ::= { ge8IPMulticastEntry 12 }
--
--        ge8IPMulticastLan5  OBJECT-TYPE
--            SYNTAX  INTEGER {
--                    off(1),
--                    on(2)
--                }
--            ACCESS  read-only
--            STATUS  mandatory
--            DESCRIPTION
--                "IP Multicast LAN5 on/off"
--            ::= { ge8IPMulticastEntry 13 }
--
--        ge8IPMulticastLan6  OBJECT-TYPE
--            SYNTAX  INTEGER {
--                    off(1),
--                    on(2)
--                }
--            ACCESS  read-only
--            STATUS  mandatory
--            DESCRIPTION
--                "IP Multicast LAN6 on/off"
--            ::= { ge8IPMulticastEntry 14 }
--
--        ge8IPMulticastLan7  OBJECT-TYPE
--            SYNTAX  INTEGER {
--                    off(1),
--                    on(2)
--                }
--            ACCESS  read-only
--            STATUS  mandatory
--            DESCRIPTION
--                "IP Multicast LAN7 on/off"
--            ::= { ge8IPMulticastEntry 15 }
--
--        ge8IPMulticastLan8  OBJECT-TYPE
--            SYNTAX  INTEGER {
--                    off(1),
--                    on(2)
--                }
--            ACCESS  read-only
--            STATUS  mandatory
--            DESCRIPTION
--                "IP Multicast LAN8 on/off"
--            ::= { ge8IPMulticastEntry 16 }



--
--   ge8QosGroup
--
    ge8QosGroup  OBJECT IDENTIFIER ::= { ge8SwitchGroup 8 }

--
--   ge8QosEnableTable
--
        ge8QosEnableTable  OBJECT-TYPE
            SYNTAX  SEQUENCE OF  Ge8QosEnableEntry
            ACCESS  not-accessible
            STATUS  mandatory
            DESCRIPTION
                "The 8GESW  QoS Enable Table."
            ::= { ge8QosGroup 1 }

        ge8QosEnableEntry  OBJECT-TYPE
            SYNTAX  Ge8QosEnableEntry
            ACCESS  not-accessible
            STATUS  mandatory
            DESCRIPTION
                "An entry in the 8GESW  QoS Enable Table."
            INDEX { ge8QosEnUnit }
            ::= { ge8QosEnableTable 1 }

        Ge8QosEnableEntry ::= SEQUENCE {
            ge8QosEnUnit                UnitID,
            ge8QosEnable                INTEGER
        }

        ge8QosEnUnit  OBJECT-TYPE
            SYNTAX  UnitID
            ACCESS  read-only
            STATUS  mandatory
            DESCRIPTION
                "unit index"
            ::= { ge8QosEnableEntry 1 }

        ge8QosEnable  OBJECT-TYPE
            SYNTAX  INTEGER {
                    disable(1),
                    enable(2)
                }
            ACCESS  read-write
            STATUS  mandatory
            DESCRIPTION
                "QoS enable/disable"
            ::= { ge8QosEnableEntry 2 }


--
--   ge8QosTrustTable
--
        ge8QosTrustTable  OBJECT-TYPE
            SYNTAX  SEQUENCE OF  Ge8QosTrustEntry
            ACCESS  not-accessible
            STATUS  mandatory
            DESCRIPTION
                "The 8GESW  QoS Trust Table."
            ::= { ge8QosGroup 2 }

        ge8QosTrustEntry  OBJECT-TYPE
            SYNTAX  Ge8QosTrustEntry
            ACCESS  not-accessible
            STATUS  mandatory
            DESCRIPTION
                "An entry in the 8GESW  QoS Trust Table."
            INDEX { ge8QosTrUnit , ge8QosTrPort }
            ::= { ge8QosTrustTable 1 }

        Ge8QosTrustEntry ::= SEQUENCE {
            ge8QosTrUnit                UnitID,
            ge8QosTrPort                Ge8SwPort,
            ge8QosTrust                 INTEGER,
            ge8QosDefaultCos            INTEGER
        }

        ge8QosTrUnit  OBJECT-TYPE
            SYNTAX  UnitID
            ACCESS  read-only
            STATUS  mandatory
            DESCRIPTION
                "unit index"
            ::= { ge8QosTrustEntry 1 }

        ge8QosTrPort  OBJECT-TYPE
            SYNTAX  Ge8SwPort
            ACCESS  read-only
            STATUS  mandatory
            DESCRIPTION
                "Port WAN1~4, LAN1~8."
            ::= { ge8QosTrustEntry 2 }

        ge8QosTrust  OBJECT-TYPE
            SYNTAX  INTEGER {
                    dscp(1),
                    cos(2)
                }
            ACCESS  read-write
            STATUS  mandatory
            DESCRIPTION
                "QoS Trust mode"
            ::= { ge8QosTrustEntry 3 }

        ge8QosDefaultCos  OBJECT-TYPE
            SYNTAX  INTEGER {
                    cos0(1),
                    cos1(2),
                    cos2(3),
                    cos3(4),
                    cos4(5),
                    cos5(6),
                    cos6(7),
                    cos7(8)
                }
            ACCESS  read-write
            STATUS  mandatory
            DESCRIPTION
                "Default COS value"
            ::= { ge8QosTrustEntry 4 }


--
--   ge8MeterRuleProfileTable
--
        ge8MeterRuleProfileTable  OBJECT-TYPE
            SYNTAX  SEQUENCE OF  Ge8MeterRuleProfileEntry
            ACCESS  not-accessible
            STATUS  mandatory
            DESCRIPTION
                "The 8GESW  QoS Meter Rule Profile Table."
            ::= { ge8QosGroup 3 }

        ge8MeterRuleProfileEntry  OBJECT-TYPE
            SYNTAX  Ge8MeterRuleProfileEntry
            ACCESS  not-accessible
            STATUS  mandatory
            DESCRIPTION
                "An entry in the 8GESW  QoS Meter Rule Profile Table."
            INDEX { ge8MrPUnit , ge8MrProfile }
            ::= { ge8MeterRuleProfileTable 1 }

        Ge8MeterRuleProfileEntry ::= SEQUENCE {
            ge8MrPUnit                   UnitID,
            ge8MrProfile                 INTEGER,
            ge8MrRule                    INTEGER,
            ge8MrUnit                    INTEGER,
            ge8MrCIR                     INTEGER,
            ge8MrCBS                     INTEGER,
            ge8MrPIR                     INTEGER,
            ge8MrPBS                     INTEGER,
            ge8MrEBS                     INTEGER,
            ge8MrYellow                  INTEGER,
            ge8MrRed                     INTEGER,
            ge8MrRemark                  INTEGER
        }

        ge8MrPUnit  OBJECT-TYPE
            SYNTAX  UnitID
            ACCESS  read-only
            STATUS  mandatory
            DESCRIPTION
                "unit index"
            ::= { ge8MeterRuleProfileEntry 1 }

        ge8MrProfile  OBJECT-TYPE
            SYNTAX  INTEGER {
                    profile1(1),
                    profile2(2),
                    profile3(3),
                    profile4(4),
                    profile5(5),
                    profile6(6),
                    profile7(7),
                    profile8(8),
                    profile9(9),
                    profile10(10),
                    profile11(11),
                    profile12(12),
                    profile13(13),
                    profile14(14),
                    profile15(15),
                    profile16(16),
                    profile17(17),
                    profile18(18),
                    profile19(19),
                    profile20(20),
                    profile21(21),
                    profile22(22),
                    profile23(23),
                    profile24(24),
                    profile25(25),
                    profile26(26),
                    profile27(27),
                    profile28(28),
                    profile29(29),
                    profile30(30),
                    profile31(31),
                    profile32(32),
                    profile33(33),
                    profile34(34),
                    profile35(35),
                    profile36(36),
                    profile37(37),
                    profile38(38),
                    profile39(39),
                    profile40(40),
                    profile41(41),
                    profile42(42),
                    profile43(43),
                    profile44(44),
                    profile45(45),
                    profile46(46),
                    profile47(47),
                    profile48(48)
                }
            ACCESS  read-only
            STATUS  mandatory
            DESCRIPTION
                "profile index"
            ::= { ge8MeterRuleProfileEntry 2 }

        ge8MrRule  OBJECT-TYPE
            SYNTAX  INTEGER {
                    trtc(1),
                    srtc(2)
                }
            ACCESS  read-write
            STATUS  mandatory
            DESCRIPTION
                "Meter rule"
            ::= { ge8MeterRuleProfileEntry 3 }

        ge8MrUnit  OBJECT-TYPE
            SYNTAX  INTEGER {
                    unit1Kbps(1),
                    unit1Mbps(2)
                }
            ACCESS  read-only
            STATUS  mandatory
            DESCRIPTION
                "Meter rate"
            ::= { ge8MeterRuleProfileEntry 4 }

        ge8MrCIR  OBJECT-TYPE
            SYNTAX  INTEGER (1..1000000)
            ACCESS  read-write
            STATUS  mandatory
            DESCRIPTION
                "TRTC:CIR, SRTC:CIR"
            ::= { ge8MeterRuleProfileEntry 5 }

        ge8MrCBS  OBJECT-TYPE
            SYNTAX  INTEGER (1..512000)
            ACCESS  read-write
            STATUS  mandatory
            DESCRIPTION
                "TRTC:CBS, SRTC:CBS"
            ::= { ge8MeterRuleProfileEntry 6 }

        ge8MrPIR  OBJECT-TYPE
            SYNTAX  INTEGER (1..1000000)
            ACCESS  read-write
            STATUS  mandatory
            DESCRIPTION
                "TRTC:PIR"
            ::= { ge8MeterRuleProfileEntry 7 }

        ge8MrPBS  OBJECT-TYPE
            SYNTAX  INTEGER (1..512000)
            ACCESS  read-write
            STATUS  mandatory
            DESCRIPTION
                "TRTC:PBS"
            ::= { ge8MeterRuleProfileEntry 8 }

        ge8MrEBS  OBJECT-TYPE
            SYNTAX  INTEGER (1..512000)
            ACCESS  read-write
            STATUS  mandatory
            DESCRIPTION
                "SRTC:EBS"
            ::= { ge8MeterRuleProfileEntry 9 }

        ge8MrYellow  OBJECT-TYPE
            SYNTAX  INTEGER {
                    keep(1),
                    drop(2),
                    remark(3)
                }
            ACCESS  read-write
            STATUS  mandatory
            DESCRIPTION
                "Meter: yellow action"
            ::= { ge8MeterRuleProfileEntry 10 }

        ge8MrRed  OBJECT-TYPE
            SYNTAX  INTEGER {
                    keep(1),
                    drop(2),
                    remark(3)
                }
            ACCESS  read-write
            STATUS  mandatory
            DESCRIPTION
                "Meter: red action"
            ::= { ge8MeterRuleProfileEntry 11 }

        ge8MrRemark  OBJECT-TYPE
            SYNTAX  INTEGER (0..63)
            ACCESS  read-write
            STATUS  mandatory
            DESCRIPTION
                "Meter: remark value"
            ::= { ge8MeterRuleProfileEntry 12 }


--
--   ge8QosVcgBindTable
--
        ge8QosVcgBindTable  OBJECT-TYPE
            SYNTAX  SEQUENCE OF  Ge8QosVcgBindEntry
            ACCESS  not-accessible
            STATUS  mandatory
            DESCRIPTION
                "The 8GESW  QoS Bind VCG to Profile Table."
            ::= { ge8QosGroup 4 }

        ge8QosVcgBindEntry  OBJECT-TYPE
            SYNTAX  Ge8QosVcgBindEntry
            ACCESS  not-accessible
            STATUS  mandatory
            DESCRIPTION
                "An entry in the 8GESW  QoS Bind VCG to Profile Table."
            INDEX { ge8QvBindUnit , ge8QvBindVcg , ge8QvBindDirection }
            ::= { ge8QosVcgBindTable 1 }

        Ge8QosVcgBindEntry ::= SEQUENCE {
            ge8QvBindUnit             UnitID,
            ge8QvBindVcg              INTEGER,
            ge8QvBindDirection        INTEGER,
            ge8QvBindProfile          INTEGER
        }

        ge8QvBindUnit  OBJECT-TYPE
            SYNTAX  UnitID
            ACCESS  read-only
            STATUS  mandatory
            DESCRIPTION
                "unit index"
            ::= { ge8QosVcgBindEntry 1 }

        ge8QvBindVcg  OBJECT-TYPE
            SYNTAX  INTEGER (1..48)
            ACCESS  read-only
            STATUS  mandatory
            DESCRIPTION
                "vcg rx/tx"
            ::= { ge8QosVcgBindEntry 2 }

        ge8QvBindDirection  OBJECT-TYPE
            SYNTAX  INTEGER {
                    tx(1),
                    rx(2)
                }
            ACCESS  read-only
            STATUS  mandatory
            DESCRIPTION
                "vcg rx/tx"
            ::= { ge8QosVcgBindEntry 3 }

        ge8QvBindProfile  OBJECT-TYPE
            SYNTAX  INTEGER {
                    no(0),
                    profile1(1),
                    profile2(2),
                    profile3(3),
                    profile4(4),
                    profile5(5),
                    profile6(6),
                    profile7(7),
                    profile8(8),
                    profile9(9),
                    profile10(10),
                    profile11(11),
                    profile12(12),
                    profile13(13),
                    profile14(14),
                    profile15(15),
                    profile16(16),
                    profile17(17),
                    profile18(18),
                    profile19(19),
                    profile20(20),
                    profile21(21),
                    profile22(22),
                    profile23(23),
                    profile24(24),
                    profile25(25),
                    profile26(26),
                    profile27(27),
                    profile28(28),
                    profile29(29),
                    profile30(30),
                    profile31(31),
                    profile32(32),
                    profile33(33),
                    profile34(34),
                    profile35(35),
                    profile36(36),
                    profile37(37),
                    profile38(38),
                    profile39(39),
                    profile40(40),
                    profile41(41),
                    profile42(42),
                    profile43(43),
                    profile44(44),
                    profile45(45),
                    profile46(46),
                    profile47(47),
                    profile48(48)
                }
            ACCESS  read-write
            STATUS  mandatory
            DESCRIPTION
                "Profile"
            ::= { ge8QosVcgBindEntry 4 }


--
-- ge8QosLanBindTable
--

        ge8QosLanBindTable  OBJECT-TYPE
            SYNTAX  SEQUENCE OF Ge8QosLanBindEntry
            ACCESS  not-accessible
            STATUS  mandatory
            DESCRIPTION
                "QoS Bind LAN port to Profile Table."
            ::= { ge8QosGroup 5 }

        ge8QosLanBindEntry  OBJECT-TYPE
            SYNTAX  Ge8QosLanBindEntry
            ACCESS  not-accessible
            STATUS  mandatory
            DESCRIPTION
                "QoS Bind LAN port to Profile Entry."
            INDEX { ge8QlBindUnit , ge8QlBindGroup }
            ::= { ge8QosLanBindTable 1 }

        Ge8QosLanBindEntry ::= SEQUENCE {
            ge8QlBindUnit                  UnitID,
            ge8QlBindGroup                 INTEGER,
            ge8QlBindPath                  INTEGER,
            ge8QlBindVlanId                INTEGER,
            ge8QlBindVlanCmd               INTEGER,
            ge8QlBindVlanList              DisplayString,
            ge8QlBindProfile               INTEGER
        }

        ge8QlBindUnit  OBJECT-TYPE
            SYNTAX  UnitID
            ACCESS  read-only
            STATUS  mandatory
            DESCRIPTION
                "unit index: 1~8 "
            ::= { ge8QosLanBindEntry 1 }

        ge8QlBindGroup  OBJECT-TYPE
            SYNTAX  INTEGER (1..48)
            ACCESS  read-only
            STATUS  mandatory
            DESCRIPTION
                "Group index"
            ::= { ge8QosLanBindEntry 2 }

        ge8QlBindPath  OBJECT-TYPE
            SYNTAX  INTEGER {
                    no(0),
                    lan1Ingress(1),
                    lan2Ingress(2),
                    lan3Ingress(3),
                    lan4Ingress(4),
                    lan5Ingress(5),
                    lan6Ingress(6),
                    lan7Ingress(7),
                    lan8Ingress(8)
                }
            ACCESS  read-write
            STATUS  mandatory
            DESCRIPTION
                "LAN path"
            ::= { ge8QosLanBindEntry 3 }

        ge8QlBindVlanId  OBJECT-TYPE
            SYNTAX  INTEGER (1..4094)
            ACCESS  read-write
            STATUS  mandatory
            DESCRIPTION
                "Vlan ID"
            ::= { ge8QosLanBindEntry 4 }

        ge8QlBindVlanCmd  OBJECT-TYPE
            SYNTAX  INTEGER {
                    no(1),
                    add(2),
                    delete(3),
                    deleteAll(4)
                }
            ACCESS  read-write
            STATUS  mandatory
            DESCRIPTION
                "Vlan command"
            ::= { ge8QosLanBindEntry 5 }

        ge8QlBindVlanList  OBJECT-TYPE
            SYNTAX  DisplayString (SIZE (0..200))
            ACCESS  read-only
            STATUS  mandatory
            DESCRIPTION
                "VLAN ID list"
            ::= { ge8QosLanBindEntry 6 }

        ge8QlBindProfile  OBJECT-TYPE
            SYNTAX  INTEGER {
                    no(0),
                    profile1(1),
                    profile2(2),
                    profile3(3),
                    profile4(4),
                    profile5(5),
                    profile6(6),
                    profile7(7),
                    profile8(8),
                    profile9(9),
                    profile10(10),
                    profile11(11),
                    profile12(12),
                    profile13(13),
                    profile14(14),
                    profile15(15),
                    profile16(16),
                    profile17(17),
                    profile18(18),
                    profile19(19),
                    profile20(20),
                    profile21(21),
                    profile22(22),
                    profile23(23),
                    profile24(24),
                    profile25(25),
                    profile26(26),
                    profile27(27),
                    profile28(28),
                    profile29(29),
                    profile30(30),
                    profile31(31),
                    profile32(32),
                    profile33(33),
                    profile34(34),
                    profile35(35),
                    profile36(36),
                    profile37(37),
                    profile38(38),
                    profile39(39),
                    profile40(40),
                    profile41(41),
                    profile42(42),
                    profile43(43),
                    profile44(44),
                    profile45(45),
                    profile46(46),
                    profile47(47),
                    profile48(48)
                }
            ACCESS  read-write
            STATUS  mandatory
            DESCRIPTION
                "Profile"
            ::= { ge8QosLanBindEntry 7 }

--
--   ge8QosTxSchedule
--
    ge8QosTxSchedule  OBJECT IDENTIFIER ::= { ge8QosGroup 6 }

--
--   ge8ScheduAlgorithmTable
--
        ge8ScheduAlgorithmTable  OBJECT-TYPE
            SYNTAX  SEQUENCE OF  Ge8ScheduAlgorithmEntry
            ACCESS  not-accessible
            STATUS  mandatory
            DESCRIPTION
                "The 8GESW  QoS Scheduling Algorithm Table."
            ::= { ge8QosTxSchedule 1 }

        ge8ScheduAlgorithmEntry  OBJECT-TYPE
            SYNTAX  Ge8ScheduAlgorithmEntry
            ACCESS  not-accessible
            STATUS  mandatory
            DESCRIPTION
                "An entry in the 8GESW  QoS Scheduling Algorithm Table."
            INDEX { ge8ScheduAlgoUnit , ge8ScheduAlgoPort }
            ::= { ge8ScheduAlgorithmTable 1 }

        Ge8ScheduAlgorithmEntry ::= SEQUENCE {
            ge8ScheduAlgoUnit          UnitID,
            ge8ScheduAlgoPort          Ge8SwPort,
            ge8ScheduAlgoP0Queue       INTEGER,
            ge8ScheduAlgoP1Queue       INTEGER,
            ge8ScheduAlgoP2Queue       INTEGER,
            ge8ScheduAlgoP3Queue       INTEGER,
            ge8ScheduAlgoP4Queue       INTEGER,
            ge8ScheduAlgoP5Queue       INTEGER,
            ge8ScheduAlgoP6Queue       INTEGER,
            ge8ScheduAlgoP7Queue       INTEGER
        }

        ge8ScheduAlgoUnit  OBJECT-TYPE
            SYNTAX  UnitID
            ACCESS  read-only
            STATUS  mandatory
            DESCRIPTION
                "unit index"
            ::= { ge8ScheduAlgorithmEntry 1 }

        ge8ScheduAlgoPort  OBJECT-TYPE
            SYNTAX  Ge8SwPort
            ACCESS  read-only
            STATUS  mandatory
            DESCRIPTION
                "Port WAN1~4, LAN1~8."
            ::= { ge8ScheduAlgorithmEntry 2 }

        ge8ScheduAlgoP0Queue  OBJECT-TYPE
            SYNTAX  INTEGER {
                    strictPriority(1),
                    weightedRoundRobin(2)
                }
            ACCESS  read-write
            STATUS  mandatory
            DESCRIPTION
                "P0 Queue"
            ::= { ge8ScheduAlgorithmEntry 3 }

        ge8ScheduAlgoP1Queue  OBJECT-TYPE
            SYNTAX  INTEGER {
                    strictPriority(1),
                    weightedRoundRobin(2)
                }
            ACCESS  read-write
            STATUS  mandatory
            DESCRIPTION
                "P1 Queue"
            ::= { ge8ScheduAlgorithmEntry 4 }

        ge8ScheduAlgoP2Queue  OBJECT-TYPE
            SYNTAX  INTEGER {
                    strictPriority(1),
                    weightedRoundRobin(2)
                }
            ACCESS  read-write
            STATUS  mandatory
            DESCRIPTION
                "P2 Queue"
            ::= { ge8ScheduAlgorithmEntry 5 }

        ge8ScheduAlgoP3Queue  OBJECT-TYPE
            SYNTAX  INTEGER {
                    strictPriority(1),
                    weightedRoundRobin(2)
                }
            ACCESS  read-write
            STATUS  mandatory
            DESCRIPTION
                "P3 Queue"
            ::= { ge8ScheduAlgorithmEntry 6 }

        ge8ScheduAlgoP4Queue  OBJECT-TYPE
            SYNTAX  INTEGER {
                    strictPriority(1),
                    weightedRoundRobin(2)
                }
            ACCESS  read-write
            STATUS  mandatory
            DESCRIPTION
                "P4 Queue"
            ::= { ge8ScheduAlgorithmEntry 7 }

        ge8ScheduAlgoP5Queue  OBJECT-TYPE
            SYNTAX  INTEGER {
                    strictPriority(1),
                    weightedRoundRobin(2)
                }
            ACCESS  read-write
            STATUS  mandatory
            DESCRIPTION
                "P5 Queue"
            ::= { ge8ScheduAlgorithmEntry 8 }

        ge8ScheduAlgoP6Queue  OBJECT-TYPE
            SYNTAX  INTEGER {
                    strictPriority(1),
                    weightedRoundRobin(2)
                }
            ACCESS  read-write
            STATUS  mandatory
            DESCRIPTION
                "P6 Queue"
            ::= { ge8ScheduAlgorithmEntry 9 }

        ge8ScheduAlgoP7Queue  OBJECT-TYPE
            SYNTAX  INTEGER {
                    strictPriority(1),
                    weightedRoundRobin(2)
                }
            ACCESS  read-write
            STATUS  mandatory
            DESCRIPTION
                "P7 Queue"
            ::= { ge8ScheduAlgorithmEntry 10 }


--
--   ge8WrrWeightTable
--
        ge8WrrWeightTable  OBJECT-TYPE
            SYNTAX  SEQUENCE OF  Ge8WrrWeightEntry
            ACCESS  not-accessible
            STATUS  mandatory
            DESCRIPTION
                "The 8GESW  QoS WRR Weight Table."
            ::= { ge8QosTxSchedule 2 }

        ge8WrrWeightEntry  OBJECT-TYPE
            SYNTAX  Ge8WrrWeightEntry
            ACCESS  not-accessible
            STATUS  mandatory
            DESCRIPTION
                "An entry in the 8GESW  QoS WRR Weight Table."
            INDEX { ge8WrrWeightUnit , ge8WrrWeightPort }
            ::= { ge8WrrWeightTable 1 }

        Ge8WrrWeightEntry ::= SEQUENCE {
            ge8WrrWeightUnit             UnitID,
            ge8WrrWeightPort             Ge8SwPort,
            ge8WrrWeightP0Queue          INTEGER,
            ge8WrrWeightP1Queue          INTEGER,
            ge8WrrWeightP2Queue          INTEGER,
            ge8WrrWeightP3Queue          INTEGER,
            ge8WrrWeightP4Queue          INTEGER,
            ge8WrrWeightP5Queue          INTEGER,
            ge8WrrWeightP6Queue          INTEGER,
            ge8WrrWeightP7Queue          INTEGER
        }

        ge8WrrWeightUnit  OBJECT-TYPE
            SYNTAX  UnitID
            ACCESS  read-only
            STATUS  mandatory
            DESCRIPTION
                "unit index"
            ::= { ge8WrrWeightEntry 1 }

        ge8WrrWeightPort  OBJECT-TYPE
            SYNTAX  Ge8SwPort
            ACCESS  read-only
            STATUS  mandatory
            DESCRIPTION
                "Port WAN1~4, LAN1~8."
            ::= { ge8WrrWeightEntry 2 }

        ge8WrrWeightP0Queue  OBJECT-TYPE
            SYNTAX  INTEGER (1..255)
            ACCESS  read-write
            STATUS  mandatory
            DESCRIPTION
                "P0 Queue Weight"
            ::= { ge8WrrWeightEntry 3 }

        ge8WrrWeightP1Queue  OBJECT-TYPE
            SYNTAX  INTEGER (1..255)
            ACCESS  read-write
            STATUS  mandatory
            DESCRIPTION
                "P1 Queue Weight"
            ::= { ge8WrrWeightEntry 4 }

        ge8WrrWeightP2Queue  OBJECT-TYPE
            SYNTAX  INTEGER (1..255)
            ACCESS  read-write
            STATUS  mandatory
            DESCRIPTION
                "P2 Queue Weight"
            ::= { ge8WrrWeightEntry 5 }

        ge8WrrWeightP3Queue  OBJECT-TYPE
            SYNTAX  INTEGER (1..255)
            ACCESS  read-write
            STATUS  mandatory
            DESCRIPTION
                "P3 Queue Weight"
            ::= { ge8WrrWeightEntry 6 }

        ge8WrrWeightP4Queue  OBJECT-TYPE
            SYNTAX  INTEGER (1..255)
            ACCESS  read-write
            STATUS  mandatory
            DESCRIPTION
                "P4 Queue Weight"
            ::= { ge8WrrWeightEntry 7 }

        ge8WrrWeightP5Queue  OBJECT-TYPE
            SYNTAX  INTEGER (1..255)
            ACCESS  read-write
            STATUS  mandatory
            DESCRIPTION
                "P5 Queue Weight"
            ::= { ge8WrrWeightEntry 8 }

        ge8WrrWeightP6Queue  OBJECT-TYPE
            SYNTAX  INTEGER (1..255)
            ACCESS  read-write
            STATUS  mandatory
            DESCRIPTION
                "P6 Queue Weight"
            ::= { ge8WrrWeightEntry 9 }

        ge8WrrWeightP7Queue  OBJECT-TYPE
            SYNTAX  INTEGER (1..255)
            ACCESS  read-write
            STATUS  mandatory
            DESCRIPTION
                "P7 Queue Weight"
            ::= { ge8WrrWeightEntry 10 }

--
--   ge8SwGeneralTable
--
        ge8SwGeneralTable  OBJECT-TYPE
            SYNTAX  SEQUENCE OF  Ge8SwGeneralEntry
            ACCESS  not-accessible
            STATUS  mandatory
            DESCRIPTION
                "The 8GESW Switch General setup Table."
            ::= { ge8SwitchGroup 9 }

        ge8SwGeneralEntry  OBJECT-TYPE
            SYNTAX  Ge8SwGeneralEntry
            ACCESS  not-accessible
            STATUS  mandatory
            DESCRIPTION
                "An entry in the 8GESW Switch General setup Table."
            INDEX { ge8SwGeneralUnit }
            ::= { ge8SwGeneralTable 1 }

        Ge8SwGeneralEntry ::= SEQUENCE {
            ge8SwGeneralUnit              UnitID,
            ge8SwGeneralJumboFrame        INTEGER,
            ge8SwGeneralBPDUForward       INTEGER
        }

        ge8SwGeneralUnit  OBJECT-TYPE
            SYNTAX  UnitID
            ACCESS  read-only
            STATUS  mandatory
            DESCRIPTION
                "unit index"
            ::= { ge8SwGeneralEntry 1 }

        ge8SwGeneralJumboFrame  OBJECT-TYPE
            SYNTAX  INTEGER {
                    enable(1),
                    disable(2)
                }
            ACCESS  read-write
            STATUS  mandatory
            DESCRIPTION
                "Support Jumbo Frame."
            ::= { ge8SwGeneralEntry 2 }

        ge8SwGeneralBPDUForward  OBJECT-TYPE
            SYNTAX  INTEGER {
                    disable(1),
                    enable(2)
                }
            ACCESS  read-write
            STATUS  mandatory
            DESCRIPTION
                "Forward BPDU."
            ::= { ge8SwGeneralEntry 3 }


--
--  ge8SwDeltaStatTable
--
        ge8SwDeltaStatTable  OBJECT-TYPE
            SYNTAX  SEQUENCE OF  Ge8SwDeltaStatEntry
            ACCESS  not-accessible
            STATUS  mandatory
            DESCRIPTION
                "The 8GESW  Switch Delta Statistic Table."
            ::= { ge8SwitchGroup 10 }

        ge8SwDeltaStatEntry  OBJECT-TYPE
            SYNTAX  Ge8SwDeltaStatEntry
            ACCESS  not-accessible
            STATUS  mandatory
            DESCRIPTION
                "An entry in the 8GESW  Switch Delta Statistic Table."
            INDEX { ge8SwDStUnit, ge8SwDStPort }
            ::= { ge8SwDeltaStatTable 1 }

        Ge8SwDeltaStatEntry ::= SEQUENCE {
            ge8SwDStUnit                  UnitID,
            ge8SwDStPort                  Ge8SwPort,
            ge8SwDStGoodOctetsRcv         Counter32,
            ge8SwDStBadOctetsRcv          Counter32,
            ge8SwDStMacTransmitErr        Counter32,
            ge8SwDStGoodPktsRcv           Counter32,
            ge8SwDStBadPktsRcv            Counter32,
            ge8SwDStBrdcPktsRcv           Counter32,
            ge8SwDStMcPktsRcv             Counter32,
            ge8SwDStPkts64Octs            Counter32,
            ge8SwDStPkts65to127Octs       Counter32,
            ge8SwDStPkts128to255Octs      Counter32,
            ge8SwDStPkts256to511Octs      Counter32,
            ge8SwDStPkts512to1023Octs     Counter32,
            ge8SwDStPkts1024toMaxOcts     Counter32,
            ge8SwDStGoodOctetsSent        Counter32,
            ge8SwDStGoodPktsSent          Counter32,
            ge8SwDStExcesCollisions       Counter32,
            ge8SwDStMcPktsSent            Counter32,
            ge8SwDStBrdcPktsSent          Counter32,
            ge8SwDStUnrecogMacCntrRcv     Counter32,
            ge8SwDStFcSent                Counter32,
            ge8SwDStGoodFcRcv             Counter32,
            ge8SwDStDropEvents            Counter32,
            ge8SwDStUndersizePkts         Counter32,
            ge8SwDStFragmentsPkts         Counter32,
            ge8SwDStOversizePkts          Counter32,
            ge8SwDStJabberPkts            Counter32,
            ge8SwDStMacRcvError           Counter32,
            ge8SwDStBadCrc                Counter32,
            ge8SwDStCollisions            Counter32,
            ge8SwDStLateCollisions        Counter32,
            ge8SwDStBadFcRcv              Counter32,
            ge8SwDStUcPktsRcv             Counter32,
            ge8SwDStUcPktsSent            Counter32,
            ge8SwDStMultiplePktsSent      Counter32,
            ge8SwDStDeferredPktsSent      Counter32
        }

        ge8SwDStUnit  OBJECT-TYPE
            SYNTAX  UnitID
            ACCESS  read-only
            STATUS  mandatory
            DESCRIPTION
                "unit index"
            ::= { ge8SwDeltaStatEntry 1 }

        ge8SwDStPort  OBJECT-TYPE
            SYNTAX  Ge8SwPort
            ACCESS  read-only
            STATUS  mandatory
            DESCRIPTION
                "Port WAN1~4, LAN1~8."
            ::= { ge8SwDeltaStatEntry 2 }

        ge8SwDStGoodOctetsRcv      OBJECT-TYPE
            SYNTAX  Counter32
            ACCESS  read-only
            STATUS  mandatory
            DESCRIPTION
                "goodOctetsRcv       "
            ::= { ge8SwDeltaStatEntry 3 }

        ge8SwDStBadOctetsRcv       OBJECT-TYPE
            SYNTAX  Counter32
            ACCESS  read-only
            STATUS  mandatory
            DESCRIPTION
                "badOctetsRcv        "
            ::= { ge8SwDeltaStatEntry 4 }

        ge8SwDStMacTransmitErr     OBJECT-TYPE
            SYNTAX  Counter32
            ACCESS  read-only
            STATUS  mandatory
            DESCRIPTION
                "macTransmitErr      "
            ::= { ge8SwDeltaStatEntry 5 }

        ge8SwDStGoodPktsRcv        OBJECT-TYPE
            SYNTAX  Counter32
            ACCESS  read-only
            STATUS  mandatory
            DESCRIPTION
                "goodPktsRcv         "
            ::= { ge8SwDeltaStatEntry 6 }

        ge8SwDStBadPktsRcv         OBJECT-TYPE
            SYNTAX  Counter32
            ACCESS  read-only
            STATUS  mandatory
            DESCRIPTION
                "badPktsRcv          "
            ::= { ge8SwDeltaStatEntry 7 }

        ge8SwDStBrdcPktsRcv        OBJECT-TYPE
            SYNTAX  Counter32
            ACCESS  read-only
            STATUS  mandatory
            DESCRIPTION
                "brdcPktsRcv         "
            ::= { ge8SwDeltaStatEntry 8 }

        ge8SwDStMcPktsRcv          OBJECT-TYPE
            SYNTAX  Counter32
            ACCESS  read-only
            STATUS  mandatory
            DESCRIPTION
                "mcPktsRcv           "
            ::= { ge8SwDeltaStatEntry 9 }

        ge8SwDStPkts64Octs         OBJECT-TYPE
            SYNTAX  Counter32
            ACCESS  read-only
            STATUS  mandatory
            DESCRIPTION
                "pkts64Octets        "
            ::= { ge8SwDeltaStatEntry 10 }

        ge8SwDStPkts65to127Octs    OBJECT-TYPE
            SYNTAX  Counter32
            ACCESS  read-only
            STATUS  mandatory
            DESCRIPTION
                "pkts65to127Octets   "
            ::= { ge8SwDeltaStatEntry 11 }

        ge8SwDStPkts128to255Octs   OBJECT-TYPE
            SYNTAX  Counter32
            ACCESS  read-only
            STATUS  mandatory
            DESCRIPTION
                "pkts128to255Octets  "
            ::= { ge8SwDeltaStatEntry 12 }

        ge8SwDStPkts256to511Octs   OBJECT-TYPE
            SYNTAX  Counter32
            ACCESS  read-only
            STATUS  mandatory
            DESCRIPTION
                "pkts256to511Octets  "
            ::= { ge8SwDeltaStatEntry 13 }

        ge8SwDStPkts512to1023Octs  OBJECT-TYPE
            SYNTAX  Counter32
            ACCESS  read-only
            STATUS  mandatory
            DESCRIPTION
                "pkts512to1023Octets "
            ::= { ge8SwDeltaStatEntry 14 }

        ge8SwDStPkts1024toMaxOcts  OBJECT-TYPE
            SYNTAX  Counter32
            ACCESS  read-only
            STATUS  mandatory
            DESCRIPTION
                "pkts1024tomaxOoctets"
            ::= { ge8SwDeltaStatEntry 15 }

        ge8SwDStGoodOctetsSent     OBJECT-TYPE
            SYNTAX  Counter32
            ACCESS  read-only
            STATUS  mandatory
            DESCRIPTION
                "goodOctetsSent      "
            ::= { ge8SwDeltaStatEntry 16 }

        ge8SwDStGoodPktsSent       OBJECT-TYPE
            SYNTAX  Counter32
            ACCESS  read-only
            STATUS  mandatory
            DESCRIPTION
                "goodPktsSent        "
            ::= { ge8SwDeltaStatEntry 17 }

        ge8SwDStExcesCollisions    OBJECT-TYPE
            SYNTAX  Counter32
            ACCESS  read-only
            STATUS  mandatory
            DESCRIPTION
                "excessiveCollisions "
            ::= { ge8SwDeltaStatEntry 18 }

        ge8SwDStMcPktsSent         OBJECT-TYPE
            SYNTAX  Counter32
            ACCESS  read-only
            STATUS  mandatory
            DESCRIPTION
                "mcPktsSent          "
            ::= { ge8SwDeltaStatEntry 19 }

        ge8SwDStBrdcPktsSent       OBJECT-TYPE
            SYNTAX  Counter32
            ACCESS  read-only
            STATUS  mandatory
            DESCRIPTION
                "brdcPktsSent        "
            ::= { ge8SwDeltaStatEntry 20 }

        ge8SwDStUnrecogMacCntrRcv  OBJECT-TYPE
            SYNTAX  Counter32
            ACCESS  read-only
            STATUS  mandatory
            DESCRIPTION
                "unrecogMacCntrRcv   "
            ::= { ge8SwDeltaStatEntry 21 }

        ge8SwDStFcSent             OBJECT-TYPE
            SYNTAX  Counter32
            ACCESS  read-only
            STATUS  mandatory
            DESCRIPTION
                "fcSent              "
            ::= { ge8SwDeltaStatEntry 22 }

        ge8SwDStGoodFcRcv          OBJECT-TYPE
            SYNTAX  Counter32
            ACCESS  read-only
            STATUS  mandatory
            DESCRIPTION
                "goodFcRcv           "
            ::= { ge8SwDeltaStatEntry 23 }

        ge8SwDStDropEvents         OBJECT-TYPE
            SYNTAX  Counter32
            ACCESS  read-only
            STATUS  mandatory
            DESCRIPTION
                "dropEvents          "
            ::= { ge8SwDeltaStatEntry 24 }

        ge8SwDStUndersizePkts      OBJECT-TYPE
            SYNTAX  Counter32
            ACCESS  read-only
            STATUS  mandatory
            DESCRIPTION
                "undersizePkts       "
            ::= { ge8SwDeltaStatEntry 25 }

        ge8SwDStFragmentsPkts      OBJECT-TYPE
            SYNTAX  Counter32
            ACCESS  read-only
            STATUS  mandatory
            DESCRIPTION
                "fragmentsPkts       "
            ::= { ge8SwDeltaStatEntry 26 }

        ge8SwDStOversizePkts       OBJECT-TYPE
            SYNTAX  Counter32
            ACCESS  read-only
            STATUS  mandatory
            DESCRIPTION
                "oversizePkts        "
            ::= { ge8SwDeltaStatEntry 27 }

        ge8SwDStJabberPkts         OBJECT-TYPE
            SYNTAX  Counter32
            ACCESS  read-only
            STATUS  mandatory
            DESCRIPTION
                "jabberPkts          "
            ::= { ge8SwDeltaStatEntry 28 }

        ge8SwDStMacRcvError        OBJECT-TYPE
            SYNTAX  Counter32
            ACCESS  read-only
            STATUS  mandatory
            DESCRIPTION
                "macRcvError         "
            ::= { ge8SwDeltaStatEntry 29 }

        ge8SwDStBadCrc             OBJECT-TYPE
            SYNTAX  Counter32
            ACCESS  read-only
            STATUS  mandatory
            DESCRIPTION
                "badCrc              "
            ::= { ge8SwDeltaStatEntry 30 }

        ge8SwDStCollisions         OBJECT-TYPE
            SYNTAX  Counter32
            ACCESS  read-only
            STATUS  mandatory
            DESCRIPTION
                "collisions          "
            ::= { ge8SwDeltaStatEntry 31 }

        ge8SwDStLateCollisions     OBJECT-TYPE
            SYNTAX  Counter32
            ACCESS  read-only
            STATUS  mandatory
            DESCRIPTION
                "lateCollisions      "
            ::= { ge8SwDeltaStatEntry 32 }

        ge8SwDStBadFcRcv           OBJECT-TYPE
            SYNTAX  Counter32
            ACCESS  read-only
            STATUS  mandatory
            DESCRIPTION
                "badFcRcv            "
            ::= { ge8SwDeltaStatEntry 33 }

        ge8SwDStUcPktsRcv          OBJECT-TYPE
            SYNTAX  Counter32
            ACCESS  read-only
            STATUS  mandatory
            DESCRIPTION
                "ucPktsRcv           "
            ::= { ge8SwDeltaStatEntry 34 }

        ge8SwDStUcPktsSent         OBJECT-TYPE
            SYNTAX  Counter32
            ACCESS  read-only
            STATUS  mandatory
            DESCRIPTION
                "ucPktsSent          "
            ::= { ge8SwDeltaStatEntry 35 }

        ge8SwDStMultiplePktsSent   OBJECT-TYPE
            SYNTAX  Counter32
            ACCESS  read-only
            STATUS  mandatory
            DESCRIPTION
                "multiplePktsSent    "
            ::= { ge8SwDeltaStatEntry 36 }

        ge8SwDStDeferredPktsSent   OBJECT-TYPE
            SYNTAX  Counter32
            ACCESS  read-only
            STATUS  mandatory
            DESCRIPTION
                "deferredPktsSent    "
            ::= { ge8SwDeltaStatEntry 37 }


--
--  ge8SwDeltaStatTable
--
        ge8SwDeltaStatTable  OBJECT-TYPE
            SYNTAX  SEQUENCE OF  Ge8SwDeltaStatEntry
            ACCESS  not-accessible
            STATUS  mandatory
            DESCRIPTION
                "The 8GESW  Switch Delta Statistic Table."
            ::= { ge8SwitchGroup 10 }

        ge8SwDeltaStatEntry  OBJECT-TYPE
            SYNTAX  Ge8SwDeltaStatEntry
            ACCESS  not-accessible
            STATUS  mandatory
            DESCRIPTION
                "An entry in the 8GESW  Switch Delta Statistic Table."
            INDEX { ge8SwDStUnit, ge8SwDStPort }
            ::= { ge8SwDeltaStatTable 1 }

        Ge8SwDeltaStatEntry ::= SEQUENCE {
            ge8SwDStUnit                  UnitID,
            ge8SwDStPort                  Ge8SwPort,
            ge8SwDStGoodOctetsRcv         Counter32,
            ge8SwDStBadOctetsRcv          Counter32,
            ge8SwDStMacTransmitErr        Counter32,
            ge8SwDStGoodPktsRcv           Counter32,
            ge8SwDStBadPktsRcv            Counter32,
            ge8SwDStBrdcPktsRcv           Counter32,
            ge8SwDStMcPktsRcv             Counter32,
            ge8SwDStPkts64Octs            Counter32,
            ge8SwDStPkts65to127Octs       Counter32,
            ge8SwDStPkts128to255Octs      Counter32,
            ge8SwDStPkts256to511Octs      Counter32,
            ge8SwDStPkts512to1023Octs     Counter32,
            ge8SwDStPkts1024toMaxOcts     Counter32,
            ge8SwDStGoodOctetsSent        Counter32,
            ge8SwDStGoodPktsSent          Counter32,
            ge8SwDStExcesCollisions       Counter32,
            ge8SwDStMcPktsSent            Counter32,
            ge8SwDStBrdcPktsSent          Counter32,
            ge8SwDStUnrecogMacCntrRcv     Counter32,
            ge8SwDStFcSent                Counter32,
            ge8SwDStGoodFcRcv             Counter32,
            ge8SwDStDropEvents            Counter32,
            ge8SwDStUndersizePkts         Counter32,
            ge8SwDStFragmentsPkts         Counter32,
            ge8SwDStOversizePkts          Counter32,
            ge8SwDStJabberPkts            Counter32,
            ge8SwDStMacRcvError           Counter32,
            ge8SwDStBadCrc                Counter32,
            ge8SwDStCollisions            Counter32,
            ge8SwDStLateCollisions        Counter32,
            ge8SwDStBadFcRcv              Counter32,
            ge8SwDStUcPktsRcv             Counter32,
            ge8SwDStUcPktsSent            Counter32,
            ge8SwDStMultiplePktsSent      Counter32,
            ge8SwDStDeferredPktsSent      Counter32
        }

        ge8SwDStUnit  OBJECT-TYPE
            SYNTAX  UnitID
            ACCESS  read-only
            STATUS  mandatory
            DESCRIPTION
                "unit index"
            ::= { ge8SwDeltaStatEntry 1 }

        ge8SwDStPort  OBJECT-TYPE
            SYNTAX  Ge8SwPort
            ACCESS  read-only
            STATUS  mandatory
            DESCRIPTION
                "Port WAN1~4, LAN1~8."
            ::= { ge8SwDeltaStatEntry 2 }

        ge8SwDStGoodOctetsRcv      OBJECT-TYPE
            SYNTAX  Counter32
            ACCESS  read-only
            STATUS  mandatory
            DESCRIPTION
                "goodOctetsRcv       "
            ::= { ge8SwDeltaStatEntry 3 }

        ge8SwDStBadOctetsRcv       OBJECT-TYPE
            SYNTAX  Counter32
            ACCESS  read-only
            STATUS  mandatory
            DESCRIPTION
                "badOctetsRcv        "
            ::= { ge8SwDeltaStatEntry 4 }

        ge8SwDStMacTransmitErr     OBJECT-TYPE
            SYNTAX  Counter32
            ACCESS  read-only
            STATUS  mandatory
            DESCRIPTION
                "macTransmitErr      "
            ::= { ge8SwDeltaStatEntry 5 }

        ge8SwDStGoodPktsRcv        OBJECT-TYPE
            SYNTAX  Counter32
            ACCESS  read-only
            STATUS  mandatory
            DESCRIPTION
                "goodPktsRcv         "
            ::= { ge8SwDeltaStatEntry 6 }

        ge8SwDStBadPktsRcv         OBJECT-TYPE
            SYNTAX  Counter32
            ACCESS  read-only
            STATUS  mandatory
            DESCRIPTION
                "badPktsRcv          "
            ::= { ge8SwDeltaStatEntry 7 }

        ge8SwDStBrdcPktsRcv        OBJECT-TYPE
            SYNTAX  Counter32
            ACCESS  read-only
            STATUS  mandatory
            DESCRIPTION
                "brdcPktsRcv         "
            ::= { ge8SwDeltaStatEntry 8 }

        ge8SwDStMcPktsRcv          OBJECT-TYPE
            SYNTAX  Counter32
            ACCESS  read-only
            STATUS  mandatory
            DESCRIPTION
                "mcPktsRcv           "
            ::= { ge8SwDeltaStatEntry 9 }

        ge8SwDStPkts64Octs         OBJECT-TYPE
            SYNTAX  Counter32
            ACCESS  read-only
            STATUS  mandatory
            DESCRIPTION
                "pkts64Octets        "
            ::= { ge8SwDeltaStatEntry 10 }

        ge8SwDStPkts65to127Octs    OBJECT-TYPE
            SYNTAX  Counter32
            ACCESS  read-only
            STATUS  mandatory
            DESCRIPTION
                "pkts65to127Octets   "
            ::= { ge8SwDeltaStatEntry 11 }

        ge8SwDStPkts128to255Octs   OBJECT-TYPE
            SYNTAX  Counter32
            ACCESS  read-only
            STATUS  mandatory
            DESCRIPTION
                "pkts128to255Octets  "
            ::= { ge8SwDeltaStatEntry 12 }

        ge8SwDStPkts256to511Octs   OBJECT-TYPE
            SYNTAX  Counter32
            ACCESS  read-only
            STATUS  mandatory
            DESCRIPTION
                "pkts256to511Octets  "
            ::= { ge8SwDeltaStatEntry 13 }

        ge8SwDStPkts512to1023Octs  OBJECT-TYPE
            SYNTAX  Counter32
            ACCESS  read-only
            STATUS  mandatory
            DESCRIPTION
                "pkts512to1023Octets "
            ::= { ge8SwDeltaStatEntry 14 }

        ge8SwDStPkts1024toMaxOcts  OBJECT-TYPE
            SYNTAX  Counter32
            ACCESS  read-only
            STATUS  mandatory
            DESCRIPTION
                "pkts1024tomaxOoctets"
            ::= { ge8SwDeltaStatEntry 15 }

        ge8SwDStGoodOctetsSent     OBJECT-TYPE
            SYNTAX  Counter32
            ACCESS  read-only
            STATUS  mandatory
            DESCRIPTION
                "goodOctetsSent      "
            ::= { ge8SwDeltaStatEntry 16 }

        ge8SwDStGoodPktsSent       OBJECT-TYPE
            SYNTAX  Counter32
            ACCESS  read-only
            STATUS  mandatory
            DESCRIPTION
                "goodPktsSent        "
            ::= { ge8SwDeltaStatEntry 17 }

        ge8SwDStExcesCollisions    OBJECT-TYPE
            SYNTAX  Counter32
            ACCESS  read-only
            STATUS  mandatory
            DESCRIPTION
                "excessiveCollisions "
            ::= { ge8SwDeltaStatEntry 18 }

        ge8SwDStMcPktsSent         OBJECT-TYPE
            SYNTAX  Counter32
            ACCESS  read-only
            STATUS  mandatory
            DESCRIPTION
                "mcPktsSent          "
            ::= { ge8SwDeltaStatEntry 19 }

        ge8SwDStBrdcPktsSent       OBJECT-TYPE
            SYNTAX  Counter32
            ACCESS  read-only
            STATUS  mandatory
            DESCRIPTION
                "brdcPktsSent        "
            ::= { ge8SwDeltaStatEntry 20 }

        ge8SwDStUnrecogMacCntrRcv  OBJECT-TYPE
            SYNTAX  Counter32
            ACCESS  read-only
            STATUS  mandatory
            DESCRIPTION
                "unrecogMacCntrRcv   "
            ::= { ge8SwDeltaStatEntry 21 }

        ge8SwDStFcSent             OBJECT-TYPE
            SYNTAX  Counter32
            ACCESS  read-only
            STATUS  mandatory
            DESCRIPTION
                "fcSent              "
            ::= { ge8SwDeltaStatEntry 22 }

        ge8SwDStGoodFcRcv          OBJECT-TYPE
            SYNTAX  Counter32
            ACCESS  read-only
            STATUS  mandatory
            DESCRIPTION
                "goodFcRcv           "
            ::= { ge8SwDeltaStatEntry 23 }

        ge8SwDStDropEvents         OBJECT-TYPE
            SYNTAX  Counter32
            ACCESS  read-only
            STATUS  mandatory
            DESCRIPTION
                "dropEvents          "
            ::= { ge8SwDeltaStatEntry 24 }

        ge8SwDStUndersizePkts      OBJECT-TYPE
            SYNTAX  Counter32
            ACCESS  read-only
            STATUS  mandatory
            DESCRIPTION
                "undersizePkts       "
            ::= { ge8SwDeltaStatEntry 25 }

        ge8SwDStFragmentsPkts      OBJECT-TYPE
            SYNTAX  Counter32
            ACCESS  read-only
            STATUS  mandatory
            DESCRIPTION
                "fragmentsPkts       "
            ::= { ge8SwDeltaStatEntry 26 }

        ge8SwDStOversizePkts       OBJECT-TYPE
            SYNTAX  Counter32
            ACCESS  read-only
            STATUS  mandatory
            DESCRIPTION
                "oversizePkts        "
            ::= { ge8SwDeltaStatEntry 27 }

        ge8SwDStJabberPkts         OBJECT-TYPE
            SYNTAX  Counter32
            ACCESS  read-only
            STATUS  mandatory
            DESCRIPTION
                "jabberPkts          "
            ::= { ge8SwDeltaStatEntry 28 }

        ge8SwDStMacRcvError        OBJECT-TYPE
            SYNTAX  Counter32
            ACCESS  read-only
            STATUS  mandatory
            DESCRIPTION
                "macRcvError         "
            ::= { ge8SwDeltaStatEntry 29 }

        ge8SwDStBadCrc             OBJECT-TYPE
            SYNTAX  Counter32
            ACCESS  read-only
            STATUS  mandatory
            DESCRIPTION
                "badCrc              "
            ::= { ge8SwDeltaStatEntry 30 }

        ge8SwDStCollisions         OBJECT-TYPE
            SYNTAX  Counter32
            ACCESS  read-only
            STATUS  mandatory
            DESCRIPTION
                "collisions          "
            ::= { ge8SwDeltaStatEntry 31 }

        ge8SwDStLateCollisions     OBJECT-TYPE
            SYNTAX  Counter32
            ACCESS  read-only
            STATUS  mandatory
            DESCRIPTION
                "lateCollisions      "
            ::= { ge8SwDeltaStatEntry 32 }

        ge8SwDStBadFcRcv           OBJECT-TYPE
            SYNTAX  Counter32
            ACCESS  read-only
            STATUS  mandatory
            DESCRIPTION
                "badFcRcv            "
            ::= { ge8SwDeltaStatEntry 33 }

        ge8SwDStUcPktsRcv          OBJECT-TYPE
            SYNTAX  Counter32
            ACCESS  read-only
            STATUS  mandatory
            DESCRIPTION
                "ucPktsRcv           "
            ::= { ge8SwDeltaStatEntry 34 }

        ge8SwDStUcPktsSent         OBJECT-TYPE
            SYNTAX  Counter32
            ACCESS  read-only
            STATUS  mandatory
            DESCRIPTION
                "ucPktsSent          "
            ::= { ge8SwDeltaStatEntry 35 }

        ge8SwDStMultiplePktsSent   OBJECT-TYPE
            SYNTAX  Counter32
            ACCESS  read-only
            STATUS  mandatory
            DESCRIPTION
                "multiplePktsSent    "
            ::= { ge8SwDeltaStatEntry 36 }

        ge8SwDStDeferredPktsSent   OBJECT-TYPE
            SYNTAX  Counter32
            ACCESS  read-only
            STATUS  mandatory
            DESCRIPTION
                "deferredPktsSent    "
            ::= { ge8SwDeltaStatEntry 37 }


--
--
--
    ge8StatusGroup        OBJECT IDENTIFIER ::= { ge8EosCard 10 }


--
-- ENET LCAS Status Table
--
    ge8LcasStatus         OBJECT IDENTIFIER ::= { ge8StatusGroup 1 }

--
-- ENET LCAS Sink Status Table
--
        ge8LcasSinkStatusTable  OBJECT-TYPE
            SYNTAX  SEQUENCE OF Ge8LcasSinkStatusEntry
            ACCESS  not-accessible
            STATUS  mandatory
            DESCRIPTION
                "LCAS SINK status table"
            ::= { ge8LcasStatus 1 }

        ge8LcasSinkStatusEntry  OBJECT-TYPE
            SYNTAX  Ge8LcasSinkStatusEntry
            ACCESS  not-accessible
            STATUS  mandatory
            DESCRIPTION
                "An entry in the LCAS SINK status table"
            INDEX { ge8LcasSinkUnit , ge8LcasSinkPort , ge8LcasSinkChannel }
            ::= { ge8LcasSinkStatusTable 1 }

        Ge8LcasSinkStatusEntry ::= SEQUENCE {
            ge8LcasSinkUnit              UnitID,
            ge8LcasSinkPort              GeVcgNum,
            ge8LcasSinkChannel           ChannelNum,
            ge8LcasSinkState             INTEGER
        }

        ge8LcasSinkUnit  OBJECT-TYPE
            SYNTAX  UnitID
            ACCESS  read-only
            STATUS  mandatory
            DESCRIPTION
                "Unit 1 to 8"
            ::= { ge8LcasSinkStatusEntry 1 }

        ge8LcasSinkPort  OBJECT-TYPE
            SYNTAX  GeVcgNum
            ACCESS  read-only
            STATUS  mandatory
            DESCRIPTION
                "vcg port index "
            ::= { ge8LcasSinkStatusEntry 2 }

        ge8LcasSinkChannel  OBJECT-TYPE
            SYNTAX  ChannelNum
            ACCESS  read-only
            STATUS  mandatory
            DESCRIPTION
                "Channel index"
            ::= { ge8LcasSinkStatusEntry 3 }

        ge8LcasSinkState  OBJECT-TYPE
            SYNTAX  INTEGER{
                    notAvailable(1),
                    ok(2),
                    idle(3),
                    fail(4)
                }
            ACCESS  read-only
            STATUS  mandatory
            DESCRIPTION
                "LCAS SINK state"
            ::= { ge8LcasSinkStatusEntry 4 }

--
-- ENET LCAS Source Status Table
--
        ge8LcasSourceStatusTable  OBJECT-TYPE
            SYNTAX  SEQUENCE OF Ge8LcasSourceStatusEntry
            ACCESS  not-accessible
            STATUS  mandatory
            DESCRIPTION
                "LCAS SOURCE status table"
            ::= { ge8LcasStatus 2 }

        ge8LcasSourceStatusEntry  OBJECT-TYPE
            SYNTAX  Ge8LcasSourceStatusEntry
            ACCESS  not-accessible
            STATUS  mandatory
            DESCRIPTION
                "An entry in the LCAS SOURCE status table"
            INDEX { ge8LcasSourceUnit , ge8LcasSourcePort , ge8LcasSourceChannel }
            ::= { ge8LcasSourceStatusTable 1 }

        Ge8LcasSourceStatusEntry ::= SEQUENCE {
            ge8LcasSourceUnit            UnitID,
            ge8LcasSourcePort            GeVcgNum,
            ge8LcasSourceChannel         ChannelNum,
            ge8LcasSourceState           INTEGER
        }

        ge8LcasSourceUnit  OBJECT-TYPE
            SYNTAX  UnitID
            ACCESS  read-only
            STATUS  mandatory
            DESCRIPTION
                "Unit 1 to 8"
            ::= { ge8LcasSourceStatusEntry 1 }

        ge8LcasSourcePort  OBJECT-TYPE
            SYNTAX  GeVcgNum
            ACCESS  read-only
            STATUS  mandatory
            DESCRIPTION
                "vcg port index "
            ::= { ge8LcasSourceStatusEntry 2 }

        ge8LcasSourceChannel  OBJECT-TYPE
            SYNTAX  ChannelNum
            ACCESS  read-only
            STATUS  mandatory
            DESCRIPTION
                "Channel index"
            ::= { ge8LcasSourceStatusEntry 3 }

        ge8LcasSourceState  OBJECT-TYPE
            SYNTAX  INTEGER{
                    notAvailable(1),
                    add(2),
                    norm(3),
                    eos(4),
                    idle(5),
                    dnu(6),
                    fixed(7)
                }
            ACCESS  read-only
            STATUS  mandatory
            DESCRIPTION
                "LCAS SOURCE state"
            ::= { ge8LcasSourceStatusEntry 4 }


--
--   ge8LedStatusTable
--
        ge8LedStatusTable  OBJECT-TYPE
            SYNTAX  SEQUENCE OF  Ge8LedStatusEntry
            ACCESS  not-accessible
            STATUS  mandatory
            DESCRIPTION
                "The 8GESW  LED Status Table."
            ::= { ge8StatusGroup 2 }

        ge8LedStatusEntry  OBJECT-TYPE
            SYNTAX  Ge8LedStatusEntry
            ACCESS  not-accessible
            STATUS  mandatory
            DESCRIPTION
                "An entry in the 8GESW  LED Status Table."
            INDEX { ge8LedStaUnit }
            ::= { ge8LedStatusTable 1 }

        Ge8LedStatusEntry ::= SEQUENCE {
            ge8LedStaUnit                UnitID,
            ge8LedStaActiveLED           LedStatusType,
            ge8LedStaTestLED             LedStatusType,
            ge8LedStaAlarmLED            LedStatusType
        }

        ge8LedStaUnit  OBJECT-TYPE
            SYNTAX  UnitID
            ACCESS  read-only
            STATUS  mandatory
            DESCRIPTION
                "unit index"
            ::= { ge8LedStatusEntry 1 }

        ge8LedStaActiveLED  OBJECT-TYPE
            SYNTAX  LedStatusType
            ACCESS  read-only
            STATUS  mandatory
            DESCRIPTION
                "Active LED status"
            ::= { ge8LedStatusEntry 2 }

        ge8LedStaTestLED  OBJECT-TYPE
            SYNTAX  LedStatusType
            ACCESS  read-only
            STATUS  mandatory
            DESCRIPTION
                "Test LED status"
            ::= { ge8LedStatusEntry 3 }

        ge8LedStaAlarmLED  OBJECT-TYPE
            SYNTAX  LedStatusType
            ACCESS  read-only
            STATUS  mandatory
            DESCRIPTION
                "Alarm LED status"
            ::= { ge8LedStatusEntry 4 }


--
--   ge8LinkStatusTable
--
        ge8LinkStatusTable  OBJECT-TYPE
            SYNTAX  SEQUENCE OF  Ge8LinkStatusEntry
            ACCESS  not-accessible
            STATUS  mandatory
            DESCRIPTION
                "The 8GESW  LAN Link Status Table."
            ::= { ge8StatusGroup 3 }

        ge8LinkStatusEntry  OBJECT-TYPE
            SYNTAX  Ge8LinkStatusEntry
            ACCESS  not-accessible
            STATUS  mandatory
            DESCRIPTION
                "An entry in the 8GESW  LAN Link Status Table."
            INDEX { ge8LinkStUnit , ge8LinkStPort }
            ::= { ge8LinkStatusTable 1 }

        Ge8LinkStatusEntry ::= SEQUENCE {
            ge8LinkStUnit                UnitID,
            ge8LinkStPort                Ge8LanPort,
            ge8LinkStState               INTEGER,
            ge8LinkStSpeed               INTEGER,
            ge8LinkStDuplex              INTEGER,
            ge8LinkStInterface           INTEGER
        }

        ge8LinkStUnit  OBJECT-TYPE
            SYNTAX  UnitID
            ACCESS  read-only
            STATUS  mandatory
            DESCRIPTION
                "unit index"
            ::= { ge8LinkStatusEntry 1 }

        ge8LinkStPort  OBJECT-TYPE
            SYNTAX  Ge8LanPort
            ACCESS  read-only
            STATUS  mandatory
            DESCRIPTION
                "Port LAN1~8."
            ::= { ge8LinkStatusEntry 2 }

        ge8LinkStState  OBJECT-TYPE
            SYNTAX  INTEGER {
                    down(1),
                    up(2)
                }
            ACCESS  read-only
            STATUS  mandatory
            DESCRIPTION
                "The 8GESW  LAN Link State"
            ::= { ge8LinkStatusEntry 3 }

        ge8LinkStSpeed  OBJECT-TYPE
            SYNTAX  INTEGER {
                    na(1),
                    speed1000M(2),
                    speed100M(3),
                    speed10M(4)
                }
            ACCESS  read-only
            STATUS  mandatory
            DESCRIPTION
                "The 8GESW  LAN Link Speed"
            ::= { ge8LinkStatusEntry 4 }

        ge8LinkStDuplex  OBJECT-TYPE
            SYNTAX  INTEGER {
                    na(1),
                    half(2),
                    full(3)
                }
            ACCESS  read-only
            STATUS  mandatory
            DESCRIPTION
                "The 8GESW  LAN Duplex type"
            ::= { ge8LinkStatusEntry 5 }

        ge8LinkStInterface  OBJECT-TYPE
            SYNTAX  INTEGER {
                    na(1),
                    fiber(2),
                    copper(3)
                }
            ACCESS  read-only
            STATUS  mandatory
            DESCRIPTION
                "The 8GESW  LAN Interface type"
            ::= { ge8LinkStatusEntry 6 }


--
-- SFP Information Table
--

        ge8SfpInfoTable  OBJECT-TYPE
            SYNTAX  SEQUENCE OF  Ge8SfpInfoEntry
            ACCESS  not-accessible
            STATUS  mandatory
            DESCRIPTION
                "8GESW  SFP information table "
            ::= { ge8StatusGroup 4 }

        ge8SfpInfoEntry  OBJECT-TYPE
            SYNTAX  Ge8SfpInfoEntry
            ACCESS  not-accessible
            STATUS  mandatory
            DESCRIPTION
                "8GESW  SFP information entry"
            INDEX { ge8SfpInfoUnit , ge8SfpInfoPort }
            ::= { ge8SfpInfoTable 1 }

        Ge8SfpInfoEntry ::= SEQUENCE {
            ge8SfpInfoUnit             UnitID,
            ge8SfpInfoPort             Ge8LanPort,
            ge8SfpInfoEquip            INTEGER,
            ge8SfpInfoConnector        INTEGER,
            ge8SfpInfoTransceiver      DisplayString,
            ge8SfpInfoLinkLength       DisplayString,
            ge8SfpInfoTechnology       DisplayString,
            ge8SfpInfoEncoding         DisplayString,
-- 2014-01-23 modify below by Sue
--            ge8SfpInfoLen9to125mm      DisplayString,
--            ge8SfpInfoLen50to125mm     DisplayString,
--            ge8SfpInfoLen62p5to125mm   DisplayString,
            ge8SfpInfoLen9to125um      DisplayString,
            ge8SfpInfoLen50to125um     DisplayString,
            ge8SfpInfoLen62p5to125um   DisplayString,
-- 2014-01-23 modify above by Sue
            ge8SfpInfoLenCopper        DisplayString,
            ge8SfpInfoTemperature      DisplayString,
            ge8SfpInfoVcc              DisplayString,
            ge8SfpInfoTxBias           DisplayString,
            ge8SfpInfoTxPower          DisplayString,
            ge8SfpInfoRxPower          DisplayString,
            ge8SfpInfoDateCode         DisplayString,
            ge8SfpInfoVendorName       DisplayString,
            ge8SfpInfoVendorOUI        DisplayString,
            ge8SfpInfoVendorPN         DisplayString,
            ge8SfpInfoVendorRev        DisplayString,
            ge8SfpInfoWaveLength       DisplayString
        }

        ge8SfpInfoUnit  OBJECT-TYPE
            SYNTAX  UnitID
            ACCESS  read-only
            STATUS  mandatory
            DESCRIPTION
                "unit 1 to 8."
            ::= { ge8SfpInfoEntry  1 }

        ge8SfpInfoPort  OBJECT-TYPE
            SYNTAX  Ge8LanPort
            ACCESS  read-only
            STATUS  mandatory
            DESCRIPTION
                "PORT index"
            ::= { ge8SfpInfoEntry  2 }

        ge8SfpInfoEquip  OBJECT-TYPE
            SYNTAX  INTEGER {
                    unequipped(1),
                    equipped(2)
                }
            ACCESS  read-only
            STATUS  mandatory
            DESCRIPTION
                "Port equip or not"
            ::= { ge8SfpInfoEntry 3 }

        ge8SfpInfoConnector  OBJECT-TYPE
            SYNTAX  INTEGER {
                    notAvailable(1),
                    sc(2),
                    fibreChannelStyle1Copper(3),
                    fibreChannelStyle2Copper(4),
                    bncTnc(5),
                    fibreChannelCoaxialHeader(6),
                    fiberJack(7),
                    lc(8),
                    mtRJ(9),
                    mu(10),
                    sg(11),
                    optcalPigtail(12),
                    hssdcIi(13),
                    copperPigtail(14)
                }
            ACCESS  read-only
            STATUS  mandatory
            DESCRIPTION
                "Port connector"
            ::= { ge8SfpInfoEntry 4 }

        ge8SfpInfoTransceiver  OBJECT-TYPE
            SYNTAX  DisplayString
            ACCESS  read-only
            STATUS  mandatory
            DESCRIPTION
                "Port transceiver"
            ::= { ge8SfpInfoEntry 5 }

        ge8SfpInfoLinkLength  OBJECT-TYPE
            SYNTAX  DisplayString
            ACCESS  read-only
            STATUS  mandatory
            DESCRIPTION
                "Port Link Length"
            ::= { ge8SfpInfoEntry 6 }

        ge8SfpInfoTechnology  OBJECT-TYPE
            SYNTAX  DisplayString
            ACCESS  read-only
            STATUS  mandatory
            DESCRIPTION
                "Port Technology"
            ::= { ge8SfpInfoEntry 7 }

        ge8SfpInfoEncoding  OBJECT-TYPE
            SYNTAX  DisplayString
            ACCESS  read-only
            STATUS  mandatory
            DESCRIPTION
                "Port Encoding"
            ::= { ge8SfpInfoEntry 8 }

-- 2014-01-23 modify below by Sue
--        ge8SfpInfoLen9to125mm  OBJECT-TYPE
--            SYNTAX  DisplayString
--            ACCESS  read-only
--            STATUS  mandatory
--            DESCRIPTION
--                "Port length for 9/125 mm fiber"
--            ::= { ge8SfpInfoEntry 9 }
--
--        ge8SfpInfoLen50to125mm  OBJECT-TYPE
--            SYNTAX  DisplayString
--            ACCESS  read-only
--            STATUS  mandatory
--            DESCRIPTION
--                "Port length for 50/125 mm fiber"
--            ::= { ge8SfpInfoEntry 10 }
--
--        ge8SfpInfoLen62p5to125mm  OBJECT-TYPE
--            SYNTAX  DisplayString
--            ACCESS  read-only
--            STATUS  mandatory
--            DESCRIPTION
--                "Port length for 62.5/125 mm fiber"
--            ::= { ge8SfpInfoEntry 11 }
        ge8SfpInfoLen9to125um  OBJECT-TYPE
            SYNTAX  DisplayString
            ACCESS  read-only
            STATUS  mandatory
            DESCRIPTION
                "Port length for 9/125 um fiber"
            ::= { ge8SfpInfoEntry 9 }

        ge8SfpInfoLen50to125um  OBJECT-TYPE
            SYNTAX  DisplayString
            ACCESS  read-only
            STATUS  mandatory
            DESCRIPTION
                "Port length for 50/125 um fiber"
            ::= { ge8SfpInfoEntry 10 }

        ge8SfpInfoLen62p5to125um  OBJECT-TYPE
            SYNTAX  DisplayString
            ACCESS  read-only
            STATUS  mandatory
            DESCRIPTION
                "Port length for 62.5/125 um fiber"
            ::= { ge8SfpInfoEntry 11 }
-- 2014-01-23 modify above by Sue

        ge8SfpInfoLenCopper  OBJECT-TYPE
            SYNTAX  DisplayString
            ACCESS  read-only
            STATUS  mandatory
            DESCRIPTION
                "Port length for copper"
            ::= { ge8SfpInfoEntry 12 }

        ge8SfpInfoTemperature  OBJECT-TYPE
            SYNTAX  DisplayString
            ACCESS  read-only
            STATUS  mandatory
            DESCRIPTION
                "Port Temperature"
            ::= { ge8SfpInfoEntry 13 }

        ge8SfpInfoVcc  OBJECT-TYPE
            SYNTAX  DisplayString
            ACCESS  read-only
            STATUS  mandatory
            DESCRIPTION
                "Port Vcc"
            ::= { ge8SfpInfoEntry 14 }

        ge8SfpInfoTxBias  OBJECT-TYPE
            SYNTAX  DisplayString
            ACCESS  read-only
            STATUS  mandatory
            DESCRIPTION
                "Port Tx Bias current"
            ::= { ge8SfpInfoEntry 15 }

        ge8SfpInfoTxPower  OBJECT-TYPE
            SYNTAX  DisplayString
            ACCESS  read-only
            STATUS  mandatory
            DESCRIPTION
                "Port Tx power"
            ::= { ge8SfpInfoEntry 16 }

        ge8SfpInfoRxPower  OBJECT-TYPE
            SYNTAX  DisplayString
            ACCESS  read-only
            STATUS  mandatory
            DESCRIPTION
                "Port Rx power"
            ::= { ge8SfpInfoEntry 17 }

        ge8SfpInfoDateCode  OBJECT-TYPE
            SYNTAX  DisplayString
            ACCESS  read-only
            STATUS  mandatory
            DESCRIPTION
                "Date Code"
            ::= { ge8SfpInfoEntry 18 }

        ge8SfpInfoVendorName  OBJECT-TYPE
            SYNTAX  DisplayString
            ACCESS  read-only
            STATUS  mandatory
            DESCRIPTION
                "Vendor Name"
            ::= { ge8SfpInfoEntry 19 }

        ge8SfpInfoVendorOUI  OBJECT-TYPE
            SYNTAX  DisplayString
            ACCESS  read-only
            STATUS  mandatory
            DESCRIPTION
                "Vendor OUI"
            ::= { ge8SfpInfoEntry 20 }

        ge8SfpInfoVendorPN  OBJECT-TYPE
            SYNTAX  DisplayString
            ACCESS  read-only
            STATUS  mandatory
            DESCRIPTION
                "Vendor PN"
            ::= { ge8SfpInfoEntry 21 }

        ge8SfpInfoVendorRev  OBJECT-TYPE
            SYNTAX  DisplayString
            ACCESS  read-only
            STATUS  mandatory
            DESCRIPTION
                "Vendor Reversion"
            ::= { ge8SfpInfoEntry 22 }

        ge8SfpInfoWaveLength  OBJECT-TYPE
            SYNTAX  DisplayString
            ACCESS  read-only
            STATUS  mandatory
            DESCRIPTION
                "Wave Length"
            ::= { ge8SfpInfoEntry 23 }


--
--   ge8CommandControlTable
--
        ge8CommandControlTable  OBJECT-TYPE
            SYNTAX  SEQUENCE OF  Ge8CommandControlEntry
            ACCESS  not-accessible
            STATUS  mandatory
            DESCRIPTION
                "The 8GESW  Command Control Table."
            ::= { ge8EosCard 11 }

        ge8CommandControlEntry  OBJECT-TYPE
            SYNTAX  Ge8CommandControlEntry
            ACCESS  not-accessible
            STATUS  mandatory
            DESCRIPTION
                "An entry in the 8GESW  Command Control Table."
            INDEX { ge8CmdCtrlUnit }
            ::= { ge8CommandControlTable 1 }

        Ge8CommandControlEntry ::= SEQUENCE {
            ge8CmdCtrlUnit               UnitID,
            ge8CmdCtrlReset              INTEGER,
            ge8CmdCtrlLoadDefault        INTEGER,
            ge8CmdCtrlClearStatistic     INTEGER
        }

        ge8CmdCtrlUnit  OBJECT-TYPE
            SYNTAX  UnitID
            ACCESS  read-only
            STATUS  mandatory
            DESCRIPTION
                "unit index"
            ::= { ge8CommandControlEntry 1 }

        ge8CmdCtrlReset  OBJECT-TYPE
            SYNTAX  INTEGER {
                    coldReset(2),
                    no(255)
                }
            ACCESS  read-write
            STATUS  mandatory
            DESCRIPTION
                "Unit reset"
            ::= { ge8CommandControlEntry 2 }

        ge8CmdCtrlLoadDefault  OBJECT-TYPE
            SYNTAX  INTEGER {
                    loadDefault(1),
                    no(255)
                }
            ACCESS  read-write
            STATUS  mandatory
            DESCRIPTION
                "Unit load default"
            ::= { ge8CommandControlEntry 3 }

        ge8CmdCtrlClearStatistic  OBJECT-TYPE
            SYNTAX  INTEGER {
                    clearStatistic(1),
                    no(255)
                }
            ACCESS  read-write
            STATUS  mandatory
            DESCRIPTION
                "Unit Clear Statistic"
            ::= { ge8CommandControlEntry 4 }


--
--   ge8XcDisplayTable
--
        ge8XcDisplayTable  OBJECT-TYPE
            SYNTAX  SEQUENCE OF  Ge8XcDisplayEntry
            ACCESS  not-accessible
            STATUS  mandatory
            DESCRIPTION
                "The 8GESW  xc display Table."
            ::= { ge8EosCard 12 }

        ge8XcDisplayEntry  OBJECT-TYPE
            SYNTAX  Ge8XcDisplayEntry
            ACCESS  not-accessible
            STATUS  mandatory
            DESCRIPTION
                "An entry in the 8GESW  xc display Table."
            INDEX { ge8XcDispMap , ge8XcDispUnit ,
                    ge8XcDispPort , ge8XcDispChannel }
            ::= { ge8XcDisplayTable 1 }

        Ge8XcDisplayEntry ::= SEQUENCE {
            ge8XcDispMap                 XcMap,
            ge8XcDispUnit                UnitID,
            ge8XcDispPort                GeVcgNum,
            ge8XcDispChannel             ChannelNum,
            ge8XcDispPriType             NewXcModel,
            ge8XcDispPriSlot             XcSlot,
            ge8XcDispPriPort             PortID,
            ge8XcDispPriChannel          ChannelNum,
            ge8XcDispPriAug1Sts3Path     Aug1Sts3Num,
            ge8XcDispPriVc3Sts1Path      Vc3Sts1Num,
            ge8XcDispPriVc1xVtxPath      Vc1xVtxNum,
            ge8XcDispXcGranularity       INTEGER,
            ge8XcDispXcType              XcType,
            ge8XcDispSecType             NewXcModel,
            ge8XcDispSecSlot             XcSlot,
            ge8XcDispSecPort             PortID,
            ge8XcDispSecChannel          ChannelNum,
            ge8XcDispSecAug1Sts3Path     Aug1Sts3Num,
            ge8XcDispSecVc3Sts1Path      Vc3Sts1Num,
-- 2016-01-14 modify below by-Sue
--            ge8XcDispSecVc1xVtxPath      Vc1xVtxNum
            ge8XcDispSecVc1xVtxPath      Vc1xVtxNum
--            ge8XcDispDesMsspId                                                MsspIdNum,
--            ge8XcDispSrcMsspId                                                MsspIdNum
-- 2016-01-14 modify above by-Sue

    }

        ge8XcDispMap  OBJECT-TYPE
            SYNTAX  XcMap
            ACCESS  read-only
            STATUS  mandatory
            DESCRIPTION
                "xc map index"
            ::= { ge8XcDisplayEntry 1 }

        ge8XcDispUnit  OBJECT-TYPE
            SYNTAX  UnitID
            ACCESS  read-only
            STATUS  mandatory
            DESCRIPTION
                "unit index"
            ::= { ge8XcDisplayEntry 2 }

        ge8XcDispPort  OBJECT-TYPE
            SYNTAX  GeVcgNum
            ACCESS  read-only
            STATUS  mandatory
            DESCRIPTION
                "vcg port index"
            ::= { ge8XcDisplayEntry 3 }

        ge8XcDispChannel  OBJECT-TYPE
            SYNTAX  ChannelNum
            ACCESS  read-only
            STATUS  mandatory
            DESCRIPTION
                "Channel index"
            ::= { ge8XcDisplayEntry 4 }

        ge8XcDispPriType  OBJECT-TYPE
            SYNTAX  NewXcModel
            ACCESS  read-only
            STATUS  mandatory
            DESCRIPTION
                " Xc Primary Unit Type"
            ::= { ge8XcDisplayEntry 5 }

        ge8XcDispPriSlot  OBJECT-TYPE
            SYNTAX  XcSlot
            ACCESS  read-only
            STATUS  mandatory
            DESCRIPTION
                "Xc Primary Unit "
            ::= { ge8XcDisplayEntry 6 }

        ge8XcDispPriPort  OBJECT-TYPE
            SYNTAX  PortID
            ACCESS  read-only
            STATUS  mandatory
            DESCRIPTION
                "Xc Primary port "
            ::= { ge8XcDisplayEntry 7 }

        ge8XcDispPriChannel  OBJECT-TYPE
            SYNTAX  ChannelNum
            ACCESS  read-only
            STATUS  mandatory
            DESCRIPTION
                "Xc Primary channel "
            ::= { ge8XcDisplayEntry 8 }

        ge8XcDispPriAug1Sts3Path  OBJECT-TYPE
            SYNTAX  Aug1Sts3Num
            ACCESS  read-only
            STATUS  mandatory
            DESCRIPTION
                "Xc Primary AUG1/STS3 path"
            ::= { ge8XcDisplayEntry 9 }

        ge8XcDispPriVc3Sts1Path  OBJECT-TYPE
            SYNTAX  Vc3Sts1Num
            ACCESS  read-only
            STATUS  mandatory
            DESCRIPTION
                "Xc Primary VC3/STS1 path"
            ::= { ge8XcDisplayEntry 10 }

        ge8XcDispPriVc1xVtxPath  OBJECT-TYPE
            SYNTAX  Vc1xVtxNum
            ACCESS  read-only
            STATUS  mandatory
            DESCRIPTION
                "Xc Primary VC1x/VTx path"
            ::= { ge8XcDisplayEntry 11 }

        ge8XcDispXcGranularity  OBJECT-TYPE
            SYNTAX  INTEGER {
                    tu3(2),
                    au3Sts1(3),
                    tu11Vt15(4),
                    tu12Vt2(5),
                    vc4Sts3c(6),
                    notAvailable(100)
                }
            ACCESS  read-only
            STATUS  mandatory
            DESCRIPTION
                "Xc granularity"
            ::= { ge8XcDisplayEntry 12 }

        ge8XcDispXcType  OBJECT-TYPE
            SYNTAX  XcType
            ACCESS  read-only
            STATUS  mandatory
            DESCRIPTION
                "Xc type"
            ::= { ge8XcDisplayEntry 13 }

        ge8XcDispSecType  OBJECT-TYPE
            SYNTAX  NewXcModel
            ACCESS  read-only
            STATUS  mandatory
            DESCRIPTION
                " Xc Secondary Unit Type"
            ::= { ge8XcDisplayEntry 14 }

        ge8XcDispSecSlot  OBJECT-TYPE
            SYNTAX  XcSlot
            ACCESS  read-only
            STATUS  mandatory
            DESCRIPTION
                "Xc Secondary Unit "
            ::= { ge8XcDisplayEntry 15 }

        ge8XcDispSecPort  OBJECT-TYPE
            SYNTAX  PortID
            ACCESS  read-only
            STATUS  mandatory
            DESCRIPTION
                "Xc Secondary port "
            ::= { ge8XcDisplayEntry 16 }

        ge8XcDispSecChannel  OBJECT-TYPE
            SYNTAX  ChannelNum
            ACCESS  read-only
            STATUS  mandatory
            DESCRIPTION
                "Xc Secondary channel "
            ::= { ge8XcDisplayEntry 17 }

        ge8XcDispSecAug1Sts3Path  OBJECT-TYPE
            SYNTAX  Aug1Sts3Num
            ACCESS  read-only
            STATUS  mandatory
            DESCRIPTION
                "Xc Secondary AUG1/STS3 path"
            ::= { ge8XcDisplayEntry 18 }

        ge8XcDispSecVc3Sts1Path  OBJECT-TYPE
            SYNTAX  Vc3Sts1Num
            ACCESS  read-only
            STATUS  mandatory
            DESCRIPTION
                "Xc Secondary VC3/STS1 path"
            ::= { ge8XcDisplayEntry 19 }

        ge8XcDispSecVc1xVtxPath  OBJECT-TYPE
            SYNTAX  Vc1xVtxNum
            ACCESS  read-only
            STATUS  mandatory
            DESCRIPTION
                "Xc Secondary VC1x/VTx path"
            ::= { ge8XcDisplayEntry 20 }

-- 2016-01-14 add below by-Sue
--        ge8XcDispDesMsspId  OBJECT-TYPE
--             SYNTAX  MsspIdNum
--             ACCESS  read-only
--             STATUS  mandatory
--             DESCRIPTION
--                "Xc destination mssp id"
--            ::= { ge8XcDisplayEntry 21 }

--        ge8XcDispSrcMsspId  OBJECT-TYPE
--             SYNTAX  MsspIdNum
--             ACCESS  read-only
--             STATUS  mandatory
--             DESCRIPTION
--                "Xc source mssp id"
--            ::= { ge8XcDisplayEntry 22 }
-- 2016-01-14 add above by-Sue


--
-- GE8 SNCP/UPSR APS Table
--

        ge8SncpApsTable  OBJECT-TYPE
            SYNTAX  SEQUENCE OF  Ge8SncpApsEntry
            ACCESS  not-accessible
            STATUS  mandatory
            DESCRIPTION
                "ENET SNCP/UPSR APS table "
            ::= { ge8EosCard 13 }

        ge8SncpApsEntry  OBJECT-TYPE
            SYNTAX  Ge8SncpApsEntry
            ACCESS  not-accessible
            STATUS  mandatory
            DESCRIPTION
                "ENET SNCP/UPSR APS entry"
            INDEX { ge8SncpUnit , ge8SncpPort , ge8SncpChannel }
            ::= { ge8SncpApsTable 1 }

        Ge8SncpApsEntry ::= SEQUENCE {
            ge8SncpUnit                  UnitID,
            ge8SncpPort                  GeVcgNum,
            ge8SncpChannel               ChannelNum,
            ge8SncpCurrSlot              XcSlot,
            ge8SncpCurrPort              PortID,
            ge8SncpCurrChannel           ChannelNum,
            ge8SncpCurrAug1Sts3Path      Aug1Sts3Num,
            ge8SncpCurrVc3Sts1Path       Vc3Sts1Num,
            ge8SncpCurrVc1xVtxPath       Vc1xVtxNum,
            ge8SncpPPType                XcType,
            ge8SncpCmd                   SncpUserCmd,
            ge8SncpRevertive             INTEGER
        }

        ge8SncpUnit  OBJECT-TYPE
            SYNTAX  UnitID
            ACCESS  read-only
            STATUS  mandatory
            DESCRIPTION
                "unit index"
            ::= { ge8SncpApsEntry 1 }

        ge8SncpPort  OBJECT-TYPE
            SYNTAX  GeVcgNum
            ACCESS  read-only
            STATUS  mandatory
            DESCRIPTION
                "VCG number"
            ::= { ge8SncpApsEntry 2 }

        ge8SncpChannel  OBJECT-TYPE
            SYNTAX  ChannelNum
            ACCESS  read-only
            STATUS  mandatory
            DESCRIPTION
                "CHANNEL #1~#64"
            ::= { ge8SncpApsEntry 3 }

        ge8SncpCurrSlot  OBJECT-TYPE
            SYNTAX  XcSlot
            ACCESS  read-only
            STATUS  mandatory
            DESCRIPTION
                "SNCP/UPSR current slot"
            ::= { ge8SncpApsEntry 4 }

        ge8SncpCurrPort  OBJECT-TYPE
            SYNTAX  PortID
            ACCESS  read-only
            STATUS  mandatory
            DESCRIPTION
                "SNCP/UPSR current port"
            ::= { ge8SncpApsEntry 5 }

        ge8SncpCurrChannel  OBJECT-TYPE
            SYNTAX  ChannelNum
            ACCESS  read-only
            STATUS  mandatory
            DESCRIPTION
                "SNCP/UPSR current channel"
            ::= { ge8SncpApsEntry 6 }

        ge8SncpCurrAug1Sts3Path  OBJECT-TYPE
            SYNTAX  Aug1Sts3Num
            ACCESS  read-only
            STATUS  mandatory
            DESCRIPTION
                "SNCP/UPSR current Aug1/Sts3"
            ::= { ge8SncpApsEntry 7 }

        ge8SncpCurrVc3Sts1Path  OBJECT-TYPE
            SYNTAX  Vc3Sts1Num
            ACCESS  read-only
            STATUS  mandatory
            DESCRIPTION
                "SNCP/UPSR current Vc3/Sts1"
            ::= { ge8SncpApsEntry 8 }

        ge8SncpCurrVc1xVtxPath  OBJECT-TYPE
            SYNTAX  Vc1xVtxNum
            ACCESS  read-only
            STATUS  mandatory
            DESCRIPTION
                "SNCP/UPSR current Vc1x/Vtx"
            ::= { ge8SncpApsEntry 9 }

        ge8SncpPPType  OBJECT-TYPE
            SYNTAX  XcType
            ACCESS  read-only
            STATUS  mandatory
            DESCRIPTION
                "SNCP/UPSR path protection type"
            ::= { ge8SncpApsEntry 10 }

        ge8SncpCmd  OBJECT-TYPE
            SYNTAX  SncpUserCmd
            ACCESS  read-write
            STATUS  mandatory
            DESCRIPTION
                "SNCP/UPSR APS command"
            ::= { ge8SncpApsEntry 11 }

        ge8SncpRevertive  OBJECT-TYPE
            SYNTAX  INTEGER {
                    nonRevertive(1),
                    revertive(2)
                }
            ACCESS  read-write
            STATUS  mandatory
            DESCRIPTION
                "SNCP/UPSR revertive or non-revertive"
            ::= { ge8SncpApsEntry 12 }

--
-- GE8 TPSG Protection Table
--
        ge8TPSGProtectTable  OBJECT-TYPE
            SYNTAX  SEQUENCE OF Ge8TPSGProtectEntry
            ACCESS  not-accessible
            STATUS  mandatory
            DESCRIPTION
                "TPSG protection table"
            ::= { ge8EosCard 14 }

        ge8TPSGProtectEntry  OBJECT-TYPE
            SYNTAX  Ge8TPSGProtectEntry
            ACCESS  not-accessible
            STATUS  mandatory
            DESCRIPTION
                "An entry in the TPSG protection table"
            INDEX { ge8TPSGProtectUnit }
            ::= { ge8TPSGProtectTable 1 }

        Ge8TPSGProtectEntry ::= SEQUENCE {
            ge8TPSGProtectUnit           UnitID,
            ge8TPSGProtectActive         INTEGER,
            ge8TPSGProtectStatus         INTEGER
        }

        ge8TPSGProtectUnit  OBJECT-TYPE
            SYNTAX  UnitID
            ACCESS  read-only
            STATUS  mandatory
            DESCRIPTION
                "Unit 1 to 8"
            ::= { ge8TPSGProtectEntry 1 }

        ge8TPSGProtectActive  OBJECT-TYPE
            SYNTAX  INTEGER{
                    none(0),
                    standby(1),
                    working(2)
                }
            ACCESS  read-only
            STATUS  mandatory
            DESCRIPTION
                "TPSG active working/standby"
            ::= { ge8TPSGProtectEntry 2 }

        ge8TPSGProtectStatus  OBJECT-TYPE
            SYNTAX  INTEGER{
                    syncFailed(1),
                    syncOk(2),
                    startSync(3),
                    duringSync(4),
                    updateFailed(5),
                    unsync(6)
                }
            ACCESS  read-only
            STATUS  mandatory
            DESCRIPTION
                "TPSG Status"
            ::= { ge8TPSGProtectEntry 3 }


--
-- GE8 Slot Info Table
--
        ge8SlotInfoTable  OBJECT-TYPE
            SYNTAX  SEQUENCE OF Ge8SlotInfoEntry
            ACCESS  not-accessible
            STATUS  mandatory
            DESCRIPTION
                "Slot Info table"
            ::= { ge8EosCard 15 }

        ge8SlotInfoEntry  OBJECT-TYPE
            SYNTAX  Ge8SlotInfoEntry
            ACCESS  not-accessible
            STATUS  mandatory
            DESCRIPTION
                "An entry in the Slot info table"
            INDEX { ge8SlotInfoUnit }
            ::= { ge8SlotInfoTable 1 }

        Ge8SlotInfoEntry ::= SEQUENCE {
            ge8SlotInfoUnit           UnitID,
            ge8SlotInfoCardModel      CardModel,
            ge8SlotInfoRegModel       INTEGER
        }

        ge8SlotInfoUnit  OBJECT-TYPE
            SYNTAX  UnitID
            ACCESS  read-only
            STATUS  mandatory
            DESCRIPTION
                "Unit 1 to 8"
            ::= { ge8SlotInfoEntry 1 }

        ge8SlotInfoCardModel  OBJECT-TYPE
            SYNTAX  CardModel
            ACCESS  read-only
            STATUS  mandatory
            DESCRIPTION
                "HW info card model"
            ::= { ge8SlotInfoEntry 2 }

        ge8SlotInfoRegModel  OBJECT-TYPE
            SYNTAX  INTEGER {
                    empty(1),
                    ge8eos622SwNoProtection(49),
                    ge8eos622SwProtection(50),
                    na(255)
                }
            ACCESS  read-only
            STATUS  mandatory
            DESCRIPTION
                "Registered Model"
            ::= { ge8SlotInfoEntry 3 }



--===========================================================================--
--===========================================================================--




--===========================================================================--
--===========================================================================--
--  for LS cards
--===========================================================================--
--===========================================================================--

    tsiFunction              OBJECT IDENTIFIER ::= { system 101 }

--
--  TSI function
--
        setTSIfunction  OBJECT-TYPE
            SYNTAX  INTEGER {
                    bidirection(1),
                    multicast(2)
                }
            ACCESS  read-write
            STATUS  mandatory
            DESCRIPTION
                "Set TSI function as 1:1 bidirection or 1:N multicast."
            ::= { tsiFunction 1 }

        idleSignalling  OBJECT-TYPE
            SYNTAX  INTEGER   {
                    b0001(1),
                    b0010(2),
                    b0011(3),
                    b0100(4),
                    b0101(5),
                    b0110(6),
                    b0111(7),
                    b1000(8),
                    b1001(9),
                    b1010(10),
                    b1011(11),
                    b1100(12),
                    b1101(13),
                    b1110(14),
                    b1111(15)
                }
            ACCESS  read-write
            STATUS  mandatory
            DESCRIPTION
                "Idle signalling from 1~15 (0001~1111 binary)."
            ::= { tsiFunction 2 }

        idleData OBJECT-TYPE
            SYNTAX  INTEGER (0..255)
            ACCESS  read-write
            STATUS  mandatory
            DESCRIPTION
                "Idle data from 0~255 (0x00~0xFF1 hex)."
            ::= { tsiFunction 3 }

        teMapperType OBJECT-TYPE
            SYNTAX  INTEGER   {
                    e1(1),
                    t1(2),
                    t1-vt12(3)
                }
            ACCESS  read-write
            STATUS  mandatory
            DESCRIPTION
                "Set TE mapper type. Change type will clear all map!"
            ::= { tsiFunction 11 }

        teMapperOOS  OBJECT-TYPE
            SYNTAX  INTEGER   {
                    b0001(1),
                    b0010(2),
                    b0011(3),
                    b0100(4),
                    b0101(5),
                    b0110(6),
                    b0111(7),
                    b1000(8),
                    b1001(9),
                    b1010(10),
                    b1011(11),
                    b1100(12),
                    b1101(13),
                    b1110(14),
                    b1111(15)
                }
            ACCESS  read-write
            STATUS  mandatory
            DESCRIPTION
                "OOS"
            ::= { tsiFunction 12 }


--
--  TE mapper framer
--
        teMapperFramerTable  OBJECT-TYPE
            SYNTAX  SEQUENCE OF TeMapperFramerEntry
            ACCESS  not-accessible
            STATUS  mandatory
            DESCRIPTION
                "A list of Current TSI Map."
            ::= { tsiFunction 13 }

        teMapperFramerEntry  OBJECT-TYPE
            SYNTAX  TeMapperFramerEntry
            ACCESS  not-accessible
            STATUS  mandatory
            DESCRIPTION
                "An Entry for Current TSI Map."
            INDEX { teMapperFramerIndex }
            ::= { teMapperFramerTable 1 }

        TeMapperFramerEntry ::= SEQUENCE  {
            teMapperFramerIndex         Vte1ID,
            teMapperFrameType           INTEGER,
            teMapperRDImode             INTEGER,
            teMapperFrameStatus         INTEGER
        }

        teMapperFramerIndex  OBJECT-TYPE
            SYNTAX  Vte1ID
            ACCESS  read-only
            STATUS  mandatory
            DESCRIPTION
                "Select Virtual TE number"
            ::= { teMapperFramerEntry 1 }

        teMapperFrameType  OBJECT-TYPE
            SYNTAX  INTEGER   {
                    e1-crc-on(1),
                    e1-crc-off(2),
                    e1-cas-crc-on(3),
                    e1-cas-crc-off(4),
                    e1-unframed(5),
                    t1-esf(11),
                    t1-d4(12),
                    t1-cas-esf(13),
                    t1-cas-d4(14)
--                        t1-unframe(15)
                }
            ACCESS  read-write
            STATUS  mandatory
            DESCRIPTION
                "VTE1 frame type."
            ::= { teMapperFramerEntry 2 }

        teMapperRDImode  OBJECT-TYPE
            SYNTAX  INTEGER   {
                    rdi(1),
                    e-rdi(2)
                }
            ACCESS  read-write
            STATUS  mandatory
            DESCRIPTION
                "VTE1 RDI mode."
            ::= { teMapperFramerEntry 3 }

        teMapperFrameStatus  OBJECT-TYPE
            SYNTAX  INTEGER   {
                    sync(1),
                    rcvRAI(2),
                    xmtRAI(4),
                    rcvAIS(8),
                    xmtAIS(16),
                    rcvLOF(32),
                    rcvLOS(64),
                    rcvLoMF(128),
                    rcvLOFandLoMF(160),
                    rcvLoSF(512),
                    rcvLOFandLoSF(544),
                    rcvLOFandLoMFandLoSF(672),
                    xmtTS16YellowAlarm(1024),
                    rcvCRCerror(2048),
                    otherFailure(4096)
                }
            ACCESS  read-only
            STATUS  mandatory
            DESCRIPTION
                "VTE1 frame status in BITS."
            ::= { teMapperFramerEntry 11 }


--
-- VTE1 SNCP APS Table
--

        vte1SncpApsTab  OBJECT-TYPE
            SYNTAX  SEQUENCE OF  VTE1SncpApsEty
            ACCESS  not-accessible
            STATUS  mandatory
            DESCRIPTION
                "VTE1 SNCP APS table "
            ::= { tsiFunction 14 }

        vte1SncpApsEty  OBJECT-TYPE
            SYNTAX  VTE1SncpApsEty
            ACCESS  not-accessible
            STATUS  mandatory
            DESCRIPTION
                "VTE1 SNCP APS entry"
            INDEX { vte1SncpPort }
            ::= { vte1SncpApsTab 1 }

        VTE1SncpApsEty ::= SEQUENCE {
            vte1SncpPort                PortID,
            vte1SncpCurrentPathSlot     XcSlot,
            vte1SncpCurrentPathPort     PortID,
            vte1SncpPrimaryPathSlot     XcSlot,
            vte1SncpPrimaryPathPort     PortID,
            vte1SncpPPType              XcType,
            vte1SncpCmd                 SncpUserCmd,
            vte1SncpRevertive           INTEGER
        }

        vte1SncpPort  OBJECT-TYPE
            SYNTAX  PortID
            ACCESS  read-only
            STATUS  mandatory
            DESCRIPTION
                "PORT #1~#28"
            ::= { vte1SncpApsEty 1 }

        vte1SncpCurrentPathSlot  OBJECT-TYPE
            SYNTAX  XcSlot
            ACCESS  read-only
            STATUS  mandatory
            DESCRIPTION
                "SNCP current path"
            ::= { vte1SncpApsEty 2 }

        vte1SncpCurrentPathPort  OBJECT-TYPE
            SYNTAX  PortID
            ACCESS  read-only
            STATUS  mandatory
            DESCRIPTION
                "SNCP current path"
            ::= { vte1SncpApsEty 3 }

        vte1SncpPrimaryPathSlot  OBJECT-TYPE
            SYNTAX  XcSlot
            ACCESS  read-only
            STATUS  mandatory
            DESCRIPTION
                "SNCP primary path"
            ::= { vte1SncpApsEty 4 }

        vte1SncpPrimaryPathPort  OBJECT-TYPE
            SYNTAX  PortID
            ACCESS  read-only
            STATUS  mandatory
            DESCRIPTION
                "SNCP primary path"
            ::= { vte1SncpApsEty 5 }

        vte1SncpPPType  OBJECT-TYPE
            SYNTAX  XcType
            ACCESS  read-only
            STATUS  mandatory
            DESCRIPTION
                "SNCP path protection type"
            ::= { vte1SncpApsEty 6 }

        vte1SncpCmd  OBJECT-TYPE
            SYNTAX  SncpUserCmd
            ACCESS  read-write
            STATUS  mandatory
            DESCRIPTION
                "SNCP APS command"
            ::= { vte1SncpApsEty 7 }

        vte1SncpRevertive  OBJECT-TYPE
            SYNTAX  INTEGER {
                    non-revertive(1),
                    revertive(2)
                }
            ACCESS  read-write
            STATUS  mandatory
            DESCRIPTION
                "SNCP/UPSR revertive or non-revertive"
            ::= { vte1SncpApsEty 8 }

--
-- VTE1 Trace Message & Signal Label Setup Table
--

        vte1J2SigLabelTable  OBJECT-TYPE
            SYNTAX  SEQUENCE OF VTE1J2SigLabelEntry
            ACCESS  not-accessible
            STATUS  mandatory
            DESCRIPTION
                "Trace message & Signal label setup table"
            ::= { tsiFunction 15 }

        vte1J2SigLabelEntry  OBJECT-TYPE
            SYNTAX  VTE1J2SigLabelEntry
            ACCESS  not-accessible
            STATUS  mandatory
            DESCRIPTION
                "An entry in the trace message & signal label setup table"
            INDEX { vte1J2SigLabelPort }
            ::= { vte1J2SigLabelTable 1 }

        VTE1J2SigLabelEntry ::= SEQUENCE {
            vte1J2SigLabelPort          Vte1ID,
            vte1J2SigLabelJ2Length      INTEGER,
            vte1J2SigLabelExpJ2Msg      DisplayString(SIZE(0..64)),
            vte1J2SigLabelTxJ2Msg       DisplayString(SIZE(0..64)),
            vte1J2SigLabelRxJ2Msg       DisplayString(SIZE(0..64)),
            vte1J2SigLabelExpSigLabel   INTEGER,
            vte1J2SigLabelRxSigLabel    INTEGER,
            vte1J2SigLabelTxSigLabel    INTEGER
        }

        vte1J2SigLabelPort  OBJECT-TYPE
            SYNTAX  Vte1ID
            ACCESS  read-only
            STATUS  mandatory
            DESCRIPTION
                "VTE1 Port 1 to 28"
            ::= { vte1J2SigLabelEntry 2 }

        vte1J2SigLabelJ2Length  OBJECT-TYPE
            SYNTAX   INTEGER {
                    null(1),
                    len-16-BYTE-space(2),
                    len-64-BYTE-space(3),
                    len-16-BYTE-null(4),
                    len-64-BYTE-null(5)
                }
            ACCESS  read-write
            STATUS  mandatory
            DESCRIPTION
                "J2 message length"
            ::= { vte1J2SigLabelEntry 3 }

        vte1J2SigLabelExpJ2Msg OBJECT-TYPE
            SYNTAX  DisplayString (SIZE(0..64))
            ACCESS  read-write
            STATUS  mandatory
            DESCRIPTION
                "The expected J2 message"
            ::= { vte1J2SigLabelEntry 4 }

        vte1J2SigLabelTxJ2Msg OBJECT-TYPE
            SYNTAX  DisplayString (SIZE(0..64))
            ACCESS  read-write
            STATUS  mandatory
            DESCRIPTION
                "The tx J2 message"
            ::= { vte1J2SigLabelEntry 5 }

        vte1J2SigLabelRxJ2Msg OBJECT-TYPE
            SYNTAX  DisplayString (SIZE(0..64))
            ACCESS  read-only
            STATUS  mandatory
            DESCRIPTION
                "The rx J2 message"
            ::= { vte1J2SigLabelEntry 6 }

        vte1J2SigLabelExpSigLabel  OBJECT-TYPE
            SYNTAX  INTEGER{
                    unequipped(1),
                    equipped(2),
                    asynchronous(3),
                    bit-synchronous(4),
                    byte-synchronous(5),
                    extended-signal-label(6),
                    test-signal(7),
                    vc-ais(8)
                }
            ACCESS  read-write
            STATUS  mandatory
            DESCRIPTION
                "The expected Path Signal Label"
            ::= { vte1J2SigLabelEntry 7 }

        vte1J2SigLabelRxSigLabel  OBJECT-TYPE
            SYNTAX  INTEGER{
                    unequipped(1),
                    equipped(2),
                    asynchronous(3),
                    bit-synchronous(4),
                    byte-synchronous(5),
                    extended-signal-label(6),
                    test-signal(7),
                    vc-ais(8)
                }
            ACCESS  read-only
            STATUS  mandatory
            DESCRIPTION
                "The rx Path Signal Label"
            ::= { vte1J2SigLabelEntry 8 }

        vte1J2SigLabelTxSigLabel  OBJECT-TYPE
            SYNTAX  INTEGER{
                    unequipped(1),
                    equipped(2),
                    asynchronous(3),
                    bit-synchronous(4),
                    byte-synchronous(5),
                    extended-signal-label(6),
                    test-signal(7),
                    vc-ais(8)
                }
            ACCESS  read-write
            STATUS  mandatory
            DESCRIPTION
                "The tx Path Signal Label"
            ::= { vte1J2SigLabelEntry 9 }


--
--  VTE1 Alarm Setup Table
--

        vte1AlarmSetupTable  OBJECT-TYPE
            SYNTAX  SEQUENCE OF VTE1AlarmSetupEntry
            ACCESS  not-accessible
            STATUS  mandatory
            DESCRIPTION
                "VTE1 Alarm setup table"
            ::= { tsiFunction 16 }

        vte1AlarmSetupEntry  OBJECT-TYPE
            SYNTAX  VTE1AlarmSetupEntry
            ACCESS  not-accessible
            STATUS  mandatory
            DESCRIPTION
                "An entry in the alarm setup table"
            INDEX { vte1AlarmPort ,
                    vte1AlarmIndex }
            ::= { vte1AlarmSetupTable 1 }

        VTE1AlarmSetupEntry ::= SEQUENCE {
            vte1AlarmPort               Vte1ID,
            vte1AlarmIndex              INTEGER,
            vte1AlarmType               INTEGER,
            vte1AlarmMask               INTEGER,
            vte1AlarmRelay              INTEGER,
            vte1AlarmSeverity           Severity
        }

        vte1AlarmPort  OBJECT-TYPE
            SYNTAX  Vte1ID
            ACCESS  read-only
            STATUS  mandatory
            DESCRIPTION
                "VTE1 Port 1 to 28"
            ::= { vte1AlarmSetupEntry 2 }

        vte1AlarmIndex  OBJECT-TYPE
            SYNTAX  INTEGER {
                    loVT-LOP(1),
                    loVT-AIS(2),
                    loVT-UNEQ(3),
                    loVT-PLM(4),
                    loVT-TIM(5),
                    loVT-RDI-P(6),
                    loVT-RDI-S(7),
                    loVT-RDI-C(8),
                    loVT-V5-REI(9),
                    loVT-V5-BIP(10),
                    line-LOF(11),
                    line-AIS(12),
                    line-RAI-YEL(13),
                    performance(14)
                }
            ACCESS  read-only
            STATUS  mandatory
            DESCRIPTION
                "VTE1 ALarm index"
            ::= { vte1AlarmSetupEntry 3 }

        vte1AlarmType  OBJECT-TYPE
            SYNTAX  INTEGER{
                    loPath-vtPath(1),
                    line(2),
                    performance(3)
                }
            ACCESS  read-only
            STATUS  mandatory
            DESCRIPTION
                "VTE1 alarm type"
            ::= { vte1AlarmSetupEntry 4 }

        vte1AlarmMask  OBJECT-TYPE
            SYNTAX  INTEGER{
                    disable(1),
                    enable(2)
                }
            ACCESS  read-write
            STATUS  mandatory
            DESCRIPTION
                "VTE1 alarm mask"
            ::= { vte1AlarmSetupEntry 5 }

        vte1AlarmRelay  OBJECT-TYPE
            SYNTAX  INTEGER{
                    disable(1),
                    enable(2)
                }
            ACCESS  read-write
            STATUS  mandatory
            DESCRIPTION
                "VTE1 alarm relay"
            ::= { vte1AlarmSetupEntry 6 }

        vte1AlarmSeverity  OBJECT-TYPE
            SYNTAX  Severity
            ACCESS  read-write
            STATUS  mandatory
            DESCRIPTION
                "VTE1 alarm severity for all ports"
            ::= { vte1AlarmSetupEntry 7 }


--
--  VTE1 Current Alarm Status Table
--

        vte1CurrAlmStatusTable  OBJECT-TYPE
            SYNTAX  SEQUENCE OF VTE1CurrAlmStatusEntry
            ACCESS  not-accessible
            STATUS  mandatory
            DESCRIPTION
                "Current alarm status table"
            ::= { tsiFunction 18 }

        vte1CurrAlmStatusEntry  OBJECT-TYPE
            SYNTAX  VTE1CurrAlmStatusEntry
            ACCESS  not-accessible
            STATUS  mandatory
            DESCRIPTION
                "An entry in the current alarm status table"
            INDEX { vte1CurrAlmPort ,
                    vte1CurrAlmIndex }
            ::= { vte1CurrAlmStatusTable 1 }

        VTE1CurrAlmStatusEntry ::= SEQUENCE {
            vte1CurrAlmPort             Vte1ID,
            vte1CurrAlmIndex            INTEGER,
            vte1CurrAlmType             INTEGER,
            vte1CurrAlmStatus           AlmStatus
        }

        vte1CurrAlmPort  OBJECT-TYPE
            SYNTAX  Vte1ID
            ACCESS  read-only
            STATUS  mandatory
            DESCRIPTION
                "VTE1 Port 1 to 28"
            ::= { vte1CurrAlmStatusEntry 2 }

        vte1CurrAlmIndex  OBJECT-TYPE
            SYNTAX  INTEGER {
                    loVT-LOP(1),
                    loVT-AIS(2),
                    loVT-UNEQ(3),
                    loVT-PLM(4),
                    loVT-TIM(5),
                    loVT-RDI-P(6),
                    loVT-RDI-S(7),
                    loVT-RDI-C(8),
                    loVT-V5-REI(9),
                    loVT-V5-BIP(10),
                    line-LOF(11),
                    line-AIS(12),
                    line-RAI-YEL(13),
                    loVT-TCA-BIP-V5(14),
                    loVT-TCA-REI-V5(15),
                    line-TCA-ES(16),
                    line-TCA-SES(17),
                    line-TCA-UAS(18)
                }
            ACCESS  read-only
            STATUS  mandatory
            DESCRIPTION
                "VTE1 alarm index"
            ::= { vte1CurrAlmStatusEntry 3 }

        vte1CurrAlmType  OBJECT-TYPE
            SYNTAX  INTEGER{
                    loPath-vtPath(1),
                    line(2)
                }
            ACCESS  read-only
            STATUS  mandatory
            DESCRIPTION
                "VTE1 alarm type"
            ::= { vte1CurrAlmStatusEntry 4 }

        vte1CurrAlmStatus  OBJECT-TYPE
            SYNTAX  AlmStatus
            ACCESS  read-only
            STATUS  mandatory
            DESCRIPTION
                "VTE1 alarm status"
            ::= { vte1CurrAlmStatusEntry 5 }


--
--  VTE1 Loopback Setup Table
--

        vte1LoopbackTable  OBJECT-TYPE
            SYNTAX  SEQUENCE OF VTE1LoopbackEntry
            ACCESS  not-accessible
            STATUS  mandatory
            DESCRIPTION
                "VTE1 Loopback setup table"
            ::= { tsiFunction 21 }

        vte1LoopbackEntry  OBJECT-TYPE
            SYNTAX  VTE1LoopbackEntry
            ACCESS  not-accessible
            STATUS  mandatory
            DESCRIPTION
                "An entry in the loopback setup table"
            INDEX { vte1LoopbackPort }
            ::= { vte1LoopbackTable 1 }

        VTE1LoopbackEntry ::= SEQUENCE {
            vte1LoopbackPort            Vte1ID,
            vte1LoopbackType            INTEGER
        }

        vte1LoopbackPort  OBJECT-TYPE
            SYNTAX  Vte1ID
            ACCESS  read-only
            STATUS  mandatory
            DESCRIPTION
                "VTE1 Port 1 to 28"
            ::= { vte1LoopbackEntry 2 }

        vte1LoopbackType  OBJECT-TYPE
            SYNTAX  INTEGER{
                    off(1),
                    to-low-speed(2),
                    to-system(3)
                }
            ACCESS  read-write
            STATUS  mandatory
            DESCRIPTION
                "VTE1 Loopback type"
            ::= { vte1LoopbackEntry 3 }


--
--  VTE1 XC Display Table
--
        vte1XcDisplayTable  OBJECT-TYPE
            SYNTAX  SEQUENCE OF  Vte1XcDisplayEntry
            ACCESS  not-accessible
            STATUS  mandatory
            DESCRIPTION
                "VTE1 XC display table "
            ::= { tsiFunction 22 }

        vte1XcDisplayEntry  OBJECT-TYPE
            SYNTAX  Vte1XcDisplayEntry
            ACCESS  not-accessible
            STATUS  mandatory
            DESCRIPTION
                "VTE1 XC display entry"
            INDEX { vte1XcDispMap , vte1XcDispUnit ,
                    vte1XcDispPort , vte1XcDispAug1Sts3 ,
                    vte1XcDispVc3Sts1 , vte1XcDispVc1xVtx }
            ::= { vte1XcDisplayTable 1 }

        Vte1XcDisplayEntry ::= SEQUENCE {
            vte1XcDispMap               XcMap,
            vte1XcDispUnit              UnitID,
            vte1XcDispPort              PortID,
            vte1XcDispAug1Sts3          Aug1Sts3Num,
            vte1XcDispVc3Sts1           Vc3Sts1Num,
            vte1XcDispVc1xVtx           Vc1xVtxNum,
            vte1XcDispPriType           NewXcModel,
            vte1XcDispPriSlot           XcSlot,
            vte1XcDispPriPort           PortID,
            vte1XcDispPriChannel        ChannelNum,
            vte1XcDispPriAug1Sts3Path   Aug1Sts3Num,
            vte1XcDispPriVc3Sts1Path    Vc3Sts1Num,
            vte1XcDispPriVc1xVtxPath    Vc1xVtxNum,
            vte1XcDispXcGranularity     INTEGER,
            vte1XcDispXcType            XcType,
            vte1XcDispSecType           NewXcModel,
            vte1XcDispSecSlot           XcSlot,
            vte1XcDispSecPort           PortID,
            vte1XcDispSecChannel        ChannelNum,
            vte1XcDispSecAug1Sts3Path   Aug1Sts3Num,
            vte1XcDispSecVc3Sts1Path    Vc3Sts1Num,
            vte1XcDispSecVc1xVtxPath    Vc1xVtxNum
        }

        vte1XcDispMap  OBJECT-TYPE
            SYNTAX  XcMap
            ACCESS  read-only
            STATUS  mandatory
            DESCRIPTION
                "xc map index"
            ::= { vte1XcDisplayEntry 1 }

        vte1XcDispUnit  OBJECT-TYPE
            SYNTAX  UnitID
            ACCESS  read-only
            STATUS  mandatory
            DESCRIPTION
                "VTE1 unit."
            ::= { vte1XcDisplayEntry 2 }

        vte1XcDispPort  OBJECT-TYPE
            SYNTAX  PortID
            ACCESS  read-only
            STATUS  mandatory
            DESCRIPTION
                "PORT"
            ::= { vte1XcDisplayEntry 3 }

        vte1XcDispAug1Sts3  OBJECT-TYPE
            SYNTAX  Aug1Sts3Num
            ACCESS  read-only
            STATUS  mandatory
            DESCRIPTION
                "AUG1/STS3 index"
            ::= { vte1XcDisplayEntry 4 }

        vte1XcDispVc3Sts1  OBJECT-TYPE
            SYNTAX  Vc3Sts1Num
            ACCESS  read-only
            STATUS  mandatory
            DESCRIPTION
                "VC3/STS1 index"
            ::= { vte1XcDisplayEntry 5 }

        vte1XcDispVc1xVtx  OBJECT-TYPE
            SYNTAX  Vc1xVtxNum
            ACCESS  read-only
            STATUS  mandatory
            DESCRIPTION
                "VC1x/VTx index"
            ::= { vte1XcDisplayEntry 6 }

        vte1XcDispPriType  OBJECT-TYPE
            SYNTAX  NewXcModel
            ACCESS  read-only
            STATUS  mandatory
            DESCRIPTION
                " Xc Primary Unit Type"
            ::= { vte1XcDisplayEntry 7 }

        vte1XcDispPriSlot  OBJECT-TYPE
            SYNTAX  XcSlot
            ACCESS  read-only
            STATUS  mandatory
            DESCRIPTION
                "Xc Primary Unit "
            ::= { vte1XcDisplayEntry 8 }

        vte1XcDispPriPort  OBJECT-TYPE
            SYNTAX  PortID
            ACCESS  read-only
            STATUS  mandatory
            DESCRIPTION
                "Xc Primary port "
            ::= { vte1XcDisplayEntry 9 }

        vte1XcDispPriChannel  OBJECT-TYPE
            SYNTAX  ChannelNum
            ACCESS  read-only
            STATUS  mandatory
            DESCRIPTION
                "Xc Primary channel "
            ::= { vte1XcDisplayEntry 10 }

        vte1XcDispPriAug1Sts3Path  OBJECT-TYPE
            SYNTAX  Aug1Sts3Num
            ACCESS  read-only
            STATUS  mandatory
            DESCRIPTION
                "Xc Primary AUG1/STS3 path"
            ::= { vte1XcDisplayEntry 11 }

        vte1XcDispPriVc3Sts1Path  OBJECT-TYPE
            SYNTAX  Vc3Sts1Num
            ACCESS  read-only
            STATUS  mandatory
            DESCRIPTION
                "Xc Primary VC3/STS1 path"
            ::= { vte1XcDisplayEntry 12 }

        vte1XcDispPriVc1xVtxPath  OBJECT-TYPE
            SYNTAX  Vc1xVtxNum
            ACCESS  read-only
            STATUS  mandatory
            DESCRIPTION
                "Xc Primary VC1x/VTx path"
            ::= { vte1XcDisplayEntry 13 }

        vte1XcDispXcGranularity  OBJECT-TYPE
            SYNTAX  INTEGER {
                    tu11-vt15(4),
                    tu12-vt2(5),
                    not-available(100)
                }
            ACCESS  read-only
            STATUS  mandatory
            DESCRIPTION
                "Xc granularity"
            ::= { vte1XcDisplayEntry 14 }

        vte1XcDispXcType  OBJECT-TYPE
            SYNTAX  XcType
            ACCESS  read-only
            STATUS  mandatory
            DESCRIPTION
                "Xc type"
            ::= { vte1XcDisplayEntry 15 }

        vte1XcDispSecType  OBJECT-TYPE
            SYNTAX  NewXcModel
            ACCESS  read-only
            STATUS  mandatory
            DESCRIPTION
                " Xc Secondary Unit Type"
            ::= { vte1XcDisplayEntry 16 }

        vte1XcDispSecSlot  OBJECT-TYPE
            SYNTAX  XcSlot
            ACCESS  read-only
            STATUS  mandatory
            DESCRIPTION
                "Xc Secondary Unit "
            ::= { vte1XcDisplayEntry 17 }

        vte1XcDispSecPort  OBJECT-TYPE
            SYNTAX  PortID
            ACCESS  read-only
            STATUS  mandatory
            DESCRIPTION
                "Xc Secondary port "
            ::= { vte1XcDisplayEntry 18 }

        vte1XcDispSecChannel  OBJECT-TYPE
            SYNTAX  ChannelNum
            ACCESS  read-only
            STATUS  mandatory
            DESCRIPTION
                "Xc Secondary channel "
            ::= { vte1XcDisplayEntry 19 }

        vte1XcDispSecAug1Sts3Path  OBJECT-TYPE
            SYNTAX  Aug1Sts3Num
            ACCESS  read-only
            STATUS  mandatory
            DESCRIPTION
                "Xc Secondary AUG1/STS3 path"
            ::= { vte1XcDisplayEntry 20 }

        vte1XcDispSecVc3Sts1Path  OBJECT-TYPE
            SYNTAX  Vc3Sts1Num
            ACCESS  read-only
            STATUS  mandatory
            DESCRIPTION
                "Xc Secondary VC3/STS1 path"
            ::= { vte1XcDisplayEntry 21 }

        vte1XcDispSecVc1xVtxPath  OBJECT-TYPE
            SYNTAX  Vc1xVtxNum
            ACCESS  read-only
            STATUS  mandatory
            DESCRIPTION
                "Xc Secondary VC1x/VTx path"
            ::= { vte1XcDisplayEntry 22 }


--
-- New VTE1 SNCP/UPSR APS Table
--

        vte1NewSncpApsTab  OBJECT-TYPE
            SYNTAX  SEQUENCE OF  Vte1NewSncpApsEty
            ACCESS  not-accessible
            STATUS  mandatory
            DESCRIPTION
                "VTE1 New SNCP APS table"
            ::= { tsiFunction 23 }

        vte1NewSncpApsEty  OBJECT-TYPE
            SYNTAX  Vte1NewSncpApsEty
            ACCESS  not-accessible
            STATUS  mandatory
            DESCRIPTION
                "VTE1 New SNCP APS entry"
            INDEX { vte1NewSncpUnit , vte1NewSncpPort }
            ::= { vte1NewSncpApsTab 1 }

        Vte1NewSncpApsEty ::= SEQUENCE {
            vte1NewSncpUnit             UnitID,
            vte1NewSncpPort             PortID,
            vte1NewSncpCurrSlot         XcSlot,
            vte1NewSncpCurrPort         PortID,
            vte1NewSncpCurrChannel      ChannelNum,
            vte1NewSncpCurrAug1Sts3Path Aug1Sts3Num,
            vte1NewSncpCurrVc3Sts1Path  Vc3Sts1Num,
            vte1NewSncpCurrVc1xVtxPath  Vc1xVtxNum,
            vte1NewSncpPPType           XcType,
            vte1NewSncpCmd              SncpUserCmd,
            vte1NewSncpRevertive        INTEGER
        }

        vte1NewSncpUnit  OBJECT-TYPE
            SYNTAX  UnitID
            ACCESS  read-only
            STATUS  mandatory
            DESCRIPTION
                "VTE1 unit."
            ::= { vte1NewSncpApsEty 1 }

        vte1NewSncpPort  OBJECT-TYPE
            SYNTAX  PortID
            ACCESS  read-only
            STATUS  mandatory
            DESCRIPTION
                "PORT"
            ::= { vte1NewSncpApsEty 2 }

        vte1NewSncpCurrSlot  OBJECT-TYPE
            SYNTAX  XcSlot
            ACCESS  read-only
            STATUS  mandatory
            DESCRIPTION
                "SNCP/UPSR current slot"
            ::= { vte1NewSncpApsEty 3 }

        vte1NewSncpCurrPort  OBJECT-TYPE
            SYNTAX  PortID
            ACCESS  read-only
            STATUS  mandatory
            DESCRIPTION
                "SNCP/UPSR current port"
            ::= { vte1NewSncpApsEty 4 }

        vte1NewSncpCurrChannel  OBJECT-TYPE
            SYNTAX  ChannelNum
            ACCESS  read-only
            STATUS  mandatory
            DESCRIPTION
                "SNCP/UPSR current channel"
            ::= { vte1NewSncpApsEty 5 }

        vte1NewSncpCurrAug1Sts3Path  OBJECT-TYPE
            SYNTAX  Aug1Sts3Num
            ACCESS  read-only
            STATUS  mandatory
            DESCRIPTION
                "SNCP/UPSR current Aug1/Sts3"
            ::= { vte1NewSncpApsEty 6 }

        vte1NewSncpCurrVc3Sts1Path  OBJECT-TYPE
            SYNTAX  Vc3Sts1Num
            ACCESS  read-only
            STATUS  mandatory
            DESCRIPTION
                "SNCP/UPSR current Vc3/Sts1"
            ::= { vte1NewSncpApsEty 7 }

        vte1NewSncpCurrVc1xVtxPath  OBJECT-TYPE
            SYNTAX  Vc1xVtxNum
            ACCESS  read-only
            STATUS  mandatory
            DESCRIPTION
                "SNCP/UPSR current Vc1x/Vtx"
            ::= { vte1NewSncpApsEty 8 }

        vte1NewSncpPPType  OBJECT-TYPE
            SYNTAX  XcType
            ACCESS  read-only
            STATUS  mandatory
            DESCRIPTION
                "SNCP/UPSR path protection type"
            ::= { vte1NewSncpApsEty 9 }

        vte1NewSncpCmd  OBJECT-TYPE
            SYNTAX  SncpUserCmd
            ACCESS  read-write
            STATUS  mandatory
            DESCRIPTION
                "SNCP/UPSR APS command"
            ::= { vte1NewSncpApsEty 10 }

        vte1NewSncpRevertive  OBJECT-TYPE
            SYNTAX  INTEGER {
                    non-revertive(1),
                    revertive(2)
                }
            ACCESS  read-write
            STATUS  mandatory
            DESCRIPTION
                "SNCP/UPSR revertive or non-revertive"
            ::= { vte1NewSncpApsEty 11 }


--
--  VTE1 Performance
--

    vte1Performance           OBJECT IDENTIFIER ::= { tsiFunction 31 }


        vte1PerfCtrlClearPerf  OBJECT-TYPE
            SYNTAX  INTEGER {
                    clear(1)
                }
            ACCESS  read-write
            STATUS  mandatory
            DESCRIPTION
                "Clear VTE1 performance data"
            ::= { vte1Performance 1 }

--
--  VTE1 Performance Threshold Setup Table
--

        vte1PerfThreshSetupTable  OBJECT-TYPE
            SYNTAX  SEQUENCE OF VTE1PerfThreshSetupEntry
            ACCESS  not-accessible
            STATUS  mandatory
            DESCRIPTION
                "VTE1 Performance threshold setup"
            ::= { vte1Performance 2 }

        vte1PerfThreshSetupEntry  OBJECT-TYPE
            SYNTAX  VTE1PerfThreshSetupEntry
            ACCESS  not-accessible
            STATUS  mandatory
            DESCRIPTION
                "An entry in the performance threshold setup table"
            INDEX { vte1PerfTCAMonitorPoint }
            ::= { vte1PerfThreshSetupTable 1 }

        VTE1PerfThreshSetupEntry ::= SEQUENCE {
            vte1PerfTCAMonitorPoint     INTEGER,
            vte1PerfTCAType             INTEGER,
            vte1PerfTCAEnable           INTEGER,
            vte1PerfTCASeverity         Severity,
            vte1PerfTCAThreshold        INTEGER
        }

        vte1PerfTCAMonitorPoint  OBJECT-TYPE
            SYNTAX  INTEGER {
                    v5-bip(1),
                    v5-rei(2),
                    line-es(3),
                    line-ses(4),
                    line-uas(5)
                }
            ACCESS  read-only
            STATUS  mandatory
            DESCRIPTION
                "TCA monitor point index"
            ::= { vte1PerfThreshSetupEntry 2 }

        vte1PerfTCAType  OBJECT-TYPE
            SYNTAX  INTEGER{
                    loPath-vtPath(1),
                    line(2)
                }
            ACCESS  read-only
            STATUS  mandatory
            DESCRIPTION
                "VTE1 performance threshold type"
            ::= { vte1PerfThreshSetupEntry 3 }

        vte1PerfTCAEnable  OBJECT-TYPE
            SYNTAX  INTEGER{
                    disable(1),
                    enable(2)
                }
            ACCESS  read-write
            STATUS  mandatory
            DESCRIPTION
                "TCA disable/enable"
            ::= { vte1PerfThreshSetupEntry 4 }

        vte1PerfTCASeverity  OBJECT-TYPE
            SYNTAX  Severity
            ACCESS  read-write
            STATUS  mandatory
            DESCRIPTION
                "TCA severity"
            ::= { vte1PerfThreshSetupEntry 5 }

        vte1PerfTCAThreshold  OBJECT-TYPE
            SYNTAX  INTEGER (1..99999)
            ACCESS  read-write
            STATUS  mandatory
            DESCRIPTION
                "TCA threshold"
            ::= { vte1PerfThreshSetupEntry 6 }


--
--  VTE1 Performance Report LoPath/VTPath Current Table
--

        vte1LP-VTPCurrTable  OBJECT-TYPE
            SYNTAX  SEQUENCE OF VTE1LP-VTPCurrEntry
            ACCESS  not-accessible
            STATUS  mandatory
            DESCRIPTION
                "Performance report current"
            ::= { vte1Performance 11 }

        vte1LP-VTPCurrEntry  OBJECT-TYPE
            SYNTAX  VTE1LP-VTPCurrEntry
            ACCESS  not-accessible
            STATUS  mandatory
            DESCRIPTION
                "An entry in the performance report current table"
            INDEX { vte1LoVTCurrPort ,
                    vte1LoVTCurrAnomalyType }
            ::= { vte1LP-VTPCurrTable 1 }

        VTE1LP-VTPCurrEntry ::= SEQUENCE {
            vte1LoVTCurrPort            Vte1ID,
            vte1LoVTCurrAnomalyType     LoPathPerfAnomalyType,
            vte1LoVTCurrEB-Count        INTEGER,
            vte1LoVTCurrBBE-Count       INTEGER,
            vte1LoVTCurrES-Count        INTEGER,
            vte1LoVTCurrUAS-Count       INTEGER,
            vte1LoVTCurrBES-Count       INTEGER,
            vte1LoVTCurrSES-Count       INTEGER,
            vte1LoVTCurr15MinTimeElaps  INTEGER,
            vte1LoVTCurr24hrValid15Min  INTEGER,
            vte1LoVTCurrDayValid15Min   INTEGER,
            vte1LoVTCurr7DayValidDays   INTEGER
        }

        vte1LoVTCurrPort  OBJECT-TYPE
            SYNTAX  Vte1ID
            ACCESS  read-only
            STATUS  mandatory
            DESCRIPTION
                "VTE1 Port 1 to 28"
            ::= { vte1LP-VTPCurrEntry 2 }

        vte1LoVTCurrAnomalyType  OBJECT-TYPE
            SYNTAX  LoPathPerfAnomalyType
            ACCESS  read-only
            STATUS  mandatory
            DESCRIPTION
                "Performance report LoPath/VTPath Anomaly Type"
            ::= { vte1LP-VTPCurrEntry 3 }

        vte1LoVTCurrEB-Count  OBJECT-TYPE
            SYNTAX  INTEGER
            ACCESS  read-only
            STATUS  mandatory
            DESCRIPTION
                "Current Error Block"
            ::= { vte1LP-VTPCurrEntry 4 }

        vte1LoVTCurrBBE-Count  OBJECT-TYPE
            SYNTAX  INTEGER
            ACCESS  read-only
            STATUS  mandatory
            DESCRIPTION
                "Current Background Block Error"
            ::= { vte1LP-VTPCurrEntry 5 }

        vte1LoVTCurrES-Count  OBJECT-TYPE
            SYNTAX  INTEGER
            ACCESS  read-only
            STATUS  mandatory
            DESCRIPTION
                "Error Second"
            ::= { vte1LP-VTPCurrEntry 6 }

        vte1LoVTCurrUAS-Count  OBJECT-TYPE
            SYNTAX  INTEGER
            ACCESS  read-only
            STATUS  mandatory
            DESCRIPTION
                "Unavailable Second"
            ::= { vte1LP-VTPCurrEntry 7 }

        vte1LoVTCurrBES-Count  OBJECT-TYPE
            SYNTAX  INTEGER
            ACCESS  read-only
            STATUS  mandatory
            DESCRIPTION
                "Background Error Second"
            ::= { vte1LP-VTPCurrEntry 8 }

        vte1LoVTCurrSES-Count  OBJECT-TYPE
            SYNTAX  INTEGER
            ACCESS  read-only
            STATUS  mandatory
            DESCRIPTION
                "Severly Error Second"
            ::= { vte1LP-VTPCurrEntry 9 }

        vte1LoVTCurr15MinTimeElaps  OBJECT-TYPE
            SYNTAX  INTEGER
            ACCESS  read-only
            STATUS  mandatory
            DESCRIPTION
                "Valid Seconds in Current 15-Min Interval"
            ::= { vte1LP-VTPCurrEntry 10 }

        vte1LoVTCurr24hrValid15Min  OBJECT-TYPE
            SYNTAX  INTEGER
            ACCESS  read-only
            STATUS  mandatory
            DESCRIPTION
                "Valid 15-Min Intervals in Current 24-Hour Interval"
            ::= { vte1LP-VTPCurrEntry 11 }

        vte1LoVTCurrDayValid15Min  OBJECT-TYPE
            SYNTAX  INTEGER
            ACCESS  read-only
            STATUS  mandatory
            DESCRIPTION
                "Valid 15-Min Intervals in Current Day"
            ::= { vte1LP-VTPCurrEntry 12 }

        vte1LoVTCurr7DayValidDays  OBJECT-TYPE
            SYNTAX  INTEGER
            ACCESS  read-only
            STATUS  mandatory
            DESCRIPTION
                "Valid Days in Current Seven Day"
            ::= { vte1LP-VTPCurrEntry 13 }


--
--  VTE1 Performance Report LoPath/VTPath Interval Table
--

        vte1LP-VTPIntvTable  OBJECT-TYPE
            SYNTAX  SEQUENCE OF VTE1LP-VTPIntvEntry
            ACCESS  not-accessible
            STATUS  mandatory
            DESCRIPTION
                "Performance report Inteval"
            ::= { vte1Performance 12 }

        vte1LP-VTPIntvEntry  OBJECT-TYPE
            SYNTAX  VTE1LP-VTPIntvEntry
            ACCESS  not-accessible
            STATUS  mandatory
            DESCRIPTION
                "An entry in the performance report interval table"
            INDEX { vte1LoVTIntvPort ,
                    vte1LoVTIntvAnomalyType ,
                    vte1LoVTIntvPeriod }
            ::= { vte1LP-VTPIntvTable 1 }

        VTE1LP-VTPIntvEntry ::= SEQUENCE {
            vte1LoVTIntvPort            Vte1ID,
            vte1LoVTIntvAnomalyType     LoPathPerfAnomalyType,
            vte1LoVTIntvPeriod          INTEGER (1..96),
            vte1LoVTIntvEB-Count        INTEGER,
            vte1LoVTIntvBBE-Count       INTEGER,
            vte1LoVTIntvES-Count        INTEGER,
            vte1LoVTIntvUAS-Count       INTEGER,
            vte1LoVTIntvBES-Count       INTEGER,
            vte1LoVTIntvSES-Count       INTEGER
        }

        vte1LoVTIntvPort  OBJECT-TYPE
            SYNTAX  Vte1ID
            ACCESS  read-only
            STATUS  mandatory
            DESCRIPTION
                "VTE1 Port 1 to 28"
            ::= { vte1LP-VTPIntvEntry 2 }

        vte1LoVTIntvAnomalyType  OBJECT-TYPE
            SYNTAX  LoPathPerfAnomalyType
            ACCESS  read-only
            STATUS  mandatory
            DESCRIPTION
                "Performance report LoPath/VTPath Anomaly Type"
            ::= { vte1LP-VTPIntvEntry 3 }

        vte1LoVTIntvPeriod  OBJECT-TYPE
            SYNTAX  INTEGER (1..96)
            ACCESS  read-only
            STATUS  mandatory
            DESCRIPTION
                "LoPath Interval Period"
            ::= { vte1LP-VTPIntvEntry 4 }

        vte1LoVTIntvEB-Count  OBJECT-TYPE
            SYNTAX  INTEGER
            ACCESS  read-only
            STATUS  mandatory
            DESCRIPTION
                "Current Error Block"
            ::= { vte1LP-VTPIntvEntry 5 }

        vte1LoVTIntvBBE-Count  OBJECT-TYPE
            SYNTAX  INTEGER
            ACCESS  read-only
            STATUS  mandatory
            DESCRIPTION
                "Current Background Block Error"
            ::= { vte1LP-VTPIntvEntry 6 }

        vte1LoVTIntvES-Count  OBJECT-TYPE
            SYNTAX  INTEGER
            ACCESS  read-only
            STATUS  mandatory
            DESCRIPTION
                "Error Second"
            ::= { vte1LP-VTPIntvEntry 7 }

        vte1LoVTIntvUAS-Count  OBJECT-TYPE
            SYNTAX  INTEGER
            ACCESS  read-only
            STATUS  mandatory
            DESCRIPTION
                "Unavailable Second"
            ::= { vte1LP-VTPIntvEntry 8 }

        vte1LoVTIntvBES-Count  OBJECT-TYPE
            SYNTAX  INTEGER
            ACCESS  read-only
            STATUS  mandatory
            DESCRIPTION
                "Background Error Second"
            ::= { vte1LP-VTPIntvEntry 9 }

        vte1LoVTIntvSES-Count  OBJECT-TYPE
            SYNTAX  INTEGER
            ACCESS  read-only
            STATUS  mandatory
            DESCRIPTION
                "Severly Error Second"
            ::= { vte1LP-VTPIntvEntry 10 }


--
--  VTE1 Performance Report LoPath/VT-Path Seven Days Table
--

        vte1LP-VTP7DaysTable  OBJECT-TYPE
            SYNTAX  SEQUENCE OF VTE1LP-VTP7DaysEntry
            ACCESS  not-accessible
            STATUS  mandatory
            DESCRIPTION
                "Performance report Seven Days"
            ::= { vte1Performance 13 }

        vte1LP-VTP7DaysEntry  OBJECT-TYPE
            SYNTAX  VTE1LP-VTP7DaysEntry
            ACCESS  not-accessible
            STATUS  mandatory
            DESCRIPTION
                "An entry in the performance report seven days table"
            INDEX { vte1LoVT7DaysPort ,
                    vte1LoVT7DaysAnomalyType ,
                    vte1LoVT7DaysDayIndex }
            ::= { vte1LP-VTP7DaysTable 1 }

        VTE1LP-VTP7DaysEntry ::= SEQUENCE {
            vte1LoVT7DaysPort           Vte1ID,
            vte1LoVT7DaysAnomalyType    LoPathPerfAnomalyType,
            vte1LoVT7DaysDayIndex       INTEGER (1..7),
            vte1LoVT7DaysDate           DisplayString (SIZE (0..255) ),
            vte1LoVT7DaysEB-Count       INTEGER,
            vte1LoVT7DaysBBE-Count      INTEGER,
            vte1LoVT7DaysES-Count       INTEGER,
            vte1LoVT7DaysUAS-Count      INTEGER,
            vte1LoVT7DaysBES-Count      INTEGER,
            vte1LoVT7DaysSES-Count      INTEGER
        }

        vte1LoVT7DaysPort  OBJECT-TYPE
            SYNTAX  Vte1ID
            ACCESS  read-only
            STATUS  mandatory
            DESCRIPTION
                "VTE1 Port 1 to 28"
            ::= { vte1LP-VTP7DaysEntry 2 }

        vte1LoVT7DaysAnomalyType  OBJECT-TYPE
            SYNTAX  LoPathPerfAnomalyType
            ACCESS  read-only
            STATUS  mandatory
            DESCRIPTION
                "Performance report LoPath/VTPath Anomaly Type"
            ::= { vte1LP-VTP7DaysEntry 3 }

        vte1LoVT7DaysDayIndex  OBJECT-TYPE
            SYNTAX  INTEGER (1..7)
            ACCESS  read-only
            STATUS  mandatory
            DESCRIPTION
                "LoPath Seven Days day index"
            ::= { vte1LP-VTP7DaysEntry 4 }

        vte1LoVT7DaysDate  OBJECT-TYPE
            SYNTAX  DisplayString (SIZE (0..255) )
            ACCESS  read-only
            STATUS  mandatory
            DESCRIPTION
                "Seven Days Date"
            ::= { vte1LP-VTP7DaysEntry 5 }

        vte1LoVT7DaysEB-Count  OBJECT-TYPE
            SYNTAX  INTEGER
            ACCESS  read-only
            STATUS  mandatory
            DESCRIPTION
                "Current Error Block"
            ::= { vte1LP-VTP7DaysEntry 6 }

        vte1LoVT7DaysBBE-Count  OBJECT-TYPE
            SYNTAX  INTEGER
            ACCESS  read-only
            STATUS  mandatory
            DESCRIPTION
                "Current Background Block Error"
            ::= { vte1LP-VTP7DaysEntry 7 }

        vte1LoVT7DaysES-Count  OBJECT-TYPE
            SYNTAX  INTEGER
            ACCESS  read-only
            STATUS  mandatory
            DESCRIPTION
                "Error Second"
            ::= { vte1LP-VTP7DaysEntry 8 }

        vte1LoVT7DaysUAS-Count  OBJECT-TYPE
            SYNTAX  INTEGER
            ACCESS  read-only
            STATUS  mandatory
            DESCRIPTION
                "Unavailable Second"
            ::= { vte1LP-VTP7DaysEntry 9 }

        vte1LoVT7DaysBES-Count  OBJECT-TYPE
            SYNTAX  INTEGER
            ACCESS  read-only
            STATUS  mandatory
            DESCRIPTION
                "Background Error Second"
            ::= { vte1LP-VTP7DaysEntry 10 }

        vte1LoVT7DaysSES-Count  OBJECT-TYPE
            SYNTAX  INTEGER
            ACCESS  read-only
            STATUS  mandatory
            DESCRIPTION
                "Severly Error Second"
            ::= { vte1LP-VTP7DaysEntry 11 }


--
--  VTE1 Performance Report LoPath/VTPath Total Table
--

        vte1LP-VTPTotalTable  OBJECT-TYPE
            SYNTAX  SEQUENCE OF VTE1LP-VTPTotalEntry
            ACCESS  not-accessible
            STATUS  mandatory
            DESCRIPTION
                "Performance report Total"
            ::= { vte1Performance 14 }

        vte1LP-VTPTotalEntry  OBJECT-TYPE
            SYNTAX  VTE1LP-VTPTotalEntry
            ACCESS  not-accessible
            STATUS  mandatory
            DESCRIPTION
                "An entry in the performance report total table"
            INDEX { vte1LoVTTotalPort ,
                    vte1LoVTTotalAnomalyType }
            ::= { vte1LP-VTPTotalTable 1 }

        VTE1LP-VTPTotalEntry ::= SEQUENCE {
            vte1LoVTTotalPort           Vte1ID,
            vte1LoVTTotalAnomalyType    LoPathPerfAnomalyType,
            vte1LoVTTotalEB-Count       INTEGER,
            vte1LoVTTotalBBE-Count      INTEGER,
            vte1LoVTTotalES-Count       INTEGER,
            vte1LoVTTotalUAS-Count      INTEGER,
            vte1LoVTTotalBES-Count      INTEGER,
            vte1LoVTTotalSES-Count      INTEGER
        }

        vte1LoVTTotalPort  OBJECT-TYPE
            SYNTAX  Vte1ID
            ACCESS  read-only
            STATUS  mandatory
            DESCRIPTION
                "VTE1 Port 1 to 28"
            ::= { vte1LP-VTPTotalEntry 2 }

        vte1LoVTTotalAnomalyType  OBJECT-TYPE
            SYNTAX  LoPathPerfAnomalyType
            ACCESS  read-only
            STATUS  mandatory
            DESCRIPTION
                "Performance report LoPath/VTPath Anomaly Type"
            ::= { vte1LP-VTPTotalEntry 3 }

        vte1LoVTTotalEB-Count  OBJECT-TYPE
            SYNTAX  INTEGER
            ACCESS  read-only
            STATUS  mandatory
            DESCRIPTION
                "Current Error Block"
            ::= { vte1LP-VTPTotalEntry 4 }

        vte1LoVTTotalBBE-Count  OBJECT-TYPE
            SYNTAX  INTEGER
            ACCESS  read-only
            STATUS  mandatory
            DESCRIPTION
                "Current Background Block Error"
            ::= { vte1LP-VTPTotalEntry 5 }

        vte1LoVTTotalES-Count  OBJECT-TYPE
            SYNTAX  INTEGER
            ACCESS  read-only
            STATUS  mandatory
            DESCRIPTION
                "Error Second"
            ::= { vte1LP-VTPTotalEntry 6 }

        vte1LoVTTotalUAS-Count  OBJECT-TYPE
            SYNTAX  INTEGER
            ACCESS  read-only
            STATUS  mandatory
            DESCRIPTION
                "Unavailable Second"
            ::= { vte1LP-VTPTotalEntry 7 }

        vte1LoVTTotalBES-Count  OBJECT-TYPE
            SYNTAX  INTEGER
            ACCESS  read-only
            STATUS  mandatory
            DESCRIPTION
                "Background Error Second"
            ::= { vte1LP-VTPTotalEntry 8 }

        vte1LoVTTotalSES-Count  OBJECT-TYPE
            SYNTAX  INTEGER
            ACCESS  read-only
            STATUS  mandatory
            DESCRIPTION
                "Severly Error Second"
            ::= { vte1LP-VTPTotalEntry 9 }

--
--  VTE1 Performance Report Line Current Table
--

        vte1LineCurrTable  OBJECT-TYPE
            SYNTAX  SEQUENCE OF VTE1LineCurrEntry
            ACCESS  not-accessible
            STATUS  mandatory
            DESCRIPTION
                "Performance report current"
            ::= { vte1Performance 15 }

        vte1LineCurrEntry  OBJECT-TYPE
            SYNTAX  VTE1LineCurrEntry
            ACCESS  not-accessible
            STATUS  mandatory
            DESCRIPTION
                "An entry in the performance report current table"
            INDEX { vte1LineCurrPort }
            ::= { vte1LineCurrTable 1 }

        VTE1LineCurrEntry ::= SEQUENCE {
            vte1LineCurrPort            Vte1ID,
            vte1LineCurrES-Count        INTEGER,
            vte1LineCurrUAS-Count       INTEGER,
            vte1LineCurrBES-Count       INTEGER,
            vte1LineCurrSES-Count       INTEGER,
            vte1LineCurr15MinTimeElaps  INTEGER,
            vte1LineCurr24hrValid15Min  INTEGER,
            vte1LineCurrDayValid15Min   INTEGER,
            vte1LineCurr7DayValidDays   INTEGER
        }

        vte1LineCurrPort  OBJECT-TYPE
            SYNTAX  Vte1ID
            ACCESS  read-only
            STATUS  mandatory
            DESCRIPTION
                "VTE1 Port 1 to 28"
            ::= { vte1LineCurrEntry 2 }


        vte1LineCurrES-Count  OBJECT-TYPE
            SYNTAX  INTEGER
            ACCESS  read-only
            STATUS  mandatory
            DESCRIPTION
                "Error Second"
            ::= { vte1LineCurrEntry 3 }

        vte1LineCurrUAS-Count  OBJECT-TYPE
            SYNTAX  INTEGER
            ACCESS  read-only
            STATUS  mandatory
            DESCRIPTION
                "Unavailable Second"
            ::= { vte1LineCurrEntry 4 }

        vte1LineCurrBES-Count  OBJECT-TYPE
            SYNTAX  INTEGER
            ACCESS  read-only
            STATUS  mandatory
            DESCRIPTION
                "Background Error Second"
            ::= { vte1LineCurrEntry 5 }

        vte1LineCurrSES-Count  OBJECT-TYPE
            SYNTAX  INTEGER
            ACCESS  read-only
            STATUS  mandatory
            DESCRIPTION
                "Severly Error Second"
            ::= { vte1LineCurrEntry 6 }

        vte1LineCurr15MinTimeElaps  OBJECT-TYPE
            SYNTAX  INTEGER
            ACCESS  read-only
            STATUS  mandatory
            DESCRIPTION
                "Valid Seconds in Current 15-Min Interval"
            ::= { vte1LineCurrEntry 8 }

        vte1LineCurr24hrValid15Min  OBJECT-TYPE
            SYNTAX  INTEGER
            ACCESS  read-only
            STATUS  mandatory
            DESCRIPTION
                "Valid 15-Min Intervals in Current 24-Hour Interval"
            ::= { vte1LineCurrEntry 9 }

        vte1LineCurrDayValid15Min  OBJECT-TYPE
            SYNTAX  INTEGER
            ACCESS  read-only
            STATUS  mandatory
            DESCRIPTION
                "Valid 15-Min Intervals in Current Day"
            ::= { vte1LineCurrEntry 10 }

        vte1LineCurr7DayValidDays  OBJECT-TYPE
            SYNTAX  INTEGER
            ACCESS  read-only
            STATUS  mandatory
            DESCRIPTION
                "Valid Days in Current Seven Day"
            ::= { vte1LineCurrEntry 11 }


--
--  VTE1 Performance Report Line Interval Table
--

        vte1LineIntervalTable  OBJECT-TYPE
            SYNTAX  SEQUENCE OF VTE1LineIntervalEntry
            ACCESS  not-accessible
            STATUS  mandatory
            DESCRIPTION
                "Performance report Inteval"
            ::= { vte1Performance 16 }

        vte1LineIntervalEntry  OBJECT-TYPE
            SYNTAX  VTE1LineIntervalEntry
            ACCESS  not-accessible
            STATUS  mandatory
            DESCRIPTION
                "An entry in the performance report interval table"
            INDEX { vte1LineIntvPort ,
                    vte1LineIntvPeriod }
            ::= { vte1LineIntervalTable 1 }

        VTE1LineIntervalEntry ::= SEQUENCE {
            vte1LineIntvPort            Vte1ID,
            vte1LineIntvPeriod          INTEGER (1..96),
            vte1LineIntvES-Count        INTEGER,
            vte1LineIntvUAS-Count       INTEGER,
            vte1LineIntvBES-Count       INTEGER,
            vte1LineIntvSES-Count       INTEGER
        }

        vte1LineIntvPort  OBJECT-TYPE
            SYNTAX  Vte1ID
            ACCESS  read-only
            STATUS  mandatory
            DESCRIPTION
                "VTE1 Port 1 to 28"
            ::= { vte1LineIntervalEntry 2 }

        vte1LineIntvPeriod  OBJECT-TYPE
            SYNTAX  INTEGER (1..96)
            ACCESS  read-only
            STATUS  mandatory
            DESCRIPTION
                "Line Interval Period"
            ::= { vte1LineIntervalEntry 3 }

        vte1LineIntvES-Count  OBJECT-TYPE
            SYNTAX  INTEGER
            ACCESS  read-only
            STATUS  mandatory
            DESCRIPTION
                "Error Second"
            ::= { vte1LineIntervalEntry 4 }

        vte1LineIntvUAS-Count  OBJECT-TYPE
            SYNTAX  INTEGER
            ACCESS  read-only
            STATUS  mandatory
            DESCRIPTION
                "Unavailable Second"
            ::= { vte1LineIntervalEntry 5 }

        vte1LineIntvBES-Count  OBJECT-TYPE
            SYNTAX  INTEGER
            ACCESS  read-only
            STATUS  mandatory
            DESCRIPTION
                "Background Error Second"
            ::= { vte1LineIntervalEntry 6 }

        vte1LineIntvSES-Count  OBJECT-TYPE
            SYNTAX  INTEGER
            ACCESS  read-only
            STATUS  mandatory
            DESCRIPTION
                "Severly Error Second"
            ::= { vte1LineIntervalEntry 7 }


--
--  VTE1 Performance Report Line Seven Days Table
--

        vte1Line7DaysTable  OBJECT-TYPE
            SYNTAX  SEQUENCE OF VTE1Line7DaysEntry
            ACCESS  not-accessible
            STATUS  mandatory
            DESCRIPTION
                "Performance report seven days"
            ::= { vte1Performance 17 }

        vte1Line7DaysEntry  OBJECT-TYPE
            SYNTAX  VTE1Line7DaysEntry
            ACCESS  not-accessible
            STATUS  mandatory
            DESCRIPTION
                "An entry in the performance report seven days table"
            INDEX { vte1Line7DaysPort ,
                    vte1Line7DaysDayIndex }
            ::= { vte1Line7DaysTable 1 }

        VTE1Line7DaysEntry ::= SEQUENCE {
            vte1Line7DaysPort           Vte1ID,
            vte1Line7DaysDayIndex       INTEGER (1..7),
            vte1Line7DaysDate           DisplayString (SIZE (0..255) ),
            vte1Line7DaysES-Count       INTEGER,
            vte1Line7DaysUAS-Count      INTEGER,
            vte1Line7DaysBES-Count      INTEGER,
            vte1Line7DaysSES-Count      INTEGER
        }

        vte1Line7DaysPort  OBJECT-TYPE
            SYNTAX  Vte1ID
            ACCESS  read-only
            STATUS  mandatory
            DESCRIPTION
                "VTE1 Port 1 to 28"
            ::= { vte1Line7DaysEntry 2 }

        vte1Line7DaysDayIndex  OBJECT-TYPE
            SYNTAX  INTEGER (1..7)
            ACCESS  read-only
            STATUS  mandatory
            DESCRIPTION
                "Line Seven Days day index"
            ::= { vte1Line7DaysEntry 3 }

        vte1Line7DaysDate  OBJECT-TYPE
            SYNTAX  DisplayString (SIZE (0..255) )
            ACCESS  read-only
            STATUS  mandatory
            DESCRIPTION
                "Seven Days Date"
            ::= { vte1Line7DaysEntry 4 }

        vte1Line7DaysES-Count  OBJECT-TYPE
            SYNTAX  INTEGER
            ACCESS  read-only
            STATUS  mandatory
            DESCRIPTION
                "Error Second"
            ::= { vte1Line7DaysEntry 5 }

        vte1Line7DaysUAS-Count  OBJECT-TYPE
            SYNTAX  INTEGER
            ACCESS  read-only
            STATUS  mandatory
            DESCRIPTION
                "Unavailable Second"
            ::= { vte1Line7DaysEntry 6 }

        vte1Line7DaysBES-Count  OBJECT-TYPE
            SYNTAX  INTEGER
            ACCESS  read-only
            STATUS  mandatory
            DESCRIPTION
                "Background Error Second"
            ::= { vte1Line7DaysEntry 7 }

        vte1Line7DaysSES-Count  OBJECT-TYPE
            SYNTAX  INTEGER
            ACCESS  read-only
            STATUS  mandatory
            DESCRIPTION
                "Severly Error Second"
            ::= { vte1Line7DaysEntry 8 }


--
--  VTE1 Performance Report Line Total Table
--

        vte1LineTotalTable  OBJECT-TYPE
            SYNTAX  SEQUENCE OF VTE1LineTotalEntry
            ACCESS  not-accessible
            STATUS  mandatory
            DESCRIPTION
                "Performance report Total"
            ::= { vte1Performance 18 }

        vte1LineTotalEntry  OBJECT-TYPE
            SYNTAX  VTE1LineTotalEntry
            ACCESS  not-accessible
            STATUS  mandatory
            DESCRIPTION
                "An entry in the performance report total table"
            INDEX { vte1LineTotalPort }
            ::= { vte1LineTotalTable 1 }

        VTE1LineTotalEntry ::= SEQUENCE {
            vte1LineTotalPort           Vte1ID,
            vte1LineTotalES-Count       INTEGER,
            vte1LineTotalUAS-Count      INTEGER,
            vte1LineTotalBES-Count      INTEGER,
            vte1LineTotalSES-Count      INTEGER
        }

        vte1LineTotalPort  OBJECT-TYPE
            SYNTAX  Vte1ID
            ACCESS  read-only
            STATUS  mandatory
            DESCRIPTION
                "VTE1 Port 1 to 28"
            ::= { vte1LineTotalEntry 2 }

        vte1LineTotalES-Count  OBJECT-TYPE
            SYNTAX  INTEGER
            ACCESS  read-only
            STATUS  mandatory
            DESCRIPTION
                "Error Second"
            ::= { vte1LineTotalEntry 3 }

        vte1LineTotalUAS-Count  OBJECT-TYPE
            SYNTAX  INTEGER
            ACCESS  read-only
            STATUS  mandatory
            DESCRIPTION
                "Unavailable Second"
            ::= { vte1LineTotalEntry 4 }

        vte1LineTotalBES-Count  OBJECT-TYPE
            SYNTAX  INTEGER
            ACCESS  read-only
            STATUS  mandatory
            DESCRIPTION
                "Background Error Second"
            ::= { vte1LineTotalEntry 5 }

        vte1LineTotalSES-Count  OBJECT-TYPE
            SYNTAX  INTEGER
            ACCESS  read-only
            STATUS  mandatory
            DESCRIPTION
                "Severly Error Second"
            ::= { vte1LineTotalEntry 6 }


--
--  VTE1 Consolidation
--

    vte1Consolidation       OBJECT IDENTIFIER ::= { tsiFunction 41 }

        vte1GenCfgHexData  OBJECT-TYPE
            SYNTAX  OCTET STRING
            ACCESS  read-only
            STATUS  mandatory
            DESCRIPTION
                "Hex data: (len = 32)
                Byte 0: vintage = 1;
                Byte 1: mapper type (e1=0, t1=1, t1-tu12=2);
                Byte 2: max_port (21 or 28);
                Byte 3: oos;
                Byte 4~31: port 1~28 cfg;
                xxxrffff: ffff = frame mode,
                r = rdi mode,
                xxx = reserved."
            ::= { vte1Consolidation  1 }

        vte1GenAlmHexData  OBJECT-TYPE
            SYNTAX  OCTET STRING
            ACCESS  read-only
            STATUS  mandatory
            DESCRIPTION
                "Hex data"
            ::= { vte1Consolidation  2 }

        vte1AlmStatHexData  OBJECT-TYPE
            SYNTAX  OCTET STRING
            ACCESS  read-only
            STATUS  mandatory
            DESCRIPTION
                "Hex data"
            ::= { vte1Consolidation  3 }

        vte1LoopbackHexData  OBJECT-TYPE
            SYNTAX  OCTET STRING
            ACCESS  read-only
            STATUS  mandatory
            DESCRIPTION
                "Hex data: (len = 29)
                Byte 0: vintage = 1;
                Byte 1~28: port 1~28 cfg;
                xxxxxxll: ll = loopback type,
                xxxxxx = reserved."
            ::= { vte1Consolidation  4 }

--
--  VTE1 24hour Performance Summary Hex Table
--

        vte1PerfSummaryHexTab  OBJECT-TYPE
            SYNTAX  SEQUENCE OF  VTE1PerfSummaryHexEty
            ACCESS  not-accessible
            STATUS  mandatory
            DESCRIPTION
                "VTE1 performance summary hex Table "
            ::= { vte1Consolidation 11 }

        vte1PerfSummaryHexEty OBJECT-TYPE
            SYNTAX  VTE1PerfSummaryHexEty
            ACCESS  not-accessible
            STATUS  mandatory
            DESCRIPTION
                "An entry in the VTE1 performance summary hex table."
            INDEX { vte1PerfSummaryHexPort }
            ::= { vte1PerfSummaryHexTab 1 }

        VTE1PerfSummaryHexEty ::= SEQUENCE  {
            vte1PerfSummaryHexPort        Vte1ID,
            vte1PerfSummaryHexData        OCTET STRING
        }

        vte1PerfSummaryHexPort  OBJECT-TYPE
            SYNTAX  Vte1ID
            ACCESS  read-only
            STATUS  mandatory
            DESCRIPTION
                "VTE1 port 1~28"
            ::= { vte1PerfSummaryHexEty  2 }

        vte1PerfSummaryHexData  OBJECT-TYPE
            SYNTAX  OCTET STRING
            ACCESS  read-only
            STATUS  mandatory
            DESCRIPTION
                "Hex data"
            ::= { vte1PerfSummaryHexEty  3 }

--
--  VTE1 15Min Interval Performance Hex Table
--

        vte1Perf15MinIntvHexTab  OBJECT-TYPE
            SYNTAX  SEQUENCE OF  VTE1Perf15MinIntvHexEty
            ACCESS  not-accessible
            STATUS  mandatory
            DESCRIPTION
                "VTE1 15 min interval performance hex Table "
            ::= { vte1Consolidation 12 }

        vte1Perf15MinIntvHexEty OBJECT-TYPE
            SYNTAX  VTE1Perf15MinIntvHexEty
            ACCESS  not-accessible
            STATUS  mandatory
            DESCRIPTION
                "An entry in the VTE1 15 min interval performance hex table."
            INDEX { vte1Perf15MIntvHexPort ,
                    vte1Perf15MIntvHexAnomaly ,
                    vte1Perf15MIntvHexIntv }
            ::= { vte1Perf15MinIntvHexTab 1 }

        VTE1Perf15MinIntvHexEty ::= SEQUENCE  {
            vte1Perf15MIntvHexPort        Vte1ID,
            vte1Perf15MIntvHexAnomaly     INTEGER,
            vte1Perf15MIntvHexIntv        INTEGER,
            vte1Perf15MIntvHexData        OCTET STRING
        }

        vte1Perf15MIntvHexPort  OBJECT-TYPE
            SYNTAX  Vte1ID
            ACCESS  read-only
            STATUS  mandatory
            DESCRIPTION
                "VTE1 port 1~28"
            ::= { vte1Perf15MinIntvHexEty  2 }

        vte1Perf15MIntvHexAnomaly  OBJECT-TYPE
            SYNTAX  INTEGER {
                    bip-v5(1),
                    rei-v5(2),
                    line(3)
                }
            ACCESS  read-only
            STATUS  mandatory
            DESCRIPTION
                "anomal type"
            ::= { vte1Perf15MinIntvHexEty  3 }

        vte1Perf15MIntvHexIntv  OBJECT-TYPE
            SYNTAX  INTEGER (1..96)
            ACCESS  read-only
            STATUS  mandatory
            DESCRIPTION
                "interval value"
            ::= { vte1Perf15MinIntvHexEty  4 }

        vte1Perf15MIntvHexData  OBJECT-TYPE
            SYNTAX  OCTET STRING
            ACCESS  read-only
            STATUS  mandatory
            DESCRIPTION
                "Hex data"
            ::= { vte1Perf15MinIntvHexEty  5 }


--
--  Channel Map Group
--

    channelMap              OBJECT IDENTIFIER ::= { system 102 }

        activeMapNumber  OBJECT-TYPE
            SYNTAX  INTEGER {
                    tsimap1(1),
                    tsimap2(2)
                }
            ACCESS  read-write
            STATUS  mandatory
            DESCRIPTION
                "Active Map. include HS and LS"
            ::= { channelMap 1 }

        deleteMapNumber  OBJECT-TYPE
            SYNTAX  INTEGER {
                    tsimap1(1),
                    tsimap2(2)
                }
            ACCESS  read-write
            STATUS  mandatory
            DESCRIPTION
                "Delete Map. include HS and LS"
            ::= { channelMap 2 }

        copyMap  OBJECT-TYPE
            SYNTAX  INTEGER {
                    none(1),
                    copy-active-to-the-other(2)
                }
            ACCESS  read-write
            STATUS  mandatory
            DESCRIPTION
                "Copy active TSA map to other map, include HS and LS"
            ::= { channelMap 3 }

--
--  Current Map
--
        currentMapTable  OBJECT-TYPE
            SYNTAX  SEQUENCE OF CurrentMapEntry
            ACCESS  not-accessible
            STATUS  mandatory
            DESCRIPTION
                "A list of Current TSI Map."
            ::= { channelMap 11 }

        currentMapEntry  OBJECT-TYPE
            SYNTAX  CurrentMapEntry
            ACCESS  not-accessible
            STATUS  mandatory
            DESCRIPTION
                "An Entry for Current TSI Map."
            INDEX { currentChannelMapIndex ,
                    currentPortIndex ,
                    currentTimeSlotIndex }
            ::= { currentMapTable 1 }

        CurrentMapEntry ::= SEQUENCE  {
            currentChannelMapIndex      INTEGER,
            currentPortIndex            PortID,
            currentTimeSlotIndex        INTEGER,
            currentChannelType          INTEGER,
            currentMapToSlot            INTEGER,
            currentMapToPort            PortID,
            currentMapToTS              INTEGER
        }

        currentChannelMapIndex  OBJECT-TYPE
            SYNTAX  INTEGER   {
                    slot-11(11),
                    slot-12(12),
                    slot-13(13),
                    slot-14(14),
                    slot-15(15),
                    slot-16(16),
                    slot-17(17),
                    slot-18(18),
                    slot-19(19),
                    slot-20(20),
                    slot-inband(21),
                    slot-virtualTE1(23)
                }
            ACCESS  read-only
            STATUS  mandatory
            DESCRIPTION
                "Select Slot"
            ::= { currentMapEntry 1 }

        currentPortIndex  OBJECT-TYPE
            SYNTAX  PortID
            ACCESS  read-only
            STATUS  mandatory
            DESCRIPTION
                "Select port 1~32"
            ::= { currentMapEntry 2 }

        currentTimeSlotIndex  OBJECT-TYPE
            SYNTAX  INTEGER (1..32)
            ACCESS  read-only
            STATUS  mandatory
            DESCRIPTION
                "Time slot index."
            ::= { currentMapEntry 3 }

        currentChannelType  OBJECT-TYPE
            SYNTAX  INTEGER   {
                    data(1),
                    voice(2),
                    signal(3),
                    frame(4),
                    idle(5)
                }
            ACCESS  read-only
            STATUS  mandatory
            DESCRIPTION
                "Time slot type."
            ::= { currentMapEntry 4 }

        currentMapToSlot  OBJECT-TYPE
            SYNTAX  INTEGER   {
                    slot-11(11),
                    slot-12(12),
                    slot-13(13),
                    slot-14(14),
                    slot-15(15),
                    slot-16(16),
                    slot-17(17),
                    slot-18(18),
                    slot-19(19),
                    slot-20(20),
                    slot-inband(21),
                    slot-virtualTE1(23),
                    idle(255)
                }
            ACCESS  read-only
            STATUS  mandatory
            DESCRIPTION
                "Map to other port number."
            ::= { currentMapEntry 5 }

        currentMapToPort  OBJECT-TYPE
            SYNTAX  PortID
            ACCESS  read-only
            STATUS  mandatory
            DESCRIPTION
                "Map to other port number."
            ::= { currentMapEntry 6 }

        currentMapToTS  OBJECT-TYPE
            SYNTAX  INTEGER  {
                    ts00(0),
                    ts01(1),
                    ts02(2),
                    ts03(3),
                    ts04(4),
                    ts05(5),
                    ts06(6),
                    ts07(7),
                    ts08(8),
                    ts09(9),
                    ts10(10),
                    ts11(11),
                    ts12(12),
                    ts13(13),
                    ts14(14),
                    ts15(15),
                    ts16(16),
                    ts17(17),
                    ts18(18),
                    ts19(19),
                    ts20(20),
                    ts21(21),
                    ts22(22),
                    ts23(23),
                    ts24(24),
                    ts25(25),
                    ts26(26),
                    ts27(27),
                    ts28(28),
                    ts29(29),
                    ts30(30),
                    ts31(31),
                    ts32(32),
                    idle(33)
                }
            ACCESS  read-only
            STATUS  mandatory
            DESCRIPTION
                "Map to other port time slot."
            ::= { currentMapEntry 7 }

--
--  Channel Map
--
        channelMapTable  OBJECT-TYPE
            SYNTAX  SEQUENCE OF ChannelMapEntry
            ACCESS  not-accessible
            STATUS  mandatory
            DESCRIPTION
                "Channel Mapping for TSI."
            ::= { channelMap 12 }

        channelMapEntry  OBJECT-TYPE
            SYNTAX  ChannelMapEntry
            ACCESS  not-accessible
            STATUS  mandatory
            DESCRIPTION
                "Channel Mapping for TSI."
            INDEX { ccTsiMapIndex ,
                    ccChannelMapIndex ,
                    ccPortIndex ,
                    ccTimeSlotIndex }
            ::= { channelMapTable 1 }

        ChannelMapEntry ::= SEQUENCE  {
            ccTsiMapIndex               INTEGER,
            ccChannelMapIndex           INTEGER,
            ccPortIndex                 PortID,
            ccTimeSlotIndex             INTEGER,
            ccChannelType               INTEGER,
            ccMapToSlot                 INTEGER,
            ccMapToPort                 PortID,
            ccMapToTS                   INTEGER
        }

        ccTsiMapIndex  OBJECT-TYPE
            SYNTAX  INTEGER {
                    tsimap1(1),
                    tsimap2(2)
                }
            ACCESS  read-only
            STATUS  mandatory
            DESCRIPTION
                "TSI Map index."
            ::= { channelMapEntry 1 }

        ccChannelMapIndex  OBJECT-TYPE
            SYNTAX  INTEGER   {
                    slot-11(11),
                    slot-12(12),
                    slot-13(13),
                    slot-14(14),
                    slot-15(15),
                    slot-16(16),
                    slot-17(17),
                    slot-18(18),
                    slot-19(19),
                    slot-20(20),
                    slot-inband(21),
                    slot-virtualTE1(23)
                }
            ACCESS  read-only
            STATUS  mandatory
            DESCRIPTION
                "Select Slot"
            ::= { channelMapEntry 2 }

        ccPortIndex  OBJECT-TYPE
            SYNTAX  PortID
            ACCESS  read-only
            STATUS  mandatory
            DESCRIPTION
                "Select port"
            ::= { channelMapEntry 3 }

        ccTimeSlotIndex  OBJECT-TYPE
            SYNTAX  INTEGER (1..32)
            ACCESS  read-only
            STATUS  mandatory
            DESCRIPTION
                "Time slot index."
            ::= { channelMapEntry 4 }

        ccChannelType  OBJECT-TYPE
            SYNTAX  INTEGER   {
                    data(1),
                    voice(2),
                    signal(3),
                    frame(4),
                    idle(5)
                }
            ACCESS  read-only
            STATUS  mandatory
            DESCRIPTION
                "Time slot type."
            ::= { channelMapEntry 5 }

        ccMapToSlot  OBJECT-TYPE
            SYNTAX  INTEGER   {
                    slot-11(11),
                    slot-12(12),
                    slot-13(13),
                    slot-14(14),
                    slot-15(15),
                    slot-16(16),
                    slot-17(17),
                    slot-18(18),
                    slot-19(19),
                    slot-20(20),
                    slot-inband(21),
                    slot-virtualTE1(23),
                    idle(255)
                }
            ACCESS  read-only
            STATUS  mandatory
            DESCRIPTION
                "Map to other port number."
            ::= { channelMapEntry 6 }

        ccMapToPort  OBJECT-TYPE
            SYNTAX  PortID
            ACCESS  read-only
            STATUS  mandatory
            DESCRIPTION
                "Map to other port number."
            ::= { channelMapEntry 7 }

        ccMapToTS  OBJECT-TYPE
            SYNTAX  INTEGER   {
                    ts00(0),
                    ts01(1),
                    ts02(2),
                    ts03(3),
                    ts04(4),
                    ts05(5),
                    ts06(6),
                    ts07(7),
                    ts08(8),
                    ts09(9),
                    ts10(10),
                    ts11(11),
                    ts12(12),
                    ts13(13),
                    ts14(14),
                    ts15(15),
                    ts16(16),
                    ts17(17),
                    ts18(18),
                    ts19(19),
                    ts20(20),
                    ts21(21),
                    ts22(22),
                    ts23(23),
                    ts24(24),
                    ts25(25),
                    ts26(26),
                    ts27(27),
                    ts28(28),
                    ts29(29),
                    ts30(30),
                    ts31(31),
                    ts32(32),
                    none(254),
                    idle(255)
                }
            ACCESS  read-only
            STATUS  mandatory
            DESCRIPTION
                "Map to other port time slot."
            ::= { channelMapEntry 8 }

--
--  Set Channel Map
--
    setMapTable        OBJECT IDENTIFIER ::= { channelMap 13 }

        setTsiMap  OBJECT-TYPE
            SYNTAX  INTEGER {
                    tsimap1(1),
                    tsimap2(2)
                }
            ACCESS  read-write
            STATUS  mandatory
            DESCRIPTION
                "select TSI Map index."
            ::= { setMapTable 1 }

        setTargetSlot  OBJECT-TYPE
            SYNTAX  LSmapSlot
            ACCESS  read-write
            STATUS  mandatory
            DESCRIPTION
                "Select Slot"
            ::= { setMapTable 2 }

        setTargetPort  OBJECT-TYPE
            SYNTAX  TsiPortID
            ACCESS  read-write
            STATUS  mandatory
            DESCRIPTION
                "Select Port"
            ::= { setMapTable 3 }

        setTargetStartTimeSlot  OBJECT-TYPE
            SYNTAX  INTEGER  (0..32)
            ACCESS  read-write
            STATUS  mandatory
            DESCRIPTION
                "Select Target start time slot index."
            ::= { setMapTable 4 }

        setChannelNumber  OBJECT-TYPE
            SYNTAX  INTEGER  (1..32)
            ACCESS  read-write
            STATUS  mandatory
            DESCRIPTION
                "Select map channel number."
            ::= { setMapTable 5 }

        setChannelType  OBJECT-TYPE
            SYNTAX  INTEGER   {
                    data(1),
                    voice(2)
                }
            ACCESS  read-write
            STATUS  mandatory
            DESCRIPTION
                "Select time slot type."
            ::= { setMapTable 6 }

        setSourceSlot  OBJECT-TYPE
            SYNTAX  LSmapSlot
            ACCESS  read-write
            STATUS  mandatory
            DESCRIPTION
                "Map to Source slot number."
            ::= { setMapTable 7 }

        setSourcePort  OBJECT-TYPE
            SYNTAX  TsiPortID
            ACCESS  read-write
            STATUS  mandatory
            DESCRIPTION
                "Map to Source port number."
            ::= { setMapTable 8 }

        setSourceStartTimeSlot  OBJECT-TYPE
            SYNTAX  INTEGER  (0..32)
            ACCESS  read-write
            STATUS  mandatory
            DESCRIPTION
                "Map to Source port time slot."
            ::= { setMapTable 9 }

        setCommand  OBJECT-TYPE
            SYNTAX  INTEGER   {
                    clearTarget(1),
                    clearAllAndSet(2),
                    setOnly(3),
                    forceSet(4),
                    clearStatus(5)
                }
            ACCESS  read-write
            STATUS  mandatory
            DESCRIPTION
                "Set command:
                1: clear Target port, start from time slot x;
                2: clear (all mapped channel) before set;
                3: set olny, if channel not cleared, response error.
                4: force clear target and source, then set."
            ::= { setMapTable 10 }

        setResult  OBJECT-TYPE
            SYNTAX  INTEGER   {
                    na(1),
                    ok(2),
                    err-08(8),
                    err-09(9),
                    err-10(10),
                    err-11(11),
                    err-12(12),
                    err-13(13),
                    err-14(14),
                    err-15(15),
                    err-16(16),
                    err-17(17),
                    err-18(18),
                    err-19(19),
                    err-20(20),
                    err-21(21),
                    err-22(22),
                    err-23(23),
                    err-24(24),
                    err-25(25),
                    err-26(26),
                    err-27(27),
                    err-28(28),
                    err-29(29),
                    err-30(30),
                    err-31(31),
                    err-32(32)
                }
            ACCESS  read-only
            STATUS  mandatory
            DESCRIPTION
                "Set result:
                8  Somebody is in programming!
                9  No channel is assigned to DTE port!
                10  Incorrect total selected channels!
                11  Time slot is not IDLE!
                12  Time slot (TARGET slot/port) is out of range!
                13  Time slot (SOURCE slot/port) is out of range!
                14  TARGET slot/port is in CAS mode, Time slot 16 is for signaling!
                15  SOURCE slot/port is in CAS mode, Time slot 16 is for signaling!
                16  Time slot (TARGET slot/port) conflict!
                17  Time slot (TARGET slot/port) is out of range!
                18  Time slot (SOURCE. slot/port) is out of range!
                19  Port N must be equal Time slot N(TARGET slot)!
                20  Port N must be equal Time slot N(SOURCE slot)!
                21  Only 1 time slot can be mapped to IN-BAND!
                22  DTE only can map to 1 port!
                24  SOURCE slot/port is unframed mode, TARGET slot/port must have full time slot!
                25  TARGET slot/port is unframed mode, SOURCE slot/port must have full time slot!
                26  TARGET TS should be same as TARGET port number!
                27  SOURCE TS should be same as SOURCE port number!
                28  TARGET port not exist!
                29  SOURCE port not exist!
                30  Unframed E1 must map from TS0 and have 32 TS!
                31  Unframed T1 must map from TS1 and have 25 TS!
                32  Map can not set on 1+1 protection slave side!
                ..  "
            ::= { setMapTable 11 }


--
--  PDH Ring Protection
--

    pdhRingProtection        OBJECT IDENTIFIER ::= { system 103 }

        pdhRingControl  OBJECT-TYPE
            SYNTAX  INTEGER {
                    disable(1),
                    enable(2),
                    deactivated(3)
                }
            ACCESS  read-write
            STATUS  mandatory
            DESCRIPTION
                "Enable or Disable PDH Ring Protection Function"
            ::= { pdhRingProtection 1 }

        pdhRingSwitchingInterval  OBJECT-TYPE
            SYNTAX  INTEGER (5..99)
            ACCESS  read-write
            STATUS  mandatory
            DESCRIPTION
                "PDH Ring Protection Switching Interval (Seconds)"
            ::= { pdhRingProtection 2 }

        pdhRingStation  OBJECT-TYPE
            SYNTAX  INTEGER {
                    slave(1),
                    master(2)
                }
            ACCESS  read-write
            STATUS  mandatory
            DESCRIPTION
                "Station type in the Ring"
            ::= { pdhRingProtection 3 }


--
--  PDH Ring Port Setup Table
--
        pdhRingPortSetupTable  OBJECT-TYPE
            SYNTAX  SEQUENCE OF PDHRingPortSetupEntry
            ACCESS  not-accessible
            STATUS  mandatory
            DESCRIPTION
                "PDH Ring Port Setup Table"
            ::= { pdhRingProtection 5 }

        pdhRingPortSetupEntry  OBJECT-TYPE
            SYNTAX  PDHRingPortSetupEntry
            ACCESS  not-accessible
            STATUS  mandatory
            DESCRIPTION
                "PDH Ring Port Setup Entry"
            INDEX { pdhRingSlotIndex , pdhRingPortIndex }
            ::= { pdhRingPortSetupTable 1 }

        PDHRingPortSetupEntry ::= SEQUENCE {
            pdhRingSlotIndex            UnitID,
            pdhRingPortIndex            PortID,
            pdhRingModelType            CardModel,
            pdhRingPortProtection       INTEGER,
            pdhRingPortStatus           INTEGER,
            pdhRingPortDiagnostic       INTEGER
        }

        pdhRingSlotIndex  OBJECT-TYPE
            SYNTAX  UnitID
            ACCESS  read-only
            STATUS  mandatory
            DESCRIPTION
                "PDH Ring Setup: Slot Index"
            ::= { pdhRingPortSetupEntry 1 }

        pdhRingPortIndex  OBJECT-TYPE
            SYNTAX  PortID
            ACCESS  read-only
            STATUS  mandatory
            DESCRIPTION
                "PDH Ring Setup: Port Index"
            ::= { pdhRingPortSetupEntry 2 }

        pdhRingModelType  OBJECT-TYPE
            SYNTAX  CardModel
            ACCESS  read-only
            STATUS  mandatory
            DESCRIPTION
                "PDH Ring Setup: Model Type"
            ::= { pdhRingPortSetupEntry 3 }

        pdhRingPortProtection  OBJECT-TYPE
            SYNTAX  INTEGER {
                    disable(1),
                    enable(2),
                    xxxxxx(3)
                }
            ACCESS  read-write
            STATUS  mandatory
            DESCRIPTION
                "PDH Ring Setup: Enable/Disable"
            ::= { pdhRingPortSetupEntry 4 }

        pdhRingPortStatus  OBJECT-TYPE
            SYNTAX  INTEGER {
                    disable(1),
                    normal(2),
                    in-protect(3),
                    xxxxxx(4)
                }
            ACCESS  read-only
            STATUS  mandatory
            DESCRIPTION
                "PDH Ring Port Status"
            ::= { pdhRingPortSetupEntry 5 }

        pdhRingPortDiagnostic  OBJECT-TYPE
            SYNTAX  INTEGER {
                    normal(1),
                    diag1-send-ais(2),
                    diag2-test-mode(3),
                    na(4)
                }
            ACCESS  read-write
            STATUS  mandatory
            DESCRIPTION
                "PDH Ring Port Diagnostic"
            ::= { pdhRingPortSetupEntry 6 }


--
--  QE1/QT1/mQE1 1:1 Pair Protection
--

        qe1PairProtectionTable  OBJECT-TYPE
            SYNTAX  SEQUENCE OF Qe1PairProtectionEntry
            ACCESS  not-accessible
            STATUS  mandatory
            DESCRIPTION
                "QE1/QT1/mQE1 1:1 Pair Protection Table"
            ::= { system 104 }

        qe1PairProtectionEntry  OBJECT-TYPE
            SYNTAX  Qe1PairProtectionEntry
            ACCESS  not-accessible
            STATUS  mandatory
            DESCRIPTION
                "QE1/QT1/mQE1 1:1 Pair Protection Entry"
            INDEX { qe1PairSlotIndex , qe1PairPortIndex }
            ::= { qe1PairProtectionTable 1 }

        Qe1PairProtectionEntry ::= SEQUENCE {
            qe1PairSlotIndex            INTEGER,
            qe1PairPortIndex            INTEGER,
            qe1PairModelType            CardModel,
            qe1PairPortProtection       INTEGER,
            qe1PairPortStatus           INTEGER,
            qe1PairPortForceSwitch      INTEGER
        }

        qe1PairSlotIndex  OBJECT-TYPE
            SYNTAX  INTEGER {
                    slot-11-12(1),
                    slot-13-14(2),
                    slot-15-16(3)
                }
            ACCESS  read-only
            STATUS  mandatory
            DESCRIPTION
                "QE1 1:1 Pair Protection: Slot Index"
            ::= { qe1PairProtectionEntry 1 }

        qe1PairPortIndex  OBJECT-TYPE
            SYNTAX  INTEGER {
                    port-1(1),
                    port-2(2),
                    port-3(3),
                    port-4(4)
                }
            ACCESS  read-only
            STATUS  mandatory
            DESCRIPTION
                "QE1 1:1 Pair Protection: Port Index"
            ::= { qe1PairProtectionEntry 2 }

        qe1PairModelType  OBJECT-TYPE
            SYNTAX  CardModel
            ACCESS  read-only
            STATUS  mandatory
            DESCRIPTION
                "QE1 1:1 Pair Protection: Model Type"
            ::= { qe1PairProtectionEntry 3 }

        qe1PairPortProtection  OBJECT-TYPE
            SYNTAX  INTEGER {
                    disable(1),
                    circuit(2),
                    line-non-revertive(3),
                    line-revertive(4),
                    one-plus-one-non-revertive(5),
                    one-plus-one-revertive(6)
                }
            ACCESS  read-write
            STATUS  mandatory
            DESCRIPTION
                "QE1 circuit protection:
                1 = disable,
                2 = circuit (Y cable) protection,
                3 = non revertible line protection,
                4 = revertible line protection,
                5 = 1+1 non revertible line protection,
                6 = 1+1 revertible line protection"

            ::= { qe1PairProtectionEntry 4 }

        qe1PairPortStatus  OBJECT-TYPE
            SYNTAX  INTEGER {
                    disable(1),
                    normal(2),
                    in-protect(3),
                    xxxxxx(4)
                }
            ACCESS  read-only
            STATUS  mandatory
            DESCRIPTION
                "QE1 1:1 Pair Protection: Status"
            ::= { qe1PairProtectionEntry 5 }

        qe1PairPortForceSwitch  OBJECT-TYPE
            SYNTAX  INTEGER {
                    normal(0),
                    force-switch(1)
                }
            ACCESS  read-write
            STATUS  mandatory
            DESCRIPTION
                "QE1 1:1 Pair Protection: Force switch"
            ::= { qe1PairProtectionEntry 6 }


--
--  LED Status Table
--

    lsLedStatus           OBJECT IDENTIFIER ::= { system 105 }

--
-- LS Slot LED Status Table
--

        lsSlotLedTable  OBJECT-TYPE
            SYNTAX  SEQUENCE OF LSSlotLedEntry
            ACCESS  not-accessible
            STATUS  mandatory
            DESCRIPTION
                "LS Slot LED status table."
            ::= { lsLedStatus 1 }

        lsSlotLedEntry  OBJECT-TYPE
            SYNTAX  LSSlotLedEntry
            ACCESS  not-accessible
            STATUS  mandatory
            DESCRIPTION
                "Slot LED status entry"
            INDEX { lsSlotLedIndex ,
                    lsPortLedIndex }
            ::= { lsSlotLedTable 1 }

        LSSlotLedEntry ::= SEQUENCE {
            lsSlotLedIndex              LSSlotID,
            lsPortLedIndex              INTEGER,
            lsPortLedColor              INTEGER,
            lsPortLedName               INTEGER
        }

        lsSlotLedIndex  OBJECT-TYPE
            SYNTAX  LSSlotID
            ACCESS  read-only
            STATUS  mandatory
            DESCRIPTION
                "Slot Led Number Index"
            ::= { lsSlotLedEntry 1 }

        lsPortLedIndex  OBJECT-TYPE
            SYNTAX  INTEGER (1..20)
            ACCESS  read-only
            STATUS  mandatory
            DESCRIPTION
                "Port Led Number Index"
            ::= { lsSlotLedEntry 2 }

        lsPortLedColor  OBJECT-TYPE
            SYNTAX  INTEGER {
                    none(0),
                    off(1),
                    red(2),
                    green(3),
                    yellow(4),
                    redFlash(5),
                    greenFlash(6),
                    yellowFlash(7),
                    greenFlashRed(8),
                    green-and-yellow(9),
                    greenFlash-1-hz(10),
                    greenFlash-4-hz(11),
                    greenFlash-8-hz(12),
                    greenFlash-32-hz(13),
                    redFlash-1-hz(14),
                    redFlash-4-hz(15),
                    redFlash-8-hz(16),
                    redFlash-32-hz(17)
                }
            ACCESS  read-only
            STATUS  mandatory
            DESCRIPTION
                " Port Led Color"
            ::= { lsSlotLedEntry 3 }

-- 2012-08-24 modify lsPortLedName by Rukka
        lsPortLedName  OBJECT-TYPE
            SYNTAX  INTEGER {
                    port(0),
                    a-law(1),
                    u-law(2),
                    freq-12K-hz(3),
                    freq-16K-hz(4),
                    imp-600-ohm(5),
                    imp-900-ohm(6),
                    side-a(7),
                    side-b(8),
                    with-2-WIRE(9),
                    with-4-WIRE(10),
                    ring-across-l1-l2(11),
                    ring-across-l1-gnd(12),
                    type-1(13),
                    type-2(14),
                    type-3(15),
                    type-4(16),
                    type-5(17),
                    setByDip(18),
                    eth1-speed(19),
                    eth1-act(20),
                    eth2-speed(21),
                    eth2-act(22),
                    eth3-speed(23),
                    eth3-act(24),
                    eth4-speed(25),
                    eth4-act(26),
                    active(27),
                    type(28),
                    los(29),
                    sync(30),
                    --8UDTE
                    omnibus(31),
                    ts(32),
                    oversampling(33),
                    throughclock(34),
                    --TTA
                    ttaAlarm(50),
                    outputPort1(51),
                    outputPort2(52),
                    outputPort3(53),
                    outputPort4(54),
                    inputPort1(55),
                    inputPort2(56),
                    inputPort3(57),
                    inputPort4(58),
                    --CDA
                    controlling(60),
                    subordinate(61),

                    port1(101),
                    port2(102),
                    port3(103),
                    port4(104),
                    port5(105),
                    port6(106),
                    port7(107),
                    port8(108),
                    act1(121),
                    act2(122),
                    act3(123),
                    act4(124),
                    act5(125),
                    act6(126),
                    act7(127),
                    act8(128)
                }
            ACCESS  read-only
            STATUS  mandatory
            DESCRIPTION
                " Port Led Name"
            ::= { lsSlotLedEntry 4 }

--
-- LS Remote LED Status Table
--

        lsRemoteLedTable  OBJECT-TYPE
            SYNTAX  SEQUENCE OF LSRemoteLedEntry
            ACCESS  not-accessible
            STATUS  mandatory
            DESCRIPTION
                "Remote LED status table."
            ::= { lsLedStatus 2 }

        lsRemoteLedEntry  OBJECT-TYPE
            SYNTAX  LSRemoteLedEntry
            ACCESS  not-accessible
            STATUS  mandatory
            DESCRIPTION
                "Slot LED status entry"
            INDEX { lsRemoteSlotLedIndex ,
                    lsRemotePortLedIndex ,
                    lsRemoteNumLedIndex }
            ::= { lsRemoteLedTable 1 }

        LSRemoteLedEntry ::= SEQUENCE {
            lsRemoteSlotLedIndex        LSSlotID,
            lsRemotePortLedIndex        INTEGER,
            lsRemoteNumLedIndex         INTEGER,
            lsRemotePortLedColor        INTEGER,
            lsRemotePortLedName         DisplayString
        }

        lsRemoteSlotLedIndex  OBJECT-TYPE
            SYNTAX  LSSlotID
            ACCESS  read-only
            STATUS  mandatory
            DESCRIPTION
                "Remote Slot Led Number Index"
            ::= { lsRemoteLedEntry 1 }

        lsRemotePortLedIndex  OBJECT-TYPE
            SYNTAX  INTEGER (1..20)
            ACCESS  read-only
            STATUS  mandatory
            DESCRIPTION
                "Port Led Number Index"
            ::= { lsRemoteLedEntry 2 }

        lsRemoteNumLedIndex  OBJECT-TYPE
            SYNTAX  INTEGER {
                    led-1(1),
                    led-2(2),
                    led-3(3),
                    led-4(4),
                    led-5(5),
                    led-6(6),
                    led-7(7),
                    led-8(8),
                    led-9(9),
                    led-10(10)
                }
            ACCESS  read-only
            STATUS  mandatory
            DESCRIPTION
                "Port Led Number Index"
            ::= { lsRemoteLedEntry 3 }

        lsRemotePortLedColor  OBJECT-TYPE
            SYNTAX  INTEGER {
                    xx(0),
                    off(1),
                    red(2),
                    green(3),
                    yellow(4),
                    redFlash(5),
                    greenFlash(6),
                    yellowFlash(7),
                    greenFlashRed(8),
                    green-and-yellow(9),
                    greenFlash-1-hz(10),
                    greenFlash-4-hz(11),
                    greenFlash-8-hz(12),
                    greenFlash-32-hz(13),
                    redFlash-1-hz(14),
                    redFlash-4-hz(15),
                    redFlash-8-hz(16),
                    redFlash-32-hz(17)
                }
            ACCESS  read-only
            STATUS  mandatory
            DESCRIPTION
                " Remote Led Color"
            ::= { lsRemoteLedEntry 4 }

        lsRemotePortLedName  OBJECT-TYPE
            SYNTAX  DisplayString (SIZE (1..30))
            ACCESS  read-only
            STATUS  mandatory
            DESCRIPTION
                "Remote Led Name"
            ::= { lsRemoteLedEntry 5 }


--
--  Bit Error Rate Test Table
--

    lsBertTable        OBJECT IDENTIFIER ::= { system 106 }

        ctlBertSlot  OBJECT-TYPE
            SYNTAX  INTEGER   {
                    slot-11(11),
                    slot-12(12),
                    slot-13(13),
                    slot-14(14),
                    slot-15(15),
                    slot-16(16),
                    slot-17(17),
                    slot-18(18),
                    slot-19(19),
                    slot-20(20),
                    slot-virtualTE1(23)
                }
            ACCESS  read-write
            STATUS  mandatory
            DESCRIPTION
                "BERT slot"
            ::= { lsBertTable 1 }

        ctlBertPort  OBJECT-TYPE
            SYNTAX  PortID
            ACCESS  read-write
            STATUS  mandatory
            DESCRIPTION
                "BERT port"
            ::= { lsBertTable 2 }

        ctlBertPattern  OBJECT-TYPE
            SYNTAX  INTEGER {
--                        off(1),
                    prbs2exp20-1(2),
                    prbs2exp15-1(3),
                    prbs2exp11-1(4),
                    prbs2exp9-1(5),
                    user-define(6)
                }
            ACCESS  read-write
            STATUS  mandatory
            DESCRIPTION
                "BERT pattern"
            ::= { lsBertTable 3 }

        ctlSplitMode  OBJECT-TYPE
            SYNTAX  INTEGER {
                    sendAIS(1),
                    no(2)
                }
            ACCESS  read-write
            STATUS  mandatory
            DESCRIPTION
                "BERT split mode"
            ::= { lsBertTable 4 }

        ctlBertChannel  OBJECT-TYPE
            SYNTAX  INTEGER {
                    mapped(1),
                    full(2),
                    select(3)
                }
            ACCESS  read-write
            STATUS  mandatory
            DESCRIPTION
                "BERT channel"
            ::= { lsBertTable 5 }

        ctlBertMap  OBJECT-TYPE
            SYNTAX  DisplayString (SIZE (32))
            ACCESS  read-write
            STATUS  mandatory
            DESCRIPTION
                "BERT map 32 chars, i=idle, 1=map. Ex:
                i1111iiiiiiiiiiiiiiiiiiiiiiiiiii => send BERT in TS1~4"
            ::= { lsBertTable 6 }

        ctlUserPattern  OBJECT-TYPE
            SYNTAX  INTEGER
            ACCESS  read-write
            STATUS  mandatory
            DESCRIPTION
                "BERT user pattern"
            ::= { lsBertTable 7 }

        ctlBertPeriod  OBJECT-TYPE
            SYNTAX  INTEGER
            ACCESS  read-write
            STATUS  mandatory
            DESCRIPTION
                "Period(in seconds) of BERT"
            ::= { lsBertTable 8 }

        ctlBertAction  OBJECT-TYPE
            SYNTAX  INTEGER {
                    stop(1),
                    start(2),
                    reset(3),
                    insert-error(4)
                }
            ACCESS  read-write
            STATUS  mandatory
            DESCRIPTION
                "BERT action"
            ::= { lsBertTable 9 }

        ctlChannelInBert  OBJECT-TYPE
            SYNTAX  DisplayString (SIZE (0..255) )
            ACCESS  read-only
            STATUS  mandatory
            DESCRIPTION
                "Channel in BERT"
            ::= { lsBertTable 10 }

        ctlBertStatus  OBJECT-TYPE
            SYNTAX  INTEGER {
                    unsync(1),
                    sync(2)
                }
            ACCESS  read-only
            STATUS  mandatory
            DESCRIPTION
                "BERT status"
            ::= { lsBertTable 11 }

        ctlBertElapsedTime  OBJECT-TYPE
            SYNTAX  INTEGER
            ACCESS  read-only
            STATUS  mandatory
            DESCRIPTION
                "BERT Elapsed Time (s)"
            ::= { lsBertTable 12 }

        ctlBertBitError  OBJECT-TYPE
            SYNTAX  INTEGER
            ACCESS  read-only
            STATUS  mandatory
            DESCRIPTION
                "BERT Bit Error"
            ::= { lsBertTable 13 }

        ctlBertErrorSecond  OBJECT-TYPE
            SYNTAX  INTEGER
            ACCESS  read-only
            STATUS  mandatory
            DESCRIPTION
                "BERT Error Seconds"
            ::= { lsBertTable 14 }

        ctlBertSeveralErrorSecond  OBJECT-TYPE
            SYNTAX  INTEGER
            ACCESS  read-only
            STATUS  mandatory
            DESCRIPTION
                "BERT SES"
            ::= { lsBertTable 15 }

--
--  DS0-SNCP Protection //Eddie 20130123
--
    ds0sncpProtection       OBJECT IDENTIFIER ::= { system 107 }

        ds0sncpEnable  OBJECT-TYPE
            SYNTAX  INTEGER {
                    disable(1),
                    enable(2),
                    clear-performance(11)
                }
            ACCESS  read-write
            STATUS  mandatory
            DESCRIPTION
                "DS0-SNCP Enable/Disable."
            ::= { ds0sncpProtection 1 }

        ds0sncpMap  OBJECT-TYPE
            SYNTAX  INTEGER {
                    tsimap1(1),
                    tsimap2(2)
                }
            ACCESS  read-write
            STATUS  mandatory
            DESCRIPTION
                "DS0-SNCP Using TSI Map."
            ::= { ds0sncpProtection 2 }

        ds0sncpActionResponse  OBJECT-TYPE
            SYNTAX  DisplayString (SIZE (0..255) )
            ACCESS  read-only
            STATUS  mandatory
            DESCRIPTION
                "DS0-SNCP action response."
            ::= { ds0sncpProtection 3 }



--
--  DS0-SNCP Creation
--

    ds0sncpCreationTable    OBJECT IDENTIFIER ::= { ds0sncpProtection 4 }

        dsProtectedSlot  OBJECT-TYPE
            SYNTAX  LSmapSlot
            ACCESS  read-write
            STATUS  mandatory
            DESCRIPTION
                "Select Protected Slot 11~12."
            ::= { ds0sncpCreationTable 1 }

        dsProtectedPort  OBJECT-TYPE
            SYNTAX  TsiPortID
            ACCESS  read-write
            STATUS  mandatory
            DESCRIPTION
                "Select Protected Port 11~12."
            ::= { ds0sncpCreationTable 2 }

        dsProtectedStartTS  OBJECT-TYPE
            SYNTAX  INTEGER  (1..32)
            ACCESS  read-write
            STATUS  mandatory
            DESCRIPTION
                "Select Protected start time slot index."
            ::= { ds0sncpCreationTable 3 }

        dsChannelNumber  OBJECT-TYPE
            SYNTAX  INTEGER  (1..32)
            ACCESS  read-write
            STATUS  mandatory
            DESCRIPTION
                "Select Total channel number."
            ::= { ds0sncpCreationTable 4 }

        dsPrimarySlot  OBJECT-TYPE
            SYNTAX  LSSlotID
            ACCESS  read-write
            STATUS  mandatory
            DESCRIPTION
                "Primary 3E1 slot number."
            ::= { ds0sncpCreationTable 5 }

        dsPrimaryPort  OBJECT-TYPE
            SYNTAX  ThreePortID
            ACCESS  read-write
            STATUS  mandatory
            DESCRIPTION
                "Primary 3E1 port number."
            ::= { ds0sncpCreationTable 6 }

        dsPrimaryStartTS  OBJECT-TYPE
            SYNTAX  INTEGER  (1..32)
            ACCESS  read-write
            STATUS  mandatory
            DESCRIPTION
                "Primary 3E1 start time slot."
            ::= { ds0sncpCreationTable 9 }

        dsSecondarySlot  OBJECT-TYPE
            SYNTAX  LSSlotID
            ACCESS  read-write
            STATUS  mandatory
            DESCRIPTION
                "Secondary 3E1 slot number."
            ::= { ds0sncpCreationTable 11 }

        dsSecondaryPort  OBJECT-TYPE
            SYNTAX  ThreePortID
            ACCESS  read-write
            STATUS  mandatory
            DESCRIPTION
                "Secondary 3E1 port number."
            ::= { ds0sncpCreationTable 12 }

        dsSecondaryStartTS  OBJECT-TYPE
            SYNTAX  INTEGER  (1..32)
            ACCESS  read-write
            STATUS  mandatory
            DESCRIPTION
                "Secondary 3E1 start time slot."
            ::= { ds0sncpCreationTable 15 }

        dsSwitchMode  OBJECT-TYPE
            SYNTAX  INTEGER   {
                    non-revertible(1),
                    revertible(2)
                }
            ACCESS  read-write
            STATUS  mandatory
            DESCRIPTION
                "Switch mode"
            ::= { ds0sncpCreationTable 16 }

        dsSetCommand  OBJECT-TYPE
            SYNTAX  INTEGER   {
                    check-set(1),
                    force-set(2),
                    force-switch(3),
                    delete-1(4),
                    delete-all(5),
                    lock-working(11),
                    lock-primary(12),
                    lock-secondary(13),
                    unlock(14),
                    change-switch-mode(21)
                }
            ACCESS  read-write
            STATUS  mandatory
            DESCRIPTION
                "Set command:
                1: check and set DS0-SNCP;
                2: force set DS0-SNCP;
                3: force switch a DS0-SNCP;
                4: delete a DS0-SNCP;
                5: delete all;
                11: lock on working;
                12: lock on primary;
                13: lock on secondary;
                14: unlock"
            ::= { ds0sncpCreationTable 17 }

        dsDataVoice  OBJECT-TYPE
            SYNTAX  INTEGER   {
                    data(1),
                    voice(2)
                }
            ACCESS  read-write
            STATUS  mandatory
            DESCRIPTION
                "Data or Voice"
            ::= { ds0sncpCreationTable 18 }

        dsCircuitGroup  OBJECT-TYPE
            SYNTAX  INTEGER  (0..32)
            ACCESS  read-write
            STATUS  mandatory
            DESCRIPTION
                "group number for protected port, 0 means individual."
            ::= { ds0sncpCreationTable 19 }


--
--  DS0-SNCP Information
--

        ds0sncpInfoTable  OBJECT-TYPE
            SYNTAX  SEQUENCE OF Ds0sncpInfoEntry
            ACCESS  not-accessible
            STATUS  mandatory
            DESCRIPTION
                "DS0-SNCP Protection Information Table"
            ::= { ds0sncpProtection 5 }

        ds0sncpInfoEntry  OBJECT-TYPE
            SYNTAX  Ds0sncpInfoEntry
            ACCESS  not-accessible
            STATUS  mandatory
            DESCRIPTION
                "DS0-SNCP Protection Information Entry"
            INDEX { ds0sncpInfoIndex }
            ::= { ds0sncpInfoTable 1 }

        Ds0sncpInfoEntry ::= SEQUENCE {
            ds0sncpInfoIndex            INTEGER,
            dsiProtectedSlot            LSmapSlot,
            dsiProtectedPort            TsiPortID,
            dsiProtectedTS              INTEGER,
            dsiPrimarySlot              LSSlotID,
            dsiPrimaryPort              ThreePortID,
            dsiPrimaryTS                INTEGER,
            dsiSecondarySlot            LSSlotID,
            dsiSecondaryPort            ThreePortID,
            dsiSecondaryTS              INTEGER,
            dsiSwitchMode               INTEGER,
            dsiDataVoice                INTEGER,
            dsiWorkingOn                INTEGER,
            dsiForceSwitch              INTEGER,
            dsiDeleteProtection         INTEGER
        }

        ds0sncpInfoIndex  OBJECT-TYPE
            SYNTAX  INTEGER  (1..512)
            ACCESS  read-only
            STATUS  mandatory
            DESCRIPTION
                "DS0-SNCP Information Index."
            ::= { ds0sncpInfoEntry 1 }

        dsiProtectedSlot  OBJECT-TYPE
            SYNTAX  LSmapSlot
            ACCESS  read-only
            STATUS  mandatory
            DESCRIPTION
                "Protected Slot A~D, 1~12."
            ::= { ds0sncpInfoEntry 2 }

        dsiProtectedPort  OBJECT-TYPE
            SYNTAX  TsiPortID
            ACCESS  read-only
            STATUS  mandatory
            DESCRIPTION
                "Protected Port 1~12."
            ::= { ds0sncpInfoEntry 3 }

        dsiProtectedTS  OBJECT-TYPE
            SYNTAX  INTEGER  (0..32)
            ACCESS  read-only
            STATUS  mandatory
            DESCRIPTION
                "Protected time slot."
            ::= { ds0sncpInfoEntry 4 }

        dsiPrimarySlot  OBJECT-TYPE
            SYNTAX  LSSlotID
            ACCESS  read-only
            STATUS  mandatory
            DESCRIPTION
                "Primary 3E1 slot number."
            ::= { ds0sncpInfoEntry 5 }

        dsiPrimaryPort  OBJECT-TYPE
            SYNTAX  ThreePortID
            ACCESS  read-only
            STATUS  mandatory
            DESCRIPTION
                "Primary 3E1 port number."
            ::= { ds0sncpInfoEntry 6 }

        dsiPrimaryTS  OBJECT-TYPE
            SYNTAX  INTEGER  (0..32)
            ACCESS  read-only
            STATUS  mandatory
            DESCRIPTION
                "Primary 3E1 time slot."
            ::= { ds0sncpInfoEntry 7 }

        dsiSecondarySlot  OBJECT-TYPE
            SYNTAX  LSSlotID
            ACCESS  read-only
            STATUS  mandatory
            DESCRIPTION
                "Secondary 3E1 slot number."
            ::= { ds0sncpInfoEntry 8 }

        dsiSecondaryPort  OBJECT-TYPE
            SYNTAX  ThreePortID
            ACCESS  read-only
            STATUS  mandatory
            DESCRIPTION
                "Secondary 3E1 port number."
            ::= { ds0sncpInfoEntry 9 }

        dsiSecondaryTS  OBJECT-TYPE
            SYNTAX  INTEGER  (0..32)
            ACCESS  read-only
            STATUS  mandatory
            DESCRIPTION
                "Secondary 3E1 start time slot."
            ::= { ds0sncpInfoEntry 10 }

        dsiSwitchMode  OBJECT-TYPE
            SYNTAX  INTEGER   {
                    non-revertible(1),
                    revertible(2)
                }
            ACCESS  read-only
            STATUS  mandatory
            DESCRIPTION
                "Switch mode"
            ::= { ds0sncpInfoEntry 11 }

        dsiWorkingOn  OBJECT-TYPE
            SYNTAX  INTEGER   {
                    primary(1),
                    secondary(2)
                }
            ACCESS  read-only
            STATUS  mandatory
            DESCRIPTION
                "Working on primary or secondary."
            ::= { ds0sncpInfoEntry 12 }

        dsiForceSwitch  OBJECT-TYPE
            SYNTAX  INTEGER   {
                    no(1),
                    force-switch(2)
                }
            ACCESS  read-write
            STATUS  mandatory
            DESCRIPTION
                "Force switch to standby TS."
            ::= { ds0sncpInfoEntry 13 }

        dsiDeleteProtection  OBJECT-TYPE
            SYNTAX  INTEGER   {
                    no(1),
                    delete(2)
                }
            ACCESS  read-write
            STATUS  mandatory
            DESCRIPTION
                "Delete protection."
            ::= { ds0sncpInfoEntry 14 }

        dsiDataVoice  OBJECT-TYPE
            SYNTAX  INTEGER   {
                    data(1),
                    voice(2)
                }
            ACCESS  read-only
            STATUS  mandatory
            DESCRIPTION
                "Data or Voice"
            ::= { ds0sncpInfoEntry 15 }


--
--  DS0-SNCP Performance Table
--

        ds0sncpPerfTable  OBJECT-TYPE
            SYNTAX  SEQUENCE OF Ds0sncpPerfEntry
            ACCESS  not-accessible
            STATUS  mandatory
            DESCRIPTION
                "DS0-SNCP Performance Table"
            ::= { ds0sncpProtection 6 }

        ds0sncpPerfEntry  OBJECT-TYPE
            SYNTAX  Ds0sncpPerfEntry
            ACCESS  not-accessible
            STATUS  mandatory
            DESCRIPTION
                "DS0-SNCP Performance Entry"
            INDEX { ds0sncpPerfIndex }
            ::= { ds0sncpPerfTable 1 }

        Ds0sncpPerfEntry ::= SEQUENCE {
            ds0sncpPerfIndex            INTEGER,
            dspProtectedSlot            LSmapSlot,
            dspProtectedPort            TsiPortID,
            dspProtectedTS              INTEGER,
            dspCurrentDaySeconds        INTEGER,
            dspCurrentDayAS             INTEGER,
            dspCurrentDayUAS            INTEGER,
            dspValidDayInterval         INTEGER
        }

        ds0sncpPerfIndex  OBJECT-TYPE
            SYNTAX  INTEGER  (1..512)
            ACCESS  read-only
            STATUS  mandatory
            DESCRIPTION
                "DS0-SNCP Performance Index."
            ::= { ds0sncpPerfEntry 1 }

        dspProtectedSlot  OBJECT-TYPE
            SYNTAX  LSmapSlot
            ACCESS  read-only
            STATUS  mandatory
            DESCRIPTION
                "Protected Slot 11~12."
            ::= { ds0sncpPerfEntry 2 }

        dspProtectedPort  OBJECT-TYPE
            SYNTAX  TsiPortID
            ACCESS  read-only
            STATUS  mandatory
            DESCRIPTION
                "Protected Port 11~12."
            ::= { ds0sncpPerfEntry 3 }

        dspProtectedTS  OBJECT-TYPE
            SYNTAX  INTEGER  (0..32)
            ACCESS  read-only
            STATUS  mandatory
            DESCRIPTION
                "Protected time slot."
            ::= { ds0sncpPerfEntry 4 }

        dspCurrentDaySeconds  OBJECT-TYPE
            SYNTAX  INTEGER
            ACCESS  read-only
            STATUS  mandatory
            DESCRIPTION
                "Current day elapsed seconds"
            ::= { ds0sncpPerfEntry 5 }

        dspCurrentDayAS  OBJECT-TYPE
            SYNTAX  INTEGER
            ACCESS  read-only
            STATUS  mandatory
            DESCRIPTION
                "Current day available seconds"
            ::= { ds0sncpPerfEntry 6 }

        dspCurrentDayUAS  OBJECT-TYPE
            SYNTAX  INTEGER
            ACCESS  read-only
            STATUS  mandatory
            DESCRIPTION
                "Current day unavailable seconds"
            ::= { ds0sncpPerfEntry 7 }

        dspValidDayInterval  OBJECT-TYPE
            SYNTAX  INTEGER
            ACCESS  read-only
            STATUS  mandatory
            DESCRIPTION
                "Valid days Interval number"
            ::= { ds0sncpPerfEntry 8 }


--
-- DS0-SNCP 7 Days Performance Table
--

        ds0sncp7DaysPerfTable  OBJECT-TYPE
            SYNTAX  SEQUENCE OF Ds0sncp7DaysPerfEntry
            ACCESS  not-accessible
            STATUS  mandatory
            DESCRIPTION
                "DS0-SNCP 7 days performance table."
            ::= { ds0sncpProtection 7 }

        ds0sncp7DaysPerfEntry  OBJECT-TYPE
            SYNTAX  Ds0sncp7DaysPerfEntry
            ACCESS  not-accessible
            STATUS  mandatory
            DESCRIPTION
                "DS0-SNCP 7 days performance entry."
            INDEX { dsdPerfIndex , dsdDayIndex }
            ::= { ds0sncp7DaysPerfTable 1 }

        Ds0sncp7DaysPerfEntry ::= SEQUENCE {
            dsdPerfIndex                INTEGER,
            dsdDayIndex                 INTEGER,
            dsdDateStrIndex             DisplayString,
            dsdProtectedSlot            LSmapSlot,
            dsdProtectedPort            TsiPortID,
            dsdProtectedTS              INTEGER,
            dsdDayAS                    INTEGER,
            dsdDayUAS                   INTEGER
        }

        dsdPerfIndex  OBJECT-TYPE
            SYNTAX  INTEGER  (1..512)
            ACCESS  read-only
            STATUS  mandatory
            DESCRIPTION
                "DS0-SNCP Performance Index."
            ::= { ds0sncp7DaysPerfEntry 1 }

        dsdDayIndex  OBJECT-TYPE
            SYNTAX  INTEGER  (1..7)
            ACCESS  read-only
            STATUS  mandatory
            DESCRIPTION
                "DS0-SNCP Performance Day Index."
            ::= { ds0sncp7DaysPerfEntry 2 }

        dsdDateStrIndex  OBJECT-TYPE
            SYNTAX  DisplayString (SIZE (0..32) )
            ACCESS  read-only
            STATUS  mandatory
            DESCRIPTION
                "Seven Days String "
            ::= { ds0sncp7DaysPerfEntry 3 }

        dsdProtectedSlot  OBJECT-TYPE
            SYNTAX  LSmapSlot
            ACCESS  read-only
            STATUS  mandatory
            DESCRIPTION
                "Protected Slot A~D, 1~12."
            ::= { ds0sncp7DaysPerfEntry 4 }

        dsdProtectedPort  OBJECT-TYPE
            SYNTAX  TsiPortID
            ACCESS  read-only
            STATUS  mandatory
            DESCRIPTION
                "Protected Port 1~12."
            ::= { ds0sncp7DaysPerfEntry 5 }

        dsdProtectedTS  OBJECT-TYPE
            SYNTAX  INTEGER  (0..32)
            ACCESS  read-only
            STATUS  mandatory
            DESCRIPTION
                "Protected time slot."
            ::= { ds0sncp7DaysPerfEntry 6 }

        dsdDayAS  OBJECT-TYPE
            SYNTAX  INTEGER
            ACCESS  read-only
            STATUS  mandatory
            DESCRIPTION
                "Day available seconds"
            ::= { ds0sncp7DaysPerfEntry 7 }

        dsdDayUAS  OBJECT-TYPE
            SYNTAX  INTEGER
            ACCESS  read-only
            STATUS  mandatory
            DESCRIPTION
                "Day unavailable seconds"
            ::= { ds0sncp7DaysPerfEntry 8 }


--
--  New DS0-SNCP Information
--

        newDs0sncpInfoTable  OBJECT-TYPE
            SYNTAX  SEQUENCE OF NewDs0sncpInfoEntry
            ACCESS  not-accessible
            STATUS  mandatory
            DESCRIPTION
                "New DS0-SNCP Protection Information Table"
            ::= { ds0sncpProtection 8 }

        newDs0sncpInfoEntry  OBJECT-TYPE
            SYNTAX  NewDs0sncpInfoEntry
            ACCESS  not-accessible
            STATUS  mandatory
            DESCRIPTION
                "New DS0-SNCP Protection Information Entry"
            INDEX { ndsiProtectedSlot , ndsiProtectedPort , ndsiProtectedTS }
            ::= { newDs0sncpInfoTable 1 }

        NewDs0sncpInfoEntry ::= SEQUENCE {
            ndsiProtectedSlot            LSmapSlot,
            ndsiProtectedPort            TsiPortID,
            ndsiProtectedTS              INTEGER,
            ndsiPrimarySlot              LSSlotID,
            ndsiPrimaryPort              ThreePortID,
            ndsiPrimaryTS                INTEGER,
            ndsiSecondarySlot            LSSlotID,
            ndsiSecondaryPort            ThreePortID,
            ndsiSecondaryTS              INTEGER,
            ndsiSwitchMode               INTEGER,
            ndsiDataVoice                INTEGER,
            ndsiWorkingOn                INTEGER,
            ndsiDispIndex                INTEGER,
            ndsiCircuitGroup             INTEGER,
            ndsiPrimaryStatus            INTEGER,
            ndsiSecondaryStatus          INTEGER
        }

        ndsiProtectedSlot  OBJECT-TYPE
            SYNTAX  LSmapSlot
            ACCESS  read-only
            STATUS  mandatory
            DESCRIPTION
                "Protected Slot A~D, 1~12."
            ::= { newDs0sncpInfoEntry 1 }

        ndsiProtectedPort  OBJECT-TYPE
            SYNTAX  TsiPortID
            ACCESS  read-only
            STATUS  mandatory
            DESCRIPTION
                "Protected Port 1~12."
            ::= { newDs0sncpInfoEntry 2 }

        ndsiProtectedTS  OBJECT-TYPE
            SYNTAX  INTEGER  (0..32)
            ACCESS  read-only
            STATUS  mandatory
            DESCRIPTION
                "Protected time slot."
            ::= { newDs0sncpInfoEntry 3 }

        ndsiPrimarySlot  OBJECT-TYPE
            SYNTAX  LSSlotID
            ACCESS  read-only
            STATUS  mandatory
            DESCRIPTION
                "Primary 3E1 slot number."
            ::= { newDs0sncpInfoEntry 4 }

        ndsiPrimaryPort  OBJECT-TYPE
            SYNTAX  ThreePortID
            ACCESS  read-only
            STATUS  mandatory
            DESCRIPTION
                "Primary 3E1 port number."
            ::= { newDs0sncpInfoEntry 5 }

        ndsiPrimaryTS  OBJECT-TYPE
            SYNTAX  INTEGER  (0..32)
            ACCESS  read-only
            STATUS  mandatory
            DESCRIPTION
                "Primary 3E1 time slot."
            ::= { newDs0sncpInfoEntry 6 }

        ndsiSecondarySlot  OBJECT-TYPE
            SYNTAX  LSSlotID
            ACCESS  read-only
            STATUS  mandatory
            DESCRIPTION
                "Secondary 3E1 slot number."
            ::= { newDs0sncpInfoEntry 7 }

        ndsiSecondaryPort  OBJECT-TYPE
            SYNTAX  ThreePortID
            ACCESS  read-only
            STATUS  mandatory
            DESCRIPTION
                "Secondary 3E1 port number."
            ::= { newDs0sncpInfoEntry 8 }

        ndsiSecondaryTS  OBJECT-TYPE
            SYNTAX  INTEGER  (0..32)
            ACCESS  read-only
            STATUS  mandatory
            DESCRIPTION
                "Secondary 3E1 start time slot."
            ::= { newDs0sncpInfoEntry 9 }

        ndsiSwitchMode  OBJECT-TYPE
            SYNTAX  INTEGER   {
                    non-revertible(1),
                    revertible(2)
                }
            ACCESS  read-only
            STATUS  mandatory
            DESCRIPTION
                "Switch mode"
            ::= { newDs0sncpInfoEntry 10 }

        ndsiDataVoice  OBJECT-TYPE
            SYNTAX  INTEGER   {
                    data(1),
                    voice(2)
                }
            ACCESS  read-only
            STATUS  mandatory
            DESCRIPTION
                "Data or Voice"
            ::= { newDs0sncpInfoEntry 11 }

        ndsiWorkingOn  OBJECT-TYPE
            SYNTAX  INTEGER   {
                    primary(1),
                    secondary(2)
                }
            ACCESS  read-only
            STATUS  mandatory
            DESCRIPTION
                "Working on primary or secondary."
            ::= { newDs0sncpInfoEntry 12 }

        ndsiDispIndex  OBJECT-TYPE
            SYNTAX  INTEGER  (1..512)
            ACCESS  read-only
            STATUS  mandatory
            DESCRIPTION
                "DS0-SNCP Display Index."
            ::= { newDs0sncpInfoEntry 13 }

        ndsiCircuitGroup  OBJECT-TYPE
            SYNTAX  INTEGER  (0..32)
            ACCESS  read-only
            STATUS  mandatory
            DESCRIPTION
                "group number for protected port, 0 means individual."
            ::= { newDs0sncpInfoEntry 14 }

        ndsiPrimaryStatus  OBJECT-TYPE
            SYNTAX  INTEGER   {
                    fail(1),
                    ok(2)
                }
            ACCESS  read-only
            STATUS  mandatory
            DESCRIPTION
                "Primary TS status."
            ::= { newDs0sncpInfoEntry 15 }

        ndsiSecondaryStatus  OBJECT-TYPE
            SYNTAX  INTEGER   {
                    fail(1),
                    ok(2)
                }
            ACCESS  read-only
            STATUS  mandatory
            DESCRIPTION
                "Secondary TS status."
            ::= { newDs0sncpInfoEntry 16 }


--
--  Remote Device upgrade
--

    remDevUpgradeTable       OBJECT IDENTIFIER ::= { system 108 }

        remTftpServerIP  OBJECT-TYPE
            SYNTAX  IpAddress
            ACCESS  read-write
            STATUS  mandatory
            DESCRIPTION
                "IP address of tftp server"
            ::= { remDevUpgradeTable 1 }

        remTftpFileName  OBJECT-TYPE
            SYNTAX  DisplayString (SIZE (0..255) )
            ACCESS  read-write
            STATUS  mandatory
            DESCRIPTION
                "File name for download"
            ::= { remDevUpgradeTable 2 }

        remFileTransferType  OBJECT-TYPE
            SYNTAX  INTEGER {
                    clear-status(1),
                    download-GSHDSL-remote-device(11),
                    na(255)
                }
            ACCESS  read-write
            STATUS  mandatory
            DESCRIPTION
                "upgrade device"
            ::= { remDevUpgradeTable 3 }

        remUpgradeSlot  OBJECT-TYPE
            SYNTAX  INTEGER {
                    slot-11(11),
                    slot-12(12),
                    slot-13(13),
                    slot-14(14),
                    slot-15(15),
                    slot-16(16),
                    na(99)
                }
            ACCESS  read-write
            STATUS  mandatory
            DESCRIPTION
                "upgrade slot"
            ::= { remDevUpgradeTable 4 }

        remUpgradePort  OBJECT-TYPE
            SYNTAX  INTEGER {
                    port-1(1),
                    port-2(2),
                    port-3(3),
                    port-4(4),
                    na(254)
                }
            ACCESS  read-write
            STATUS  mandatory
            DESCRIPTION
                "upgrade port"
            ::= { remDevUpgradeTable 5 }

        remUpgradeCommand  OBJECT-TYPE
            SYNTAX  INTEGER {
                    none(1),
                    upgrade(2),
                    upgrade-and-reset(3)
                }
            ACCESS  read-write
            STATUS  mandatory
            DESCRIPTION
                "upgrade command"
            ::= { remDevUpgradeTable 6 }

        remUpgradePrograss  OBJECT-TYPE
            SYNTAX  INTEGER {
                    na(0),
                    ok(1),
                    checksum-error(2),
                    timeout(3),
                    unknown-tftp-error(4),
                    file-not-found(5),
                    file-already-exists(6),
                    fail-to-read-flash(7),
                    fail-to-program-flash(8),
                    unmatch-firmware(9),
                    unmatch-config(10),
                    activating-current-config(11),
                    copy-to-redundant-fail(12),
                    send-firmware-to-card-fail(13),
                    in-prepare-config-data(16),
                    in-transmit(17),
                    in-send-to-card(18),
                    in-write-flash(19),
                    none(20),
                    prepare-config-data-fail(21),
                    other(99),

                    in-send-to-remote(104),
                    completed(105),
                    card-model-error(111),
                    card-version-error(112),
                    port-unsync(113),
                    remote-device-error(114),
                    port-not-exist(115),
                    tftp-error(116),
                    fail-to-send-card(118),
                    check-fail(120),
                    check-ok(121),
                    rs485-loss(122),
                    card-checksum-error(123),
                    incorrect-file(124),
                    firmware-error(125),
                    unmatch-model(133),
                    other-in-send(135),
                    eoc-fail(136),
                    time-out(199),
                    unknown-problem(255)
                }
            ACCESS  read-only
            STATUS  mandatory
            DESCRIPTION
                "Transfer percentage"
            ::= { remDevUpgradeTable 7 }

        remUpgradePercentage  OBJECT-TYPE
            SYNTAX  INTEGER
            ACCESS  read-only
            STATUS  mandatory
            DESCRIPTION
                "upgrade percentage"
            ::= { remDevUpgradeTable 8 }

        remUpgradeMessage  OBJECT-TYPE
            SYNTAX  DisplayString (SIZE (0..255) )
            ACCESS  read-only
            STATUS  mandatory
            DESCRIPTION
                "Message of upgrade process"
            ::= { remDevUpgradeTable 9 }

        remTftpIPv6Server  OBJECT-TYPE
            SYNTAX  DisplayString (SIZE(2..40))
            ACCESS  read-write
            STATUS  mandatory
            DESCRIPTION
                "IP V6 mode address"
            ::= { remDevUpgradeTable 10 }


--======================================================================--
--======================================================================--
--  dteCard MIB
--======================================================================--
--======================================================================--


--
--      DTE Control Table
--

        dteConfigControlTable  OBJECT-TYPE
            SYNTAX  SEQUENCE OF DTEConfigControl
            ACCESS  not-accessible
            STATUS  mandatory
            DESCRIPTION
                "DTE Configuration Control Table"
            ::= { dte-card 1 }

        dteConfigCtrlEntry  OBJECT-TYPE
            SYNTAX  DTEConfigControl
            ACCESS  not-accessible
            STATUS  mandatory
            DESCRIPTION
                "DTE configuration control entry"
            INDEX {
                    dteCCSlotIndex ,
                    dteCCPortIndex
                }
            ::= { dteConfigControlTable 1 }

        DTEConfigControl ::= SEQUENCE {
            dteCCSlotIndex              LSSlotID,
            dteCCPortIndex              PortID,
            dteCCRate                   INTEGER,
            dteCCChannel                INTEGER,
            dteCCClock                  INTEGER,
            dteCCData                   INTEGER,
            dteCCInterface              INTEGER,
            dteCCRTS                    INTEGER,
            dteCCTTM                    INTEGER,
            dteCCV54                    INTEGER
        }

        dteCCSlotIndex  OBJECT-TYPE
            SYNTAX  LSSlotID
            ACCESS  read-only
            STATUS  mandatory
            DESCRIPTION
                "DTE slot"
            ::= { dteConfigCtrlEntry 1 }

        dteCCPortIndex  OBJECT-TYPE
            SYNTAX  PortID
            ACCESS  read-only
            STATUS  mandatory
            DESCRIPTION
                " Port 1 to 6, Total 6 ports"
            ::= { dteConfigCtrlEntry 2 }

        dteCCRate   OBJECT-TYPE
            SYNTAX  INTEGER {
                    rate64k(1),
                    rate56k(2)
                }
            ACCESS  read-write
            STATUS  mandatory
            DESCRIPTION
                " DTE Rate "
            ::= { dteConfigCtrlEntry 3 }

        dteCCChannel   OBJECT-TYPE
            SYNTAX  INTEGER
            ACCESS  read-only
            STATUS  mandatory
            DESCRIPTION
                " DTE Channel: channel numbers designed by MAP."
            ::= { dteConfigCtrlEntry 4 }

        dteCCClock   OBJECT-TYPE
            SYNTAX  INTEGER {
                    normal(1),
                    inverted(2)
                }
            ACCESS  read-write
            STATUS  mandatory
            DESCRIPTION
                " DTE Clock Polarity "
            ::= { dteConfigCtrlEntry 5 }

        dteCCData   OBJECT-TYPE
            SYNTAX  INTEGER {
                    normal(1),
                    inverted(2)
                }
            ACCESS  read-write
            STATUS  mandatory
            DESCRIPTION
                " DTE Data Polarity "
            ::= { dteConfigCtrlEntry 6 }

        dteCCInterface   OBJECT-TYPE
            SYNTAX  INTEGER {
                    eia530(1),
                    x21(2),
                    rs232(3),
                    v35(4),
                    v36(5),
                    rs422(6)
                }
            ACCESS  read-only
            STATUS  mandatory
            DESCRIPTION
                " DTE Interface Type "
            ::= { dteConfigCtrlEntry 7 }

        dteCCRTS   OBJECT-TYPE
            SYNTAX  INTEGER {
                    active(1),
                    permanent(2)
                }
            ACCESS  read-write
            STATUS  mandatory
            DESCRIPTION
                " DTE RTS Permanent "
            ::= { dteConfigCtrlEntry 8 }

        dteCCTTM   OBJECT-TYPE
            SYNTAX  INTEGER {
                    off(1),
                    on(2)
                }
            ACCESS  read-write
            STATUS  mandatory
            DESCRIPTION
                " DTE Terminal Timing Mode "
            ::= { dteConfigCtrlEntry 9 }

        dteCCV54   OBJECT-TYPE
            SYNTAX  INTEGER {
                    off(1),
                    on(2)
                }
            ACCESS  read-write
            STATUS  mandatory
            DESCRIPTION
                " DTE V54 control "
            ::= { dteConfigCtrlEntry 10 }


--
--  Alarm Queue Table
--

--         dteAlarmQueueTable  OBJECT-TYPE
--             SYNTAX  SEQUENCE OF DTEAlarmQueue
--             ACCESS  not-accessible
--             STATUS  mandatory
--             DESCRIPTION
--                "DTE Alarm Queue Table"
--             ::= { dte-card 2 }
--
--         dteAlarmQueueEntry  OBJECT-TYPE
--             SYNTAX  DTEAlarmQueue
--             ACCESS  not-accessible
--             STATUS  mandatory
--             DESCRIPTION
--                "DTE alarm queue entry"
--             INDEX  { dteAQSlotIndex,
--                      dteAQPortIndex,
--                      dteAlarmQIndex }
--             ::= { dteAlarmQueueTable 1 }
--
--         DTEAlarmQueue ::=
--             SEQUENCE {
--               dteAlarmQIndex
--                 INTEGER (1..40),
--               alarmQStr
--                 DisplayString (SIZE(0..255))
--             }
--
--         dteAlarmQIndex  OBJECT-TYPE
--             SYNTAX  INTEGER (1..40)
--             ACCESS  read-only
--             STATUS  mandatory
--             DESCRIPTION
--                "Select Alarm Queue Index(1-40)"
--             ::= { dteAlarmQueueEntry 2 }
--
--         alarmQStr  OBJECT-TYPE
--             SYNTAX  DisplayString (SIZE (0..255))
--             ACCESS  read-only
--             STATUS  mandatory
--             DESCRIPTION
--                "Alarm Queue String"
--             ::= { dteAlarmQueueEntry 3 }

--
--  Alarm History Table
--

        dteAlarmHistoryTable  OBJECT-TYPE
            SYNTAX  SEQUENCE OF DTEAlarmHistory
            ACCESS  not-accessible
            STATUS  mandatory
            DESCRIPTION
                "DTE Alarm History Table"
            ::= { dte-card 3 }

        dteAlarmHistoryEntry  OBJECT-TYPE
            SYNTAX  DTEAlarmHistory
            ACCESS  not-accessible
            STATUS  mandatory
            DESCRIPTION
                "DTE alarm history entry"
            INDEX { dteAHSlotIndex ,
                    dteAHPortIndex ,
                    dteAlarmHIndex }
            ::= { dteAlarmHistoryTable 1 }

        DTEAlarmHistory ::= SEQUENCE {
            dteAHSlotIndex              LSSlotID,
            dteAHPortIndex              PortID,
            dteAlarmHIndex              INTEGER,
            dteAHcurrentHState          INTEGER,
            dteAHcount                  INTEGER,
            dteAHalarm                  LsAlarmSeverity
        }

        dteAHSlotIndex  OBJECT-TYPE
            SYNTAX  LSSlotID
            ACCESS  read-only
            STATUS  mandatory
            DESCRIPTION
                "DTE slot"
            ::= { dteAlarmHistoryEntry 1 }

        dteAHPortIndex  OBJECT-TYPE
            SYNTAX  PortID
            ACCESS  read-only
            STATUS  mandatory
            DESCRIPTION
                " Port 1 to 6, Total 6 ports"
            ::= { dteAlarmHistoryEntry 2 }

        dteAlarmHIndex  OBJECT-TYPE
            SYNTAX  INTEGER {
                    dte-alarm(1)
                }
            ACCESS  read-only
            STATUS  mandatory
            DESCRIPTION
                " Alarm History Index "
            ::= { dteAlarmHistoryEntry 3 }

        dteAHcurrentHState  OBJECT-TYPE
            SYNTAX  INTEGER {
                    ok(1),
                    alarm(2),
                    disable(3)
                }
            ACCESS  read-only
            STATUS  mandatory
            DESCRIPTION
                " Alarm History Current State"
            ::= { dteAlarmHistoryEntry 4 }

        dteAHcount  OBJECT-TYPE
            SYNTAX  INTEGER
            ACCESS  read-only
            STATUS  mandatory
            DESCRIPTION
                " Alarm History Current Count "
            ::= { dteAlarmHistoryEntry 5 }

        dteAHalarm  OBJECT-TYPE
            SYNTAX  LsAlarmSeverity
            ACCESS  read-only
            STATUS  mandatory
            DESCRIPTION
                "Alarm History Alarm Config"
            ::= { dteAlarmHistoryEntry 6 }

--
--  Alarm Control Table
--

        dteAlarmControlTable  OBJECT-TYPE
            SYNTAX  SEQUENCE OF DTEAlarmControl
            ACCESS  not-accessible
            STATUS  mandatory
            DESCRIPTION
                "The alarm control table."
            ::= { dte-card 4 }

        dteAlarmCtrlEntry  OBJECT-TYPE
            SYNTAX  DTEAlarmControl
            ACCESS  not-accessible
            STATUS  mandatory
            DESCRIPTION
                "An entry in the DTE alarm control table."
            INDEX { dteACSlotIndex ,
                    dteACPortIndex
                }
            ::= { dteAlarmControlTable 1 }

        DTEAlarmControl ::= SEQUENCE {
            dteACSlotIndex              LSSlotID,
            dteACPortIndex              PortID,
            dteACalarmDte               LsAlarmSeverity,
            dteACHistoryReset           INTEGER
--               alarmQueueReset
--                 INTEGER




    }

        dteACSlotIndex  OBJECT-TYPE
            SYNTAX  LSSlotID
            ACCESS  read-only
            STATUS  mandatory
            DESCRIPTION
                "DTE slot"
            ::= { dteAlarmCtrlEntry 1 }

        dteACPortIndex  OBJECT-TYPE
            SYNTAX  PortID
            ACCESS  read-only
            STATUS  mandatory
            DESCRIPTION
                " Port 1 to 6, Total 6 ports"
            ::= { dteAlarmCtrlEntry 2 }

        dteACalarmDte  OBJECT-TYPE
            SYNTAX  LsAlarmSeverity
            ACCESS  read-write
            STATUS  mandatory
            DESCRIPTION
                "DTE-Alarm State"
            ::= { dteAlarmCtrlEntry 3 }

        dteACHistoryReset    OBJECT-TYPE
            SYNTAX  INTEGER {
                    reset(1)
                }
            ACCESS  read-write
            STATUS  mandatory
            DESCRIPTION
                "Command: Reset Alarm History"
            ::= { dteAlarmCtrlEntry 4 }

--         alarmQueueReset    OBJECT-TYPE
--             SYNTAX  INTEGER {
--                         reset(1)
--                     }
--             ACCESS  read-write
--             STATUS  mandatory
--             DESCRIPTION
--                "Command: Reset Alarm Queue "
--             ::= { dteCommandCtrlEntry 2 }


--
-- Line Diagnostic Control Table
--

        dteLineDiagControlTable  OBJECT-TYPE
            SYNTAX  SEQUENCE OF DTELineDiagControl
            ACCESS  not-accessible
            STATUS  mandatory
            DESCRIPTION
                "DTE Diagnostic Control Table."
            ::= { dte-card 5 }

        dteDiagCtrlEntry  OBJECT-TYPE
            SYNTAX  DTELineDiagControl
            ACCESS  not-accessible
            STATUS  mandatory
            DESCRIPTION
                "An entry of DTE diagnostic control table."
            INDEX { dteDCSlotIndex ,
                    dteDCPortIndex
                }
            ::= { dteLineDiagControlTable 1 }

        DTELineDiagControl ::= SEQUENCE {
            dteDCSlotIndex              LSSlotID,
            dteDCPortIndex              PortID,
            dteDCloopbacktype           INTEGER,
            dteDCloopbackstatus         INTEGER
--               dteDCbertctrl
--                 INTEGER,
--               dteDCbertstatus
--                 INTEGER,
--               dteDCelapseseconds
--                 INTEGER,
--               dteDCerrorseconds
--                 INTEGER,
--               dteDCerrorcounts
--                 INTEGER




    }

        dteDCSlotIndex  OBJECT-TYPE
            SYNTAX  LSSlotID
            ACCESS  read-only
            STATUS  mandatory
            DESCRIPTION
                "DTE slot"
            ::= { dteDiagCtrlEntry 1 }

        dteDCPortIndex  OBJECT-TYPE
            SYNTAX  PortID
            ACCESS  read-only
            STATUS  mandatory
            DESCRIPTION
                " Port 1 to 6, Total 6 ports"
            ::= { dteDiagCtrlEntry 2 }

        dteDCloopbacktype  OBJECT-TYPE
            SYNTAX  INTEGER {
                    no-loopback(1),
                    loopback-To-DTE(2),
                    loopback-To-Line(3),
                    remoteV54-active(4),
                    remoteV54-deactive(5)
                }
            ACCESS  read-write
            STATUS  mandatory
            DESCRIPTION
                "DTE Loopback Type"
            ::= { dteDiagCtrlEntry 3 }

        dteDCloopbackstatus  OBJECT-TYPE
            SYNTAX  INTEGER {
                    success(1),
                    fail(2),
                    loopback-not-active(3)
                }
            ACCESS  read-only
            STATUS  mandatory
            DESCRIPTION
                "DTE Loopback Status"
            ::= { dteDiagCtrlEntry 4 }

--         dteDCbertctrl  OBJECT-TYPE
--             SYNTAX  INTEGER {
--                        bert-DEACTIVE(1),
--                        prbs-ACTIVE-DTE(2),
--                        qrss-ACTIVE-DTE(3),
--                        bert-RESET-ERROR-COUNT(4),
--                        bert-INJECT-ERROR(5)
--                     }
--             ACCESS  read-write
--             STATUS  mandatory
--             DESCRIPTION
--                "DTE PRBS/QRSS Control"
--             ::= { dteDiagCtrlEntry 5 }
--
--         dteDCbertstatus  OBJECT-TYPE
--             SYNTAX  INTEGER {
--                        bert-SYNC(1),
--                        bert-UNSYNC(2),
--                        bert-NOT-ACTIVE(3)
--                     }
--             ACCESS  read-only
--             STATUS  mandatory
--             DESCRIPTION
--                "DTE PRBS/QRSS Status"
--             ::= { dteDiagCtrlEntry 6 }
--
--         dteDCelapseseconds  OBJECT-TYPE
--             SYNTAX  INTEGER
--             ACCESS  read-only
--             STATUS  mandatory
--             DESCRIPTION
--                "dte PRBS/QRSS Elapse Seconds"
--             ::= { dteDiagCtrlEntry 7 }
--
--         dteDCerrorseconds  OBJECT-TYPE
--             SYNTAX  INTEGER
--             ACCESS  read-only
--             STATUS  mandatory
--             DESCRIPTION
--                "dte PRBS/QRSS Error Seconds"
--             ::= { dteDiagCtrlEntry 8 }
--
--         dteDCerrorcounts  OBJECT-TYPE
--             SYNTAX  INTEGER
--             ACCESS  read-only
--             STATUS  mandatory
--             DESCRIPTION
--                "dte PRBS/QRSS Error Counts"
--             ::= { dteDiagCtrlEntry 9 }


--
--  Command Control Table
--

        dteCommandControlTable  OBJECT-TYPE
            SYNTAX  SEQUENCE OF DTECommandControl
            ACCESS  not-accessible
            STATUS  mandatory
            DESCRIPTION
                "The command control table."
            ::= { dte-card 6 }

        dteCommandCtrlEntry  OBJECT-TYPE
            SYNTAX  DTECommandControl
            ACCESS  not-accessible
            STATUS  mandatory
            DESCRIPTION
                "An entry in the command control table."
            INDEX { dteCmdSlotIndex }
            ::= { dteCommandControlTable 1 }

        DTECommandControl ::= SEQUENCE {
            dteCmdSlotIndex             LSSlotID,
            dteReset                    INTEGER,
            dteLoadDefault              INTEGER
        }

        dteCmdSlotIndex  OBJECT-TYPE
            SYNTAX  LSSlotID
            ACCESS  read-only
            STATUS  mandatory
            DESCRIPTION
                "DTE slot"
            ::= { dteCommandCtrlEntry 1 }

        dteReset    OBJECT-TYPE
            SYNTAX  INTEGER {
                    reset(1)
                }
            ACCESS  read-write
            STATUS  mandatory
            DESCRIPTION
                "Command: Reset DTE Port"
            ::= { dteCommandCtrlEntry 3 }

        dteLoadDefault    OBJECT-TYPE
            SYNTAX  INTEGER {
                    loadDefault(1)
                }
            ACCESS  read-write
            STATUS  mandatory
            DESCRIPTION
                "Command: Load Default DTE Port"
            ::= { dteCommandCtrlEntry 4 }


--
--  SYSTEM Information Table
--

        dteSystemInfoTable  OBJECT-TYPE
            SYNTAX  SEQUENCE OF DTESystemInformation
            ACCESS  not-accessible
            STATUS  mandatory
            DESCRIPTION
                "The system information table."
            ::= { dte-card 7 }

        dteSystemInfoEntry  OBJECT-TYPE
            SYNTAX  DTESystemInformation
            ACCESS  not-accessible
            STATUS  mandatory
            DESCRIPTION
                "An entry in the system information table."
            INDEX { dteSISlotIndex
                }
            ::= { dteSystemInfoTable 1 }

        DTESystemInformation ::= SEQUENCE {
            dteSISlotIndex              LSSlotID,
            dtePromVersion              DisplayString
        }

        dteSISlotIndex  OBJECT-TYPE
            SYNTAX  LSSlotID
            ACCESS  read-only
            STATUS  mandatory
            DESCRIPTION
                "DTE slot"
            ::= { dteSystemInfoEntry 1 }

        dtePromVersion  OBJECT-TYPE
            SYNTAX  DisplayString (SIZE (0..255) )
            ACCESS  read-only
            STATUS  mandatory
            DESCRIPTION
                " DTE EPROM Version"
            ::= { dteSystemInfoEntry 2 }


--
--  DTE Status Table
--

        dteStatusTable  OBJECT-TYPE
            SYNTAX  SEQUENCE OF DTEStatus
            ACCESS  not-accessible
            STATUS  mandatory
            DESCRIPTION
                "The DTE status table."
            ::= { dte-card 8 }

        dteStatusEntry  OBJECT-TYPE
            SYNTAX  DTEStatus
            ACCESS  not-accessible
            STATUS  mandatory
            DESCRIPTION
                "An entry in the DTE status table."
            INDEX { dteStSlotIndex ,
                    dteStPortIndex
                }
            ::= { dteStatusTable 1 }

        DTEStatus ::= SEQUENCE {
            dteStSlotIndex              LSSlotID,
            dteStPortIndex              PortID,
            dteStatusRTS                INTEGER,
            dteStatusCTS                INTEGER,
            dteStatusDSR                INTEGER,
            dteStatusDCD                INTEGER,
            dteExtClkLoss               INTEGER
        }

        dteStSlotIndex  OBJECT-TYPE
            SYNTAX  LSSlotID
            ACCESS  read-only
            STATUS  mandatory
            DESCRIPTION
                "DTE slot"
            ::= { dteStatusEntry 1 }

        dteStPortIndex  OBJECT-TYPE
            SYNTAX  PortID
            ACCESS  read-only
            STATUS  mandatory
            DESCRIPTION
                " Port 1 to 6, Total 6 ports"
            ::= { dteStatusEntry 2 }

        dteStatusRTS  OBJECT-TYPE
            SYNTAX  INTEGER {
                    active(1),
                    deactive(2)
                }
            ACCESS  read-only
            STATUS  mandatory
            DESCRIPTION
                " DTE RTS status "
            ::= { dteStatusEntry 3 }

        dteStatusCTS  OBJECT-TYPE
            SYNTAX  INTEGER {
                    active(1),
                    deactive(2)
                }
            ACCESS  read-only
            STATUS  mandatory
            DESCRIPTION
                " DTE CTS status "
            ::= { dteStatusEntry 4 }

        dteStatusDSR  OBJECT-TYPE
            SYNTAX  INTEGER {
                    active(1),
                    deactive(2)
                }
            ACCESS  read-only
            STATUS  mandatory
            DESCRIPTION
                " DTE DSR status "
            ::= { dteStatusEntry 5 }

        dteStatusDCD  OBJECT-TYPE
            SYNTAX  INTEGER {
                    active(1),
                    deactive(2)
                }
            ACCESS  read-only
            STATUS  mandatory
            DESCRIPTION
                " DTE DCD status "
            ::= { dteStatusEntry 6 }

        dteExtClkLoss  OBJECT-TYPE
            SYNTAX  INTEGER {
                    normal(1),
                    loss(2)
                }
            ACCESS  read-only
            STATUS  mandatory
            DESCRIPTION
                " DTE external clock loss "
            ::= { dteStatusEntry 7 }

        dteTotalCard   OBJECT-TYPE
            SYNTAX  INTEGER
            ACCESS  read-only
            STATUS  mandatory
            DESCRIPTION
                "Total cards of DTE"
            ::= { dte-card 100 }



--======================================================================--
--======================================================================--
--  x50-card MIB
--======================================================================--
--======================================================================--

--
--  X50 Configuartion
--

        x50ConfigTable  OBJECT-TYPE
            SYNTAX  SEQUENCE OF X50ConfigEntry
            ACCESS  not-accessible
            STATUS  mandatory
            DESCRIPTION
                "The X50 Interface Configuration table."
            ::= { x50-card 1 }

        x50ConfigEntry  OBJECT-TYPE
            SYNTAX  X50ConfigEntry
            ACCESS  not-accessible
            STATUS  mandatory
            DESCRIPTION
                "An entry in the X50 Configuration table."
            INDEX {
                    x50ConfigSlotIndex ,
                    x50ConfigPortIndex
                }
            ::= { x50ConfigTable 1 }

        X50ConfigEntry ::= SEQUENCE {
            x50ConfigSlotIndex          LSSlotID,
            x50ConfigPortIndex          PortID,
            x50Channel                  INTEGER,
            x50Mux                      INTEGER,
            x50SyncMode                 INTEGER,
            x50Rate                     INTEGER,
            x50Phase                    INTEGER,
            x5048k-sel                  INTEGER,
            x50ClockPolarity            INTEGER,
            x50DataPolarity             INTEGER,
            x50RTS                      INTEGER,
            x50TTM                      INTEGER,
            x50Interface                INTEGER,
            x50Warrning                 INTEGER,
            x50DCD                      INTEGER
        }

        x50ConfigSlotIndex  OBJECT-TYPE
            SYNTAX  LSSlotID
            ACCESS  read-only
            STATUS  mandatory
            DESCRIPTION
                "X50 slot"
            ::= { x50ConfigEntry 1 }

        x50ConfigPortIndex  OBJECT-TYPE
            SYNTAX  PortID
            ACCESS  read-only
            STATUS  mandatory
            DESCRIPTION
                "X50 port 1-5"
            ::= { x50ConfigEntry 2 }

        x50Channel  OBJECT-TYPE
            SYNTAX  INTEGER
            ACCESS  read-only
            STATUS  mandatory
            DESCRIPTION
                "X50 Used channel"
            ::= { x50ConfigEntry 3 }


        x50Mux  OBJECT-TYPE
            SYNTAX  INTEGER {
                    noMux(1),
                    mux(2),
                    na(3)
                }
            ACCESS  read-write
            STATUS  mandatory
            DESCRIPTION
                "X50 MUX mode"
            ::= { x50ConfigEntry 4 }


        x50SyncMode  OBJECT-TYPE
            SYNTAX  INTEGER {
                    sync(1),
                    async8(2),
                    async9(3),
                    async10(4),
                    async11(5),
                    async12(6),
                    na(7)
                }
            ACCESS  read-write
            STATUS  mandatory
            DESCRIPTION
                "X50 Sync mode"
            ::= { x50ConfigEntry 5 }

        x50Rate  OBJECT-TYPE
            SYNTAX  INTEGER {
                    r0-6K(0),
                    r1-2K(1),
                    r2-4K(2),
                    r4-8K(3),
                    r9-6K(4),
                    r19-2K(5),
                    r38-4K(6),
                    r48K(7),
                    r64K(8),
                    na(9)
                }
            ACCESS  read-write
            STATUS  mandatory
            DESCRIPTION
                "X50 Base Rate"
            ::= { x50ConfigEntry 6 }


        x50Phase  OBJECT-TYPE
            SYNTAX  INTEGER {
                    ph1(1),
                    ph2(2),
                    ph3(3),
                    ph4(4),
                    ph5(5),
                    na(6)
                }
            ACCESS  read-write
            STATUS  mandatory
            DESCRIPTION
                "X50 Phase select"
            ::= { x50ConfigEntry 7 }

        x5048k-sel  OBJECT-TYPE
            SYNTAX  INTEGER {
                    firstHalf(1),
                    lastHalf(2),
                    oddPair(3),
                    evenPair(4),
                    na(5)
                }
            ACCESS  read-write
            STATUS  mandatory
            DESCRIPTION
                "X50 4.8k map select"
            ::= { x50ConfigEntry 8 }

        x50ClockPolarity  OBJECT-TYPE
            SYNTAX  INTEGER {
                    clockNormal(1),
                    clockInverted(2),
                    na(3)
                }
            ACCESS  read-write
            STATUS  mandatory
            DESCRIPTION
                "X50 Clock Polarity"
            ::= { x50ConfigEntry 9 }

        x50DataPolarity  OBJECT-TYPE
            SYNTAX  INTEGER {
                    dataNormal(1),
                    dataInverted(2),
                    na(3)
                }
            ACCESS  read-write
            STATUS  mandatory
            DESCRIPTION
                "X50 Data Polarity"
            ::= { x50ConfigEntry 10 }

        x50RTS  OBJECT-TYPE
            SYNTAX  INTEGER {
                    rtsActive(1),
                    rtsPermanent(2),
                    na(3)
                }
            ACCESS  read-write
            STATUS  mandatory
            DESCRIPTION
                "X50 RTS Mode"
            ::= {  x50ConfigEntry 11 }

        x50TTM  OBJECT-TYPE
            SYNTAX  INTEGER {
                    ttmOff(1),
                    ttmOn(2),
                    na(3)
                }
            ACCESS  read-write
            STATUS  mandatory
            DESCRIPTION
                "X50 TTM Mode"
            ::= { x50ConfigEntry 12 }

        x50Interface  OBJECT-TYPE
            SYNTAX  INTEGER {
                    v35(1),
                    rs449-eia530(2),
                    x21(3),
                    rs232(4),
                    na(16),
                    rs232-x50(24),
                    db25-rj(41),
                    rj-only(42)
                }
            ACCESS  read-only
            STATUS  mandatory
            DESCRIPTION
                "X50 Interface Type"
            ::= { x50ConfigEntry 13 }

        x50Warrning  OBJECT-TYPE
            SYNTAX  INTEGER {
                    no(1),
                    overlap(2),
                    na(3)
                }
--             SYNTAX  DisplayString (SIZE (0..255) )
            ACCESS  read-only
            STATUS  mandatory
            DESCRIPTION
                "X50 map setup warrning"
            ::= { x50ConfigEntry 14 }

        x50DCD  OBJECT-TYPE
            SYNTAX  INTEGER {
                    remote-all-1-forward(1),
                    permanent-ON(2),
                    remote-X50-forward(3),
                    na(4)
                }
            ACCESS  read-write
            STATUS  mandatory
            DESCRIPTION
                "X50 DCD setup"
            ::= { x50ConfigEntry 15 }

--
--  X50 Status
--

        x50StatusTable  OBJECT-TYPE
            SYNTAX  SEQUENCE OF X50StatusEntry
            ACCESS  not-accessible
            STATUS  mandatory
            DESCRIPTION
                "The X50 Interface Status table."
            ::= { x50-card 2 }

        x50StatusEntry  OBJECT-TYPE
            SYNTAX  X50StatusEntry
            ACCESS  not-accessible
            STATUS  mandatory
            DESCRIPTION
                "An entry in the X50 Status table."
            INDEX { x50StatusSlotIndex , x50StatusPortIndex }
            ::= { x50StatusTable 1 }

        X50StatusEntry ::= SEQUENCE {
            x50StatusSlotIndex          LSSlotID,
            x50StatusPortIndex          PortID,
            x50Existed                  INTEGER,
            x50RTSloss                  INTEGER,
            x50EXTCLKloss               INTEGER,
            x50DSRstatus                INTEGER,
            x50CTSstatus                INTEGER,
            x50DCDstatus                INTEGER,
            x50DTRstatus                INTEGER,
            x50RTSstatus                INTEGER,
            x50RemoteAlarm              INTEGER
        }

        x50StatusSlotIndex  OBJECT-TYPE
            SYNTAX  LSSlotID
            ACCESS  read-only
            STATUS  mandatory
            DESCRIPTION
                "X50 slot index"
            ::= { x50StatusEntry 1 }

        x50StatusPortIndex  OBJECT-TYPE
            SYNTAX  PortID
            ACCESS  read-only
            STATUS  mandatory
            DESCRIPTION
                "X50 port 1-5"
            ::= { x50StatusEntry 2 }

        x50Existed  OBJECT-TYPE
            SYNTAX  INTEGER {
                    no(1),
                    yes(2)
                }
            ACCESS  read-only
            STATUS  mandatory
            DESCRIPTION
                "X50 Existed"
            ::= { x50StatusEntry 3 }

        x50RTSloss  OBJECT-TYPE
            SYNTAX  INTEGER {
                    no(1),
                    yes(2)
                }
            ACCESS  read-only
            STATUS  mandatory
            DESCRIPTION
                "X50 RTS loss"
            ::= { x50StatusEntry 4 }

        x50EXTCLKloss  OBJECT-TYPE
            SYNTAX  INTEGER {
                    no(1),
                    yes(2)
                }
            ACCESS  read-only
            STATUS  mandatory
            DESCRIPTION
                "X50 EXT-CLK loss"
            ::= { x50StatusEntry 5 }

        x50DSRstatus  OBJECT-TYPE
            SYNTAX  INTEGER {
                    no(1),
                    yes(2)
                }
            ACCESS  read-only
            STATUS  mandatory
            DESCRIPTION
                "X50 DSR"
            ::= { x50StatusEntry 6 }

        x50CTSstatus  OBJECT-TYPE
            SYNTAX  INTEGER {
                    no(1),
                    yes(2)
                }
            ACCESS  read-only
            STATUS  mandatory
            DESCRIPTION
                "X50 CTS"
            ::= { x50StatusEntry 7 }

        x50DCDstatus  OBJECT-TYPE
            SYNTAX  INTEGER {
                    no(1),
                    yes(2)
                }
            ACCESS  read-only
            STATUS  mandatory
            DESCRIPTION
                "X50 DCD"
            ::= { x50StatusEntry 8 }

        x50DTRstatus  OBJECT-TYPE
            SYNTAX  INTEGER {
                    no(1),
                    yes(2)
                }
            ACCESS  read-only
            STATUS  mandatory
            DESCRIPTION
                "X50 DTR"
            ::= { x50StatusEntry 9 }

        x50RTSstatus  OBJECT-TYPE
            SYNTAX  INTEGER {
                    no(1),
                    yes(2)
                }
            ACCESS  read-only
            STATUS  mandatory
            DESCRIPTION
                "X50 RTS"
            ::= { x50StatusEntry 10 }

        x50RemoteAlarm  OBJECT-TYPE
            SYNTAX  INTEGER {
                    no(1),
                    yes(2),
                    na(3)
                }
            ACCESS  read-only
            STATUS  mandatory
            DESCRIPTION
                "X50 RTS"
            ::= { x50StatusEntry 11 }


--
--  Alarm History Table
--

        x50AlmHistoryTable  OBJECT-TYPE
            SYNTAX  SEQUENCE OF X50AlmHistoryEntry
            ACCESS  not-accessible
            STATUS  mandatory
            DESCRIPTION
                " Key: x50AlmHistoryUnitIndex "
            ::= { x50-card 3 }

        x50AlmHistoryEntry  OBJECT-TYPE
            SYNTAX  X50AlmHistoryEntry
            ACCESS  not-accessible
            STATUS  mandatory
            DESCRIPTION
                " "
            INDEX { x50AlmHistorySlotIndex , x50AlmHistoryPortIndex }
            ::= { x50AlmHistoryTable 1 }

        X50AlmHistoryEntry ::= SEQUENCE {
            x50AlmHistorySlotIndex      LSSlotID,
            x50AlmHistoryPortIndex      PortID,
            x50AlmHistoryState          INTEGER,
            x50AlmHistoryCount          INTEGER,
            x50AlmHistoryEnable         INTEGER
        }

        x50AlmHistorySlotIndex  OBJECT-TYPE
            SYNTAX  LSSlotID
            ACCESS  read-only
            STATUS  mandatory
            DESCRIPTION
                "X50 slot index"
            ::= { x50AlmHistoryEntry 1 }

        x50AlmHistoryPortIndex  OBJECT-TYPE
            SYNTAX  PortID
            ACCESS  read-only
            STATUS  mandatory
            DESCRIPTION
                "X50 port 1-5"
            ::= { x50AlmHistoryEntry 2 }

        x50AlmHistoryState  OBJECT-TYPE
            SYNTAX  INTEGER {
                    ok(1),
                    alarm(2),
                    disable(3),
                    na(4)
                }
            ACCESS  read-only
            STATUS  mandatory
            DESCRIPTION
                " Alarm Current State"
            ::= { x50AlmHistoryEntry 3 }

        x50AlmHistoryCount  OBJECT-TYPE
            SYNTAX  INTEGER
            ACCESS  read-only
            STATUS  mandatory
            DESCRIPTION
                " Alarm Count which happened "
            ::= { x50AlmHistoryEntry 4 }

        x50AlmHistoryEnable  OBJECT-TYPE
            SYNTAX  INTEGER {
                    disable(1),
                    major(2),
                    critical(3),
                    minor(4),
                    na(5)
                }
            ACCESS  read-only
            STATUS  mandatory
            DESCRIPTION
                "Alarm is enabled or not"
            ::= { x50AlmHistoryEntry 5 }


--
--  Alarm Control Table
--

        x50AlarmControlTable  OBJECT-TYPE
            SYNTAX  SEQUENCE OF X50AlarmControlEntry
            ACCESS  not-accessible
            STATUS  mandatory
            DESCRIPTION
                "The x50 alarm control table."
            ::= { x50-card 4 }

        x50AlarmControlEntry  OBJECT-TYPE
            SYNTAX  X50AlarmControlEntry
            ACCESS  not-accessible
            STATUS  mandatory
            DESCRIPTION
                "An entry in the x50 alarm control table."
            INDEX { x50AlarmSlotIndex , x50AlarmPortIndex }
            ::= { x50AlarmControlTable 1 }

        X50AlarmControlEntry ::= SEQUENCE {
            x50AlarmSlotIndex           LSSlotID,
            x50AlarmPortIndex           PortID,
            x50AlarmSetup               LsAlarmSeverity
        }

        x50AlarmSlotIndex  OBJECT-TYPE
            SYNTAX  LSSlotID
            ACCESS  read-only
            STATUS  mandatory
            DESCRIPTION
                "X50 slot index"
            ::= { x50AlarmControlEntry 1 }

        x50AlarmPortIndex  OBJECT-TYPE
            SYNTAX  PortID
            ACCESS  read-only
            STATUS  mandatory
            DESCRIPTION
                "X50 port 1-5"
            ::= { x50AlarmControlEntry 2 }

        x50AlarmSetup  OBJECT-TYPE
            SYNTAX  LsAlarmSeverity
            ACCESS  read-write
            STATUS  mandatory
            DESCRIPTION
                "Alarm is enabled or not"
            ::= { x50AlarmControlEntry 3 }


--
-- Diagnostic Control Table
--

        x50DiagControlTable  OBJECT-TYPE
            SYNTAX  SEQUENCE OF X50DiagControlEntry
            ACCESS  not-accessible
            STATUS  mandatory
            DESCRIPTION
                ""
            ::= { x50-card 5 }

        x50DiagControlEntry  OBJECT-TYPE
            SYNTAX  X50DiagControlEntry
            ACCESS  not-accessible
            STATUS  mandatory
            DESCRIPTION
                ""
            INDEX { x50DiagControlSlotIndex , x50DiagControlPortIndex }
            ::= { x50DiagControlTable 1 }

        X50DiagControlEntry ::= SEQUENCE {
            x50DiagControlSlotIndex     LSSlotID,
            x50DiagControlPortIndex     PortID,
            x50NearLoopback             INTEGER
--               x50V54Loopback
--                 INTEGER,
--               x50BERTControl
--                 INTEGER,
--               x50BERTStatus
--                 INTEGER,
--               x50BERTElapsedSeconds
--                 INTEGER,
--               x50BERTErrorSeconds
--                 INTEGER,
--               x50BERTErrorCounts
--                 INTEGER




    }

        x50DiagControlSlotIndex  OBJECT-TYPE
            SYNTAX  LSSlotID
            ACCESS  read-only
            STATUS  mandatory
            DESCRIPTION
                "X50 slot index"
            ::= { x50DiagControlEntry 1 }

        x50DiagControlPortIndex  OBJECT-TYPE
            SYNTAX  PortID
            ACCESS  read-only
            STATUS  mandatory
            DESCRIPTION
                "X50 port 1-5"
            ::= { x50DiagControlEntry 2 }

        x50NearLoopback  OBJECT-TYPE
            SYNTAX  INTEGER {
                    noLoopback(1),
                    x50-TO-DTE(2),
                    x50-TO-DS1(3)
                }
            ACCESS  read-write
            STATUS  mandatory
            DESCRIPTION
                "X50 Loopback Type"
            ::= { x50DiagControlEntry 3 }

--         x50BERTControl    OBJECT-TYPE
--             SYNTAX  INTEGER {
--                        bert-OFF(1),
--                        bert-ON(2),
--                        reset(3),
--                        inject-Error(4)
--                     }
--             ACCESS  read-write
--             STATUS  mandatory
--             DESCRIPTION
--                "Bert Control"
--             ::= { x50DiagControlEntry 4 }
--
--         x50BERTStatus  OBJECT-TYPE
--             SYNTAX  INTEGER {
--                        bert-SYNC(1),
--                        bert-UNSYNC(2),
--                        bert-NOT-ACTIVE(3)
--                     }
--             ACCESS  read-only
--             STATUS  mandatory
--             DESCRIPTION
--                "BERT Status"
--             ::= { x50DiagControlEntry 5 }
--
--         x50BERTElapsedSeconds  OBJECT-TYPE
--             SYNTAX  INTEGER
--             ACCESS  read-only
--             STATUS  mandatory
--             DESCRIPTION
--                "BERT Elapsed Time"
--             ::= { x50DiagControlEntry 6 }
--
--         x50BERTErrorSeconds  OBJECT-TYPE
--             SYNTAX  INTEGER
--             ACCESS  read-only
--             STATUS  mandatory
--             DESCRIPTION
--                "BERT Error Seconds"
--             ::= { x50DiagControlEntry 7 }
--
--         x50BERTErrorCounts  OBJECT-TYPE
--             SYNTAX  INTEGER
--             ACCESS  read-only
--             STATUS  mandatory
--             DESCRIPTION
--                "BERT Error Counter"
--             ::= { x50DiagControlEntry 8 }

--
-- Card Control Table
--

        x50CardControlTable  OBJECT-TYPE
            SYNTAX  SEQUENCE OF X50CardControlEntry
            ACCESS  not-accessible
            STATUS  mandatory
            DESCRIPTION
                "The x50 Card control table."
            ::= { x50-card 7 }

        x50CardControlEntry  OBJECT-TYPE
            SYNTAX  X50CardControlEntry
            ACCESS  not-accessible
            STATUS  mandatory
            DESCRIPTION
                "An entry in the x50 Card control table."
            INDEX { x50CardIndex }
            ::= { x50CardControlTable 1 }

        X50CardControlEntry ::= SEQUENCE {
            x50CardIndex                LSSlotID,
            x50Reset                    INTEGER,
            x50LoadDefault              INTEGER
        }

        x50CardIndex  OBJECT-TYPE
            SYNTAX  LSSlotID
            ACCESS  read-only
            STATUS  mandatory
            DESCRIPTION
                "x50 Card index"
            ::= { x50CardControlEntry 1 }

        x50Reset  OBJECT-TYPE
            SYNTAX  INTEGER {
                    reset(1)
                }
            ACCESS  read-write
            STATUS  mandatory
            DESCRIPTION
                "Reset x50 card"
            ::= { x50CardControlEntry 2 }

        x50LoadDefault  OBJECT-TYPE
            SYNTAX  INTEGER {
                    default(1)
                }
            ACCESS  read-write
            STATUS  mandatory
            DESCRIPTION
                "Load default"
            ::= { x50CardControlEntry 3 }


--
-- Card Information Table
--

        x50CardInformationTable  OBJECT-TYPE
            SYNTAX  SEQUENCE OF X50CardInformationEntry
            ACCESS  not-accessible
            STATUS  mandatory
            DESCRIPTION
                "The x50 Card information."
            ::= { x50-card 8 }

        x50CardInformationEntry  OBJECT-TYPE
            SYNTAX  X50CardInformationEntry
            ACCESS  not-accessible
            STATUS  mandatory
            DESCRIPTION
                "An entry in the x50 Card Information."
            INDEX { x50CardInformationIndex }
            ::= { x50CardInformationTable 1 }

        X50CardInformationEntry ::= SEQUENCE {
            x50CardInformationIndex     LSSlotID,
            x50SoftwareVersion          DisplayString
        }

        x50CardInformationIndex  OBJECT-TYPE
            SYNTAX  LSSlotID
            ACCESS  read-only
            STATUS  mandatory
            DESCRIPTION
                "x50 Card index"
            ::= { x50CardInformationEntry 1 }

        x50SoftwareVersion  OBJECT-TYPE
            SYNTAX  DisplayString (SIZE (0..255))
            ACCESS  read-only
            STATUS  mandatory
            DESCRIPTION
                "x50 card software version"
            ::= { x50CardInformationEntry 2 }

        x50TotalCard   OBJECT-TYPE
            SYNTAX  INTEGER
            ACCESS  read-only
            STATUS  mandatory
            DESCRIPTION
                "Total cards of X50"
            ::= { x50-card 100 }


--======================================================================--
--======================================================================--
--  em-card MIB
--======================================================================--
-- E&M Card

--      emConfigControlTable           OBJECT IDENTIFIER ::= { em-card 1  }
--      emDiagControlTable             OBJECT IDENTIFIER ::= { em-card 3  }
--      emCommandControlTable          OBJECT IDENTIFIER ::= { em-card 4  }
--      emAllPortConfigTable           OBJECT IDENTIFIER ::= { em-card 5  }
--      emPerPortConfigTable           OBJECT IDENTIFIER ::= { em-card 6  }
--      emALLPortSigConfigTable        OBJECT IDENTIFIER ::= { em-card 7  }
--======================================================================--

            EMOffOn ::= INTEGER   {
        off(1),
        on(2),
        null(3)
    }

        EMGain ::= INTEGER   {
        gain-neg-16-0-db(1),
        gain-neg-15-5-db(2),
        gain-neg-15-0-db(3),
        gain-neg-14-5-db(4),
        gain-neg-14-0-db(5),
        gain-neg-13-5-db(6),
        gain-neg-13-0-db(7),
        gain-neg-12-5-db(8),
        gain-neg-12-0-db(9),
        gain-neg-11-5-db(10),
        gain-neg-11-0-db(11),
        gain-neg-10-5-db(12),
        gain-neg-10-0-db(13),
        gain-neg-9-5-db(14),
        gain-neg-9-0-db(15),
        gain-neg-8-5-db(16),
        gain-neg-8-0-db(17),
        gain-neg-7-5-db(18),
        gain-neg-7-0-db(19),
        gain-neg-6-5-db(20),
        gain-neg-6-0-db(21),
        gain-neg-5-5-db(22),
        gain-neg-5-0-db(23),
        gain-neg-4-5-db(24),
        gain-neg-4-0-db(25),
        gain-neg-3-5-db(26),
        gain-neg-3-0-db(27),
        gain-neg-2-5-db(28),
        gain-neg-2-0-db(29),
        gain-neg-1-5-db(30),
        gain-neg-1-0-db(31),
        gain-neg-0-5-db(32),
        gain-0-0-db(33),
        gain-0-5-db(34),
        gain-1-0-db(35),
        gain-1-5-db(36),
        gain-2-0-db(37),
        gain-2-5-db(38),
        gain-3-0-db(39),
        gain-3-5-db(40),
        gain-4-0-db(41),
        gain-4-5-db(42),
        gain-5-0-db(43),
        gain-5-5-db(44),
        gain-6-0-db(45),
        gain-6-5-db(46),
        gain-7-0-db(47),
        not-available(255)
    }

--
--      EM Control Table
--

        emConfigControlTable  OBJECT-TYPE
            SYNTAX  SEQUENCE OF EmConfigControlEntry
            ACCESS  not-accessible
            STATUS  mandatory
            DESCRIPTION
                "E&M Configuration Control Table"
            ::= { em-card 1 }

        emConfigControlEntry  OBJECT-TYPE
            SYNTAX  EmConfigControlEntry
            ACCESS  not-accessible
            STATUS  mandatory
            DESCRIPTION
                "E&m configuration control entry"
            INDEX { emConfigControlIndex }
            ::= { emConfigControlTable 1 }

        EmConfigControlEntry ::= SEQUENCE {
            emConfigControlIndex        LSSlotID,
            emConfigControlSide         INTEGER,
            emConfigControlLine         INTEGER,
            emConfigControlImpedance    INTEGER,
            emConfigControlSignaling    INTEGER,
--             emConfigControlAB-bit
--               INTEGER,
            emConfigControlA-u-law      INTEGER,
            emConfigControlTx-gain      EMGain,
            emConfigControlRx-gain      EMGain,
            emConfigControlHW-SW-Control    INTEGER
        }

        emConfigControlIndex  OBJECT-TYPE
            SYNTAX  LSSlotID
            ACCESS  read-only
            STATUS  mandatory
            DESCRIPTION
                "EM slot"
            ::= { emConfigControlEntry 1 }

        emConfigControlSide   OBJECT-TYPE
            SYNTAX  INTEGER {
                    a(1),
                    b(2),
--                      a-b(3),
                    error(4),
                    not-available(255)
                }
            ACCESS  read-only
            STATUS  mandatory
            DESCRIPTION
                " E&M Side "
            ::= { emConfigControlEntry 2 }

        emConfigControlLine   OBJECT-TYPE
            SYNTAX  INTEGER {
                    with-2-WIRE(1),
                    with-4-WIRE(2),
                    not-available(255)
                }
            ACCESS  read-write
            STATUS  mandatory
            DESCRIPTION
                " E&M Line "
            ::= { emConfigControlEntry 3 }

        emConfigControlImpedance   OBJECT-TYPE
            SYNTAX  INTEGER {
                    imp-900-ohm(1),
                    imp-600-ohm(2),
                    not-available(255)
                }
            ACCESS  read-write
            STATUS  mandatory
            DESCRIPTION
                " IMPEDANCE "
            ::= { emConfigControlEntry 4 }

        emConfigControlSignaling   OBJECT-TYPE
            SYNTAX  INTEGER {
                    tx-ONLY(1),
                    type-1(2),
                    type-2(3),
                    type-3(4),
                    type-4(5),
                    type-5(6),
                    error(7),
                    not-available(255)
                }
            ACCESS  read-write
            STATUS  mandatory
            DESCRIPTION
                " E&M Line "
            ::= { emConfigControlEntry 5 }

--       emConfigControlAB-bit OBJECT-TYPE
--           SYNTAX  INTEGER {
--                      normal(1),
--                      invert(2)
--                   }
--           ACCESS  read-write
--           STATUS  mandatory
--           DESCRIPTION
--              " AB-BIT "
--           ::= { emConfigControlEntry 6 }

        emConfigControlA-u-law   OBJECT-TYPE
            SYNTAX  INTEGER {
                    u-law(1),
                    a-law(2),
                    not-available(255)
                }
            ACCESS  read-write
            STATUS  mandatory
            DESCRIPTION
                " A/u LAW "
            ::= { emConfigControlEntry 7 }

        emConfigControlTx-gain   OBJECT-TYPE
            SYNTAX  EMGain
            ACCESS  read-write
            STATUS  mandatory
            DESCRIPTION
                " TX-GAIN "
            ::= { emConfigControlEntry 8 }

        emConfigControlRx-gain   OBJECT-TYPE
            SYNTAX  EMGain
            ACCESS  read-write
            STATUS  mandatory
            DESCRIPTION
                " RX-GAIN "
            ::= { emConfigControlEntry 9 }

        emConfigControlHW-SW-Control   OBJECT-TYPE
            SYNTAX  INTEGER {
                    hw-control(1),
                    sw-control(2),
                    not-available(255)
                }
            ACCESS  read-only
            STATUS  mandatory
            DESCRIPTION
                " E&M HW/SW Control Mode "
            ::= { emConfigControlEntry 10 }


--
-- Line Diagnostic Control Table
--

        emDiagControlTable  OBJECT-TYPE
            SYNTAX  SEQUENCE OF EmDiagControlEntry
            ACCESS  not-accessible
            STATUS  mandatory
            DESCRIPTION
                "E&M Diagnostic Control Table."
            ::= { em-card 3 }

        emDiagControlEntry  OBJECT-TYPE
            SYNTAX  EmDiagControlEntry
            ACCESS  not-accessible
            STATUS  mandatory
            DESCRIPTION
                "An entry of E&M diagnostic control table."
            INDEX { emDiagControlIndex }
            ::= { emDiagControlTable 1 }

        EmDiagControlEntry ::= SEQUENCE {
            emDiagControlIndex          LSSlotID,
            emDiagControlTEST           INTEGER,
            emDiagControlE1             EMOffOn,
            emDiagControlE2             EMOffOn,
            emDiagControlE3             EMOffOn,
            emDiagControlE4             EMOffOn,
            emDiagControlE5             EMOffOn,
            emDiagControlE6             EMOffOn,
            emDiagControlE7             EMOffOn,
            emDiagControlE8             EMOffOn,
            emDiagControlM1             EMOffOn,
            emDiagControlM2             EMOffOn,
            emDiagControlM3             EMOffOn,
            emDiagControlM4             EMOffOn,
            emDiagControlM5             EMOffOn,
            emDiagControlM6             EMOffOn,
            emDiagControlM7             EMOffOn,
            emDiagControlM8             EMOffOn,
            emDiagControl-48V-Power     INTEGER,
            emUpLinkStatus              INTEGER,
            emTestButton                INTEGER
        }

        emDiagControlIndex  OBJECT-TYPE
            SYNTAX  LSSlotID
            ACCESS  read-only
            STATUS  mandatory
            DESCRIPTION
                "slot index"
            ::= { emDiagControlEntry 1 }

        emDiagControlTEST  OBJECT-TYPE
            SYNTAX  INTEGER {
                    stop(1),
                    start(2)
                }
            ACCESS  read-write
            STATUS  mandatory
            DESCRIPTION
                "E&M  Test Button"
            ::= { emDiagControlEntry 2 }

        emDiagControlE1  OBJECT-TYPE
            SYNTAX  EMOffOn
            ACCESS  read-only
            STATUS  mandatory
            DESCRIPTION
                "E&M  E1"
            ::= { emDiagControlEntry 3 }

        emDiagControlE2  OBJECT-TYPE
            SYNTAX  EMOffOn
            ACCESS  read-only
            STATUS  mandatory
            DESCRIPTION
                "E&M  E2"
            ::= { emDiagControlEntry 4 }

        emDiagControlE3  OBJECT-TYPE
            SYNTAX  EMOffOn
            ACCESS  read-only
            STATUS  mandatory
            DESCRIPTION
                "E&M  E3"
            ::= { emDiagControlEntry 5 }

        emDiagControlE4  OBJECT-TYPE
            SYNTAX  EMOffOn
            ACCESS  read-only
            STATUS  mandatory
            DESCRIPTION
                "E&M  E4"
            ::= { emDiagControlEntry 6 }

        emDiagControlE5  OBJECT-TYPE
            SYNTAX  EMOffOn
            ACCESS  read-only
            STATUS  mandatory
            DESCRIPTION
                "E&M  E5"
            ::= { emDiagControlEntry 7 }

        emDiagControlE6  OBJECT-TYPE
            SYNTAX  EMOffOn
            ACCESS  read-only
            STATUS  mandatory
            DESCRIPTION
                "E&M  E6"
            ::= { emDiagControlEntry 8 }

        emDiagControlE7  OBJECT-TYPE
            SYNTAX  EMOffOn
            ACCESS  read-only
            STATUS  mandatory
            DESCRIPTION
                "E&M  E7"
            ::= { emDiagControlEntry 9 }

        emDiagControlE8  OBJECT-TYPE
            SYNTAX  EMOffOn
            ACCESS  read-only
            STATUS  mandatory
            DESCRIPTION
                "E&M  E8"
            ::= { emDiagControlEntry 10 }

        emDiagControlM1  OBJECT-TYPE
            SYNTAX  EMOffOn
            ACCESS  read-only
            STATUS  mandatory
            DESCRIPTION
                "E&M  M1"
            ::= { emDiagControlEntry 11 }

        emDiagControlM2  OBJECT-TYPE
            SYNTAX  EMOffOn
            ACCESS  read-only
            STATUS  mandatory
            DESCRIPTION
                "E&M  M2"
            ::= { emDiagControlEntry 12 }

        emDiagControlM3  OBJECT-TYPE
            SYNTAX  EMOffOn
            ACCESS  read-only
            STATUS  mandatory
            DESCRIPTION
                "E&M  M3"
            ::= { emDiagControlEntry 13 }

        emDiagControlM4  OBJECT-TYPE
            SYNTAX  EMOffOn
            ACCESS  read-only
            STATUS  mandatory
            DESCRIPTION
                "E&M  M4"
            ::= { emDiagControlEntry 14 }

        emDiagControlM5  OBJECT-TYPE
            SYNTAX  EMOffOn
            ACCESS  read-only
            STATUS  mandatory
            DESCRIPTION
                "E&M  M5"
            ::= { emDiagControlEntry 15 }

        emDiagControlM6  OBJECT-TYPE
            SYNTAX  EMOffOn
            ACCESS  read-only
            STATUS  mandatory
            DESCRIPTION
                "E&M  M6"
            ::= { emDiagControlEntry 16 }

        emDiagControlM7  OBJECT-TYPE
            SYNTAX  EMOffOn
            ACCESS  read-only
            STATUS  mandatory
            DESCRIPTION
                "E&M  M7"
            ::= { emDiagControlEntry 17 }

        emDiagControlM8  OBJECT-TYPE
            SYNTAX  EMOffOn
            ACCESS  read-only
            STATUS  mandatory
            DESCRIPTION
                "E&M  M8"
            ::= { emDiagControlEntry 18 }

        emDiagControl-48V-Power  OBJECT-TYPE
            SYNTAX  INTEGER {
                    ok(1),
                    failure(2)
                }
            ACCESS  read-only
            STATUS  mandatory
            DESCRIPTION
                "<V5.0: -48V Power OK/Failure
                >V5.0: M,SB Lead 48V status"
            ::= { emDiagControlEntry 19 }

        emUpLinkStatus  OBJECT-TYPE
            SYNTAX  INTEGER {
                    ok(1),
                    failure(2),
                    na(3)
                }
            ACCESS  read-only
            STATUS  mandatory
            DESCRIPTION
                "UpLink Status"
            ::= { emDiagControlEntry 20 }

        emTestButton  OBJECT-TYPE
            SYNTAX  INTEGER {
                    available(1),
                    unavailable(2),
                    old-version(3)
                }
            ACCESS  read-only
            STATUS  mandatory
            DESCRIPTION
                "Test button available"
            ::= { emDiagControlEntry 21 }


--
--  Command Control Table
--

        emCommandControlTable  OBJECT-TYPE
            SYNTAX  SEQUENCE OF EmCommandControlEntry
            ACCESS  not-accessible
            STATUS  mandatory
            DESCRIPTION
                "The command control table."
            ::= { em-card 4 }

        emCommandControlEntry  OBJECT-TYPE
            SYNTAX  EmCommandControlEntry
            ACCESS  not-accessible
            STATUS  mandatory
            DESCRIPTION
                "An entry in the command control table."
            INDEX { emCommandControlIndex }
            ::= { emCommandControlTable 1 }

        EmCommandControlEntry ::= SEQUENCE {
            emCommandControlIndex       LSSlotID,
            emCommandControlReset       INTEGER,
            emCommandControlLoadDefault INTEGER
        }

        emCommandControlIndex  OBJECT-TYPE
            SYNTAX  LSSlotID
            ACCESS  read-only
            STATUS  mandatory
            DESCRIPTION
                "slot index"
            ::= { emCommandControlEntry 1 }

        emCommandControlLoadDefault    OBJECT-TYPE
            SYNTAX  INTEGER {
                    load-default(1)
                }
            ACCESS  read-write
            STATUS  mandatory
            DESCRIPTION
                "Command: Load Default E&M CONF"
            ::= { emCommandControlEntry 2 }

        emCommandControlReset    OBJECT-TYPE
            SYNTAX  INTEGER {
                    reset(1)
                }
            ACCESS  read-write
            STATUS  mandatory
            DESCRIPTION
                "Command: E&M Card Reset"
            ::= { emCommandControlEntry 3 }

--
--      EM All Port Control Table
--

        emAllPortConfigTable  OBJECT-TYPE
            SYNTAX  SEQUENCE OF EmAllPortConfigEntry
            ACCESS  not-accessible
            STATUS  mandatory
            DESCRIPTION
                "E&M All Port Configuration Control Table"
            ::= { em-card 5 }

        emAllPortConfigEntry  OBJECT-TYPE
            SYNTAX  EmAllPortConfigEntry
            ACCESS  not-accessible
            STATUS  mandatory
            DESCRIPTION
                "E&m All Port configuration control entry"
            INDEX { emAllPortConfigIndex }
            ::= { emAllPortConfigTable 1 }

        EmAllPortConfigEntry ::= SEQUENCE {
            emAllPortConfigIndex        LSSlotID,
            emAllPortConfigSide         INTEGER,
            emAllPortConfigLine         INTEGER,
            emAllPortConfigImpedance    INTEGER,
            emAllPortConfigSignaling    INTEGER,
            emAllPortConfigA-u-law      INTEGER,
            emAllPortConfigHW-SW-Control    INTEGER,
            emAllPortConfigTrunk-Condition  INTEGER
        }

        emAllPortConfigIndex  OBJECT-TYPE
            SYNTAX  LSSlotID
            ACCESS  read-only
            STATUS  mandatory
            DESCRIPTION
                "slot index"
            ::= { emAllPortConfigEntry 1 }

        emAllPortConfigSide   OBJECT-TYPE
            SYNTAX  INTEGER {
                    a(1),
                    b(2),
                    error(4)
                }
            ACCESS  read-only
            STATUS  mandatory
            DESCRIPTION
                " E&M Side "
            ::= { emAllPortConfigEntry 2 }

        emAllPortConfigLine   OBJECT-TYPE
            SYNTAX  INTEGER {
                    with-2-WIRE(1),
                    with-4-WIRE(2)
                }
            ACCESS  read-write
            STATUS  mandatory
            DESCRIPTION
                " E&M Line "
            ::= { emAllPortConfigEntry 3 }

        emAllPortConfigImpedance   OBJECT-TYPE
            SYNTAX  INTEGER {
                    imp-900-ohm(1),
                    imp-600-ohm(2)
                }
            ACCESS  read-write
            STATUS  mandatory
            DESCRIPTION
                " IMPEDANCE "
            ::= { emAllPortConfigEntry 4 }

        emAllPortConfigSignaling   OBJECT-TYPE
            SYNTAX  INTEGER {
                    tx-ONLY(1),
                    type-1(2),
                    type-2(3),
                    type-3(4),
                    type-4(5),
                    type-5(6),
                    error(7)
                }
            ACCESS  read-write
            STATUS  mandatory
            DESCRIPTION
                " E&M Line "
            ::= { emAllPortConfigEntry 5 }

        emAllPortConfigA-u-law   OBJECT-TYPE
            SYNTAX  INTEGER {
                    u-law(1),
                    a-law(2)
                }
            ACCESS  read-write
            STATUS  mandatory
            DESCRIPTION
                " A/u LAW "
            ::= { emAllPortConfigEntry 7 }

        emAllPortConfigHW-SW-Control   OBJECT-TYPE
            SYNTAX  INTEGER {
                    hw-control(1),
                    sw-control(2)
                }
            ACCESS  read-only
            STATUS  mandatory
            DESCRIPTION
                " E&M HW/SW Control Mode "
            ::= { emAllPortConfigEntry 8 }

        emAllPortConfigTrunk-Condition   OBJECT-TYPE
            SYNTAX  INTEGER {
                    off-hook(1),
                    on-hook(2),
                    na(3)
                }
            ACCESS  read-only
            STATUS  mandatory
            DESCRIPTION
                " E&M Trunk Condition Control Mode "
            ::= { emAllPortConfigEntry 9 }


--
--      E&M Per Port Config Control Table
--

        emPerPortConfigTable  OBJECT-TYPE
            SYNTAX  SEQUENCE OF EmPerPortConfigEntry
            ACCESS  not-accessible
            STATUS  mandatory
            DESCRIPTION
                "E&M Per Port Configuration Control Table"
            ::= { em-card 6 }

        emPerPortConfigEntry  OBJECT-TYPE
            SYNTAX  EmPerPortConfigEntry
            ACCESS  not-accessible
            STATUS  mandatory
            DESCRIPTION
                "E&M Per Port Configuration control entry"
            INDEX { emPerPortConfigIndex ,
                    emPerPortConfigPortIndex }
            ::= { emPerPortConfigTable 1 }

        EmPerPortConfigEntry ::= SEQUENCE {
            emPerPortConfigIndex        LSSlotID,
            emPerPortConfigPortIndex    PortID,
--               emPerPortConfigPLAR
--                 INTEGER,
            emPerPortConfigTx-gain      DisplayString,
            emPerPortConfigRx-gain      DisplayString
        }

        emPerPortConfigIndex  OBJECT-TYPE
            SYNTAX  LSSlotID
            ACCESS  read-only
            STATUS  mandatory
            DESCRIPTION
                "slot index"
            ::= { emPerPortConfigEntry 1 }

        emPerPortConfigPortIndex   OBJECT-TYPE
            SYNTAX  PortID
            ACCESS  read-only
            STATUS  mandatory
            DESCRIPTION
                "port index"
            ::= { emPerPortConfigEntry 2 }

--         emPerPortConfigPLAR   OBJECT-TYPE
--             SYNTAX INTEGER {
--                       off(1),
--                       on(2)
--                    }
--             ACCESS  read-write
--             STATUS  mandatory
--             DESCRIPTION
--                " Per port PLAR setting "
--             ::= { emPerPortConfigEntry 3 }

        emPerPortConfigTx-gain   OBJECT-TYPE
            SYNTAX  DisplayString (SIZE (0..255))
            ACCESS  read-write
            STATUS  mandatory
            DESCRIPTION
                " Per port TX-GAIN setting "
            ::= { emPerPortConfigEntry 4 }

        emPerPortConfigRx-gain   OBJECT-TYPE
            SYNTAX  DisplayString (SIZE (0..255))
            ACCESS  read-write
            STATUS  mandatory
            DESCRIPTION
                " Per port RX-GAIN setting "
            ::= { emPerPortConfigEntry 5 }


--
--      E&M All Port Signaling Config Control Table
--

        emALLPortSigConfigTable  OBJECT-TYPE
            SYNTAX  SEQUENCE OF EmAllPortSigConfigEntry
            ACCESS  not-accessible
            STATUS  mandatory
            DESCRIPTION
                "E&M All Port Signaling Configuration Control Table"
            ::= { em-card 7 }

        emAllPortSigConfigEntry  OBJECT-TYPE
            SYNTAX  EmAllPortSigConfigEntry
            ACCESS  not-accessible
            STATUS  mandatory
            DESCRIPTION
                "E&M all port signaling configuration control entry"
            INDEX { emAllPortSigConfigIndex ,
                    emAllPortSigConfigItemIndex ,
                    emAllPortSigConfigSigBitIndex }
            ::= { emALLPortSigConfigTable 1 }

        EmAllPortSigConfigEntry ::= SEQUENCE {
            emAllPortSigConfigIndex     LSSlotID,
            emAllPortSigConfigItemIndex INTEGER,
            emAllPortSigConfigSigBitIndex   INTEGER,
            emAllPortSigConfigSigBit        INTEGER
        }

        emAllPortSigConfigIndex  OBJECT-TYPE
            SYNTAX  LSSlotID
            ACCESS  read-only
            STATUS  mandatory
            DESCRIPTION
                "slot index"
            ::= { emAllPortSigConfigEntry 1 }

        emAllPortSigConfigItemIndex   OBJECT-TYPE
            SYNTAX  INTEGER {
                    tx-on-hook(1),
                    tx-off-hook(2),
                    rx-relay-open(3),
                    rx-relay-close(4)
                }
            ACCESS  read-only
            STATUS  mandatory
            DESCRIPTION
                "on-hook, off-hook, relay-open, relay-close"
            ::= { emAllPortSigConfigEntry 2 }

        emAllPortSigConfigSigBitIndex   OBJECT-TYPE
            SYNTAX  INTEGER {
                    a(1),
                    b(2),
                    c(3),
                    d(4)
                }
            ACCESS  read-only
            STATUS  mandatory
            DESCRIPTION
                " Signaling Bit Index "
            ::= { emAllPortSigConfigEntry 3 }

        emAllPortSigConfigSigBit   OBJECT-TYPE
            SYNTAX  INTEGER {
                    zero(0),
                    one(1),
                    do-not-care(2)
                }
            ACCESS  read-only
            STATUS  mandatory
            DESCRIPTION
                " Signaling Bit Setup 0/1 or don't care "
            ::= { emAllPortSigConfigEntry 4 }

--
--      EM6 All Port Control Table
--

        em6AllPortCfgSetTable  OBJECT-TYPE
            SYNTAX  SEQUENCE OF Em6AllPortCfgSetEntry
            ACCESS  not-accessible
            STATUS  mandatory
            DESCRIPTION
                "E&M6 All Port Configuration Control Table"
            ::= { em-card 8 }

        em6AllPortCfgSetEntry  OBJECT-TYPE
            SYNTAX  Em6AllPortCfgSetEntry
            ACCESS  not-accessible
            STATUS  mandatory
            DESCRIPTION
                "E&m6 All Port configuration control entry"
            INDEX { em6AllPortCfgSetIndex }
            ::= { em6AllPortCfgSetTable 1 }

        Em6AllPortCfgSetEntry ::= SEQUENCE {
            em6AllPortCfgSetIndex LSSlotID,
            em6AllPortCfgSetSide14  INTEGER,
            em6AllPortCfgSetSide58  INTEGER,
            em6AllPortCfgSetLine  INTEGER,
            em6AllPortCfgSetImpedance INTEGER,
            em6AllPortCfgSetSignaling INTEGER,
            em6AllPortCfgSetA-u-law   INTEGER,
            em6AllPortCfgSetHW-SW   INTEGER,
            em6AllPortCfgSetTrunk14   INTEGER,
            em6AllPortCfgSetTrunk58   INTEGER,
            em6AllPortCfgSetRingBackSW   INTEGER,
            em6AllPortCfgSetTestButton   INTEGER
        }

        em6AllPortCfgSetIndex  OBJECT-TYPE
            SYNTAX  LSSlotID
            ACCESS  read-only
            STATUS  mandatory
            DESCRIPTION
                "slot index"
            ::= { em6AllPortCfgSetEntry 1 }

        em6AllPortCfgSetSide14   OBJECT-TYPE
            SYNTAX  INTEGER {
                    a(1),
                    b(2),
                    error(4)
                }
            ACCESS  read-only
            STATUS  mandatory
            DESCRIPTION
                " E&M6 Side "
            ::= { em6AllPortCfgSetEntry 2 }

        em6AllPortCfgSetSide58   OBJECT-TYPE
            SYNTAX  INTEGER {
                    a(1),
                    b(2),
                    error(4)
                }
            ACCESS  read-only
            STATUS  mandatory
            DESCRIPTION
                " E&M6 Side "
            ::= { em6AllPortCfgSetEntry 3 }


        em6AllPortCfgSetLine   OBJECT-TYPE
            SYNTAX  INTEGER {
                    with-2-WIRE(1),
                    with-4-WIRE(2)
                }
            ACCESS  read-write
            STATUS  mandatory
            DESCRIPTION
                " E&M Line "
            ::= { em6AllPortCfgSetEntry 4 }

        em6AllPortCfgSetImpedance   OBJECT-TYPE
            SYNTAX  INTEGER {
                    imp-900-ohm(1),
                    imp-600-ohm(2)
                }
            ACCESS  read-write
            STATUS  mandatory
            DESCRIPTION
                " IMPEDANCE "
            ::= { em6AllPortCfgSetEntry 5 }

        em6AllPortCfgSetSignaling   OBJECT-TYPE
            SYNTAX  INTEGER {
                    tx-ONLY(1),
                    type-1(2),
                    type-2(3),
                    type-3(4),
                    type-4(5),
                    type-5(6),
                    error(7)
                }
            ACCESS  read-write
            STATUS  mandatory
            DESCRIPTION
                " E&M Line "
            ::= { em6AllPortCfgSetEntry 6 }

        em6AllPortCfgSetA-u-law   OBJECT-TYPE
            SYNTAX  INTEGER {
                    u-law(1),
                    a-law(2)
                }
            ACCESS  read-write
            STATUS  mandatory
            DESCRIPTION
                " A/u LAW "
            ::= { em6AllPortCfgSetEntry 7 }

        em6AllPortCfgSetHW-SW    OBJECT-TYPE
            SYNTAX  INTEGER {
                    hw-control(1),
                    sw-control(2)
                }
            ACCESS  read-only
            STATUS  mandatory
            DESCRIPTION
                " E&M HW/SW Control Mode "
            ::= { em6AllPortCfgSetEntry 8 }

        em6AllPortCfgSetTrunk14   OBJECT-TYPE
            SYNTAX  INTEGER {
                    off-hook(1),
                    on-hook(2),
                    na(3)
                }
            ACCESS  read-write
            STATUS  mandatory
            DESCRIPTION
                " E&M Trunk Condition Control Mode "
            ::= { em6AllPortCfgSetEntry 9 }

        em6AllPortCfgSetTrunk58   OBJECT-TYPE
            SYNTAX  INTEGER {
                    off-hook(1),
                    on-hook(2),
                    na(3)
                }
            ACCESS  read-write
            STATUS  mandatory
            DESCRIPTION
                " E&M Trunk Condition Control Mode "
            ::= { em6AllPortCfgSetEntry 10 }

        em6AllPortCfgSetRingBackSW   OBJECT-TYPE
            SYNTAX  INTEGER {
                    available(1),
                    unavailable(2)
                }
            ACCESS  read-write
            STATUS  mandatory
            DESCRIPTION
                " E&M Trunk Condition Control Mode "
            ::= { em6AllPortCfgSetEntry 11 }

        em6AllPortCfgSetTestButton  OBJECT-TYPE
            SYNTAX  INTEGER {
                    available(1),
                    unavailable(2)
                }
            ACCESS  read-write
            STATUS  mandatory
            DESCRIPTION
                " E&M Trunk Condition Control Mode "
            ::= { em6AllPortCfgSetEntry 12 }
--
--      E&M All Port Signaling Config Set Table
--

        em6ALLPortSigCfgSetTable  OBJECT-TYPE
            SYNTAX  SEQUENCE OF Em6AllPortSigCfgSetEntry
            ACCESS  not-accessible
            STATUS  mandatory
            DESCRIPTION
                "E&M All Port Signaling Configuration Set Table"
            ::= { em-card 9 }

        em6AllPortSigCfgSetEntry  OBJECT-TYPE
            SYNTAX  Em6AllPortSigCfgSetEntry
            ACCESS  not-accessible
            STATUS  mandatory
            DESCRIPTION
                "E&M all port signaling configuration control entry"
            INDEX { em6AllPortSigCfgSetIndex ,
                    em6AllPortSigCfgSetItemIndex ,
                    em6AllPortSigCfgSetSigBitIndex }
            ::= { em6ALLPortSigCfgSetTable 1 }

        Em6AllPortSigCfgSetEntry ::= SEQUENCE {
            em6AllPortSigCfgSetIndex  LSSlotID,
            em6AllPortSigCfgSetItemIndex  INTEGER,
            em6AllPortSigCfgSetSigBitIndex    INTEGER,
            em6AllPortSigCfgSetSigBit         INTEGER
        }

        em6AllPortSigCfgSetIndex  OBJECT-TYPE
            SYNTAX  LSSlotID
            ACCESS  read-only
            STATUS  mandatory
            DESCRIPTION
                "slot index"
            ::= { em6AllPortSigCfgSetEntry 1 }

        em6AllPortSigCfgSetItemIndex   OBJECT-TYPE
            SYNTAX  INTEGER {
                    tx-on-hook(1),
                    tx-off-hook(2),
                    rx-relay-open(3),
                    rx-relay-close(4),
                    tx-ring-back(5),
                    rx-oos-alm(6)
                }
            ACCESS  read-only
            STATUS  mandatory
            DESCRIPTION
                "on-hook, off-hook, relay-open, relay-close"
            ::= { em6AllPortSigCfgSetEntry 2 }

        em6AllPortSigCfgSetSigBitIndex   OBJECT-TYPE
            SYNTAX  INTEGER {
                    a(1),
                    b(2),
                    c(3),
                    d(4)
                }
            ACCESS  read-only
            STATUS  mandatory
            DESCRIPTION
                " Signaling Bit Index "
            ::= { em6AllPortSigCfgSetEntry 3 }

        em6AllPortSigCfgSetSigBit   OBJECT-TYPE
            SYNTAX  INTEGER {
                    zero(0),
                    one(1),
                    do-not-care(2)
                }
            ACCESS  read-write
            STATUS  mandatory
            DESCRIPTION
                " Signaling Bit Setup 0/1 or don't care "
            ::= { em6AllPortSigCfgSetEntry 4 }


--
--      E&M Per Port Diag InfoTable
--

        em6DiagInfoTable  OBJECT-TYPE
            SYNTAX  SEQUENCE OF Em6DiagInfoEntry
            ACCESS  not-accessible
            STATUS  mandatory
            DESCRIPTION
                "E&M Diag Info Table"
            ::= { em-card 10 }

        em6DiagInfoEntry  OBJECT-TYPE
            SYNTAX  Em6DiagInfoEntry
            ACCESS  not-accessible
            STATUS  mandatory
            DESCRIPTION
                "E&M Diag Infoentry"
            INDEX { em6DiagInfoIndex ,
                    em6DiagInfoPortIndex }
            ::= { em6DiagInfoTable 1 }

        Em6DiagInfoEntry ::= SEQUENCE {
            em6DiagInfoIndex              LSSlotID,
            em6DiagInfoPortIndex        PortID,
            em6DiagInfoSide           INTEGER,
            em6DiagInfoType             INTEGER,
            em6DiagInfoElead            EMOffOn,
            em6DiagInfoMlead           EMOffOn,
            em6DiagInfoAIS               EMOffOn,
            em6DiagInfoOOS              EMOffOn,
            em6DiagInfoInputPW        INTEGER,
            em6DiagInfoEleadPW       INTEGER,
            em6DiagInfoPWStatus      INTEGER,
            em6DiagInfoTx               DisplayString,
            em6DiagInfoRx              DisplayString
        }

        em6DiagInfoIndex  OBJECT-TYPE
            SYNTAX  LSSlotID
            ACCESS  read-only
            STATUS  mandatory
            DESCRIPTION
                "slot index"
            ::= { em6DiagInfoEntry 1 }

        em6DiagInfoPortIndex   OBJECT-TYPE
            SYNTAX  PortID
            ACCESS  read-only
            STATUS  mandatory
            DESCRIPTION
                "port 1-12"
            ::= { em6DiagInfoEntry 2 }

        em6DiagInfoSide   OBJECT-TYPE
            SYNTAX  INTEGER {
                    side-a(1),
                    side-b(2),
                    error(3)
                }
            ACCESS  read-only
            STATUS  mandatory
            DESCRIPTION
                " Side L1~L4 "
            ::= { em6DiagInfoEntry 3}

        em6DiagInfoType   OBJECT-TYPE
            SYNTAX  INTEGER {
                    tx-only(1),
                    type-1(2),
                    type-2(3),
                    type-3(4),
                    type-4(5),
                    type-5(6)
                }
            ACCESS  read-only
            STATUS  mandatory
            DESCRIPTION
                " signaling type"
            ::= { em6DiagInfoEntry 4}

        em6DiagInfoElead   OBJECT-TYPE
            SYNTAX  EMOffOn
            ACCESS  read-only
            STATUS  mandatory
            DESCRIPTION
                " E lead "
            ::= { em6DiagInfoEntry 5}

        em6DiagInfoMlead   OBJECT-TYPE
            SYNTAX  EMOffOn
            ACCESS  read-only
            STATUS  mandatory
            DESCRIPTION
                " M lead "
            ::= { em6DiagInfoEntry 6}

        em6DiagInfoAIS   OBJECT-TYPE
            SYNTAX  EMOffOn
            ACCESS  read-only
            STATUS  mandatory
            DESCRIPTION
                " AIS "
            ::= { em6DiagInfoEntry 7}

        em6DiagInfoOOS   OBJECT-TYPE
            SYNTAX  EMOffOn
            ACCESS  read-only
            STATUS  mandatory
            DESCRIPTION
                " OOS "
            ::= { em6DiagInfoEntry 8}

        em6DiagInfoInputPW   OBJECT-TYPE
            SYNTAX  INTEGER {
                    plusMinus48v(1),
                    plusMinus24v(2),
                    fail(3)
                }
            ACCESS  read-only
            STATUS  mandatory
            DESCRIPTION
                " Input power module"
            ::= { em6DiagInfoEntry 9}

        em6DiagInfoEleadPW   OBJECT-TYPE
            SYNTAX  INTEGER {
                    minus48v(1),
                    plus24v(2),
                    plus5v(3),
                    fail(4)
                }
            ACCESS  read-only
            STATUS  mandatory
            DESCRIPTION
                " e lead power "
            ::= { em6DiagInfoEntry 10}

        em6DiagInfoPWStatus   OBJECT-TYPE
            SYNTAX  INTEGER {
                    fail(1),
                    ok(2)
                }
            ACCESS  read-only
            STATUS  mandatory
            DESCRIPTION
                " Input power status"
            ::= { em6DiagInfoEntry 11}


        em6DiagInfoTx   OBJECT-TYPE
            SYNTAX  DisplayString (SIZE (0..255))
            ACCESS  read-only
            STATUS  mandatory
            DESCRIPTION
                " Per port TX-signal "
            ::= { em6DiagInfoEntry 12 }

        em6DiagInfoRx   OBJECT-TYPE
            SYNTAX  DisplayString (SIZE (0..255))
            ACCESS  read-only
            STATUS  mandatory
            DESCRIPTION
                " Per port RX-signal"
            ::= { em6DiagInfoEntry 13}




--
-- EM6 Line Diagnostic Control Table
--

        em6DiagControlTable  OBJECT-TYPE
            SYNTAX  SEQUENCE OF Em6DiagControlEntry
            ACCESS  not-accessible
            STATUS  mandatory
            DESCRIPTION
                "E&M6 Diagnostic Control Table."
            ::= { em-card 11 }

        em6DiagControlEntry  OBJECT-TYPE
            SYNTAX  Em6DiagControlEntry
            ACCESS  not-accessible
            STATUS  mandatory
            DESCRIPTION
                "An entry of E&M diagnostic control table."
            INDEX { em6DiagControlSlot }
            ::= { em6DiagControlTable 1 }

        Em6DiagControlEntry ::= SEQUENCE {
            em6DiagControlSlot          LSSlotID,
            em6DiagControlTest           INTEGER,
            em6DiagControlRemain           INTEGER

    }

        em6DiagControlSlot  OBJECT-TYPE
            SYNTAX  LSSlotID
            ACCESS  read-only
            STATUS  mandatory
            DESCRIPTION
                "slot index"
            ::= { em6DiagControlEntry 1 }

        em6DiagControlTest  OBJECT-TYPE
            SYNTAX  INTEGER {
                    stop(1),
                    e-lead(2),
                    voice-loopback(3),
                    channel-swap(4)
                }
            ACCESS  read-write
            STATUS  mandatory
            DESCRIPTION
                "E&M  Test Button"
            ::= { em6DiagControlEntry 2 }

        em6DiagControlRemain  OBJECT-TYPE
            SYNTAX  INTEGER
            ACCESS  read-only
            STATUS  mandatory
            DESCRIPTION
                "remain time"
            ::= { em6DiagControlEntry 3 }


--
--      EMA Per Port Enable/Disable Control Table
--

        emaPortEnableTable  OBJECT-TYPE
            SYNTAX  SEQUENCE OF EmaPortEnableEntry
            ACCESS  not-accessible
            STATUS  mandatory
            DESCRIPTION
                "EMA Per Port Enable Table"
            ::= { em-card 14 }

        emaPortEnableEntry  OBJECT-TYPE
            SYNTAX  EmaPortEnableEntry
            ACCESS  not-accessible
            STATUS  mandatory
            DESCRIPTION
                "EMA Per Port Enable entry"
            INDEX { emaPortEnableIndex ,
        emaPortEnablePort }
            ::= { emaPortEnableTable 1 }

            EmaPortEnableEntry ::= SEQUENCE {
            emaPortEnableIndex      LSSlotID,
            emaPortEnablePort       PortID,
            emaPortEnable           INTEGER
        }

        emaPortEnableIndex  OBJECT-TYPE
            SYNTAX  LSSlotID
            ACCESS  read-only
            STATUS  mandatory
            DESCRIPTION
            "slot index"
            ::= { emaPortEnableEntry 1 }

        emaPortEnablePort   OBJECT-TYPE
            SYNTAX  PortID
            ACCESS  read-only
            STATUS  mandatory
            DESCRIPTION
                "port 1-12"
            ::= { emaPortEnableEntry 2 }

        emaPortEnable   OBJECT-TYPE
            SYNTAX  INTEGER   {
                    disable(1),
                    enable(2)
                }
            ACCESS  read-write
            STATUS  mandatory
            DESCRIPTION
                " port enable/disable"
            ::= { emaPortEnableEntry 3 }

        emTotalCard   OBJECT-TYPE
            SYNTAX  INTEGER
            ACCESS  read-only
            STATUS  mandatory
            DESCRIPTION
                "Total cards of E&M"
            ::= { em-card 100 }


--======================================================================--
--======================================================================--
--  fxs-card MIB
--======================================================================--
-- FXS Card

--      fxsAllPortConfigTable        OBJECT IDENTIFIER ::= { fxs-card 1 }
--      fxsAllPortSigConfigTable     OBJECT IDENTIFIER ::= { fxs-card 2 }
--      fxsPerPortConfigTable        OBJECT IDENTIFIER ::= { fxs-card 3 }
--      fxsPortStatusTable           OBJECT IDENTIFIER ::= { fxs-card 4 }
--      fxsDiagTestControlTable      OBJECT IDENTIFIER ::= { fxs-card 5 }
--      fxsCommandControlTable       OBJECT IDENTIFIER ::= { fxs-card 6 }
--======================================================================--


--
--      FXS All Port Config Control Table
--

        fxsAllPortConfigTable  OBJECT-TYPE
            SYNTAX  SEQUENCE OF FxsAllPortConfigEntry
            ACCESS  not-accessible
            STATUS  mandatory
            DESCRIPTION
                "FXS All Port Configuration Control Table"
            ::= { fxs-card 1 }

        fxsAllPortConfigEntry  OBJECT-TYPE
            SYNTAX  FxsAllPortConfigEntry
            ACCESS  not-accessible
            STATUS  mandatory
            DESCRIPTION
                "FXS all port configuration control entry"
            INDEX { fxsAllPortConfigIndex }
            ::= { fxsAllPortConfigTable 1 }

        FxsAllPortConfigEntry ::= SEQUENCE {
            fxsAllPortConfigIndex       LSSlotID,
            fxsAllPortConfigA-u-law     INTEGER,
            fxsAllPortConfigImpedance   INTEGER,
--             fxsAllPortConfigTx-gain
--               DisplayString,
--             fxsAllPortConfigRx-gain
--               DisplayString,
            fxsAllPortConfigRing-cadence    INTEGER,
            fxsAllPortConfigRing-Freq       INTEGER,
            fxsAllPortConfigMetering-pulse  INTEGER,
            fxsAllPortConfigMetering-freq   INTEGER,
            fxsAllPortConfigMetering-level  INTEGER
        }

        fxsAllPortConfigIndex  OBJECT-TYPE
            SYNTAX  LSSlotID
            ACCESS  read-only
            STATUS  mandatory
            DESCRIPTION
                "FXS slot"
            ::= { fxsAllPortConfigEntry 1 }

        fxsAllPortConfigA-u-law   OBJECT-TYPE
            SYNTAX  INTEGER {
                    u-law(1),
                    a-law(2)
                }
            ACCESS  read-write
            STATUS  mandatory
            DESCRIPTION
                " A/u LAW "
            ::= { fxsAllPortConfigEntry 2 }

        fxsAllPortConfigImpedance   OBJECT-TYPE
            SYNTAX  INTEGER {
                    imp-900-ohm(1),
                    imp-600-ohm(2)
                }
            ACCESS  read-write
            STATUS  mandatory
            DESCRIPTION
                " IMPEDANCE "
            ::= { fxsAllPortConfigEntry 3 }

--       fxsAllPortConfigTx-gain   OBJECT-TYPE
--           SYNTAX  DisplayString (SIZE (0..255))
--           ACCESS  read-write
--           STATUS  mandatory
--           DESCRIPTION
--              " TX-GAIN "
--           ::= { fxsAllPortConfigEntry 4 }

--       fxsAllPortConfigRx-gain   OBJECT-TYPE
--           SYNTAX  DisplayString (SIZE (0..255))
--           ACCESS  read-write
--           STATUS  mandatory
--           DESCRIPTION
--              " RX-GAIN "
--           ::= { fxsAllPortConfigEntry 5 }

        fxsAllPortConfigRing-cadence   OBJECT-TYPE
            SYNTAX  INTEGER {
                    cadence-1-on-2-off(1),
                    cadence-2-on-4-off(2)
                }
            ACCESS  read-write
            STATUS  mandatory
            DESCRIPTION
                " Ring Cadence "
            ::= { fxsAllPortConfigEntry 6 }

        fxsAllPortConfigRing-Freq   OBJECT-TYPE
            SYNTAX  INTEGER {
                    freq-20-hz(1),
                    freq-25-hz(2),
                    freq-16-7-hz(3),
                    freq-50-hz(4)
                }
            ACCESS  read-write
            STATUS  mandatory
            DESCRIPTION
                " Ring Frequency "
            ::= { fxsAllPortConfigEntry 7 }

        fxsAllPortConfigMetering-pulse   OBJECT-TYPE
            SYNTAX  INTEGER {
                    off(1),
                    on(2),
                    unavail(3)
                }
            ACCESS  read-write
            STATUS  mandatory
            DESCRIPTION
                " Metering Pulse "
            ::= { fxsAllPortConfigEntry 8 }

        fxsAllPortConfigMetering-freq   OBJECT-TYPE
            SYNTAX  INTEGER {
                    freq-16k-hz(1),
                    freq-12k-hz(2),
                    unavail(3)
                }
            ACCESS  read-write
            STATUS  mandatory
            DESCRIPTION
                " Metering Frequency "
            ::= { fxsAllPortConfigEntry 9 }

        fxsAllPortConfigMetering-level   OBJECT-TYPE
            SYNTAX  INTEGER {
                    level-2-4-vrms(1),
                    level-1-vrms(2),
                    unavail(3)
                }
            ACCESS  read-write
            STATUS  mandatory
            DESCRIPTION
                " Metering Level "
            ::= { fxsAllPortConfigEntry 10 }



--
--      FXS All Port Signaling Config Control Table
--

        fxsAllPortSigConfigTable  OBJECT-TYPE
            SYNTAX  SEQUENCE OF FxsAllPortSigConfigEntry
            ACCESS  not-accessible
            STATUS  mandatory
            DESCRIPTION
                "FXS All Port Signaling Configuration Control Table"
            ::= { fxs-card 2 }

        fxsAllPortSigConfigEntry  OBJECT-TYPE
            SYNTAX  FxsAllPortSigConfigEntry
            ACCESS  not-accessible
            STATUS  mandatory
            DESCRIPTION
                "FXS all port signaling configuration control entry"
            INDEX { fxsAllPortSigConfigIndex ,
                    fxsAllPortSigConfigItemIndex ,
                    fxsAllPortSigConfigSigBitIndex }
            ::= { fxsAllPortSigConfigTable 1 }

        FxsAllPortSigConfigEntry ::= SEQUENCE {
            fxsAllPortSigConfigIndex    LSSlotID,
            fxsAllPortSigConfigItemIndex    INTEGER,
            fxsAllPortSigConfigSigBitIndex  INTEGER,
            fxsAllPortSigConfigSigBit       INTEGER
        }

        fxsAllPortSigConfigIndex  OBJECT-TYPE
            SYNTAX  LSSlotID
            ACCESS  read-only
            STATUS  mandatory
            DESCRIPTION
                "slot index"
            ::= { fxsAllPortSigConfigEntry 1 }

        fxsAllPortSigConfigItemIndex   OBJECT-TYPE
            SYNTAX  INTEGER {
                    tx-on-hook(1),
                    tx-off-hook(2),
                    tx-ring-gnd(3),
                    plar-tx-off-hook(4),
                    rx-ring-on(5),
                    rx-batt-rev-and-pulse-on(6),
                    rx-oos-alarm(7),
                    rx-tip-open(8),
                    rx-plar-rx-ring-on(9)
                }
            ACCESS  read-only
            STATUS  mandatory
            DESCRIPTION
                "on-hook, off-hook, ring-gnd, ring-on, batt-rev-pulse-on, oos-on, tip-open"
            ::= { fxsAllPortSigConfigEntry 2 }

        fxsAllPortSigConfigSigBitIndex   OBJECT-TYPE
            SYNTAX  INTEGER {
                    a(1),
                    b(2),
                    c(3),
                    d(4)
                }
            ACCESS  read-only
            STATUS  mandatory
            DESCRIPTION
                " Signaling Bit Index "
            ::= { fxsAllPortSigConfigEntry 3 }

        fxsAllPortSigConfigSigBit   OBJECT-TYPE
            SYNTAX  INTEGER {
                    zero(0),
                    one(1),
                    do-not-care(2)
                }
            ACCESS  read-write
            STATUS  mandatory
            DESCRIPTION
                " Signaling Bit Setup 0/1 or don't care "
            ::= { fxsAllPortSigConfigEntry 4 }



--
--      FXS Per Port Config Control Table
--

        fxsPerPortConfigTable  OBJECT-TYPE
            SYNTAX  SEQUENCE OF FxsPerPortConfigEntry
            ACCESS  not-accessible
            STATUS  mandatory
            DESCRIPTION
                "FXS Per Port Configuration Control Table"
            ::= { fxs-card 3 }

        fxsPerPortConfigEntry  OBJECT-TYPE
            SYNTAX  FxsPerPortConfigEntry
            ACCESS  not-accessible
            STATUS  mandatory
            DESCRIPTION
                "FXS Per Port Configuration control entry"
            INDEX { fxsPerPortConfigIndex ,
                    fxsPerPortConfigPortIndex }
            ::= { fxsPerPortConfigTable 1 }

        FxsPerPortConfigEntry ::= SEQUENCE {
            fxsPerPortConfigIndex       LSSlotID,
            fxsPerPortConfigPortIndex   PortID,
            fxsPerPortConfigPLAR        INTEGER,
            fxsPerPortConfigTx-gain     DisplayString,
            fxsPerPortConfigRx-gain     DisplayString
        }

        fxsPerPortConfigIndex  OBJECT-TYPE
            SYNTAX  LSSlotID
            ACCESS  read-only
            STATUS  mandatory
            DESCRIPTION
                "slot index"
            ::= { fxsPerPortConfigEntry 1 }

        fxsPerPortConfigPortIndex   OBJECT-TYPE
            SYNTAX  PortID
            ACCESS  read-only
            STATUS  mandatory
            DESCRIPTION
                "port 1-12"
            ::= { fxsPerPortConfigEntry 2 }

        fxsPerPortConfigPLAR   OBJECT-TYPE
            SYNTAX INTEGER {
                    off(1),
                    on(2)
                }
            ACCESS  read-write
            STATUS  mandatory
            DESCRIPTION
                " Per port PLAR setting "
            ::= { fxsPerPortConfigEntry 3 }

        fxsPerPortConfigTx-gain   OBJECT-TYPE
            SYNTAX  DisplayString (SIZE (0..255))
            ACCESS  read-write
            STATUS  mandatory
            DESCRIPTION
                " Per port TX-GAIN setting "
            ::= { fxsPerPortConfigEntry 4 }

        fxsPerPortConfigRx-gain   OBJECT-TYPE
            SYNTAX  DisplayString (SIZE (0..255))
            ACCESS  read-write
            STATUS  mandatory
            DESCRIPTION
                " Per port RX-GAIN setting "
            ::= { fxsPerPortConfigEntry 5 }


--
--      FXS Port Status Table
--

        fxsPortStatusTable  OBJECT-TYPE
            SYNTAX  SEQUENCE OF FxsPortStatusEntry
            ACCESS  not-accessible
            STATUS  mandatory
            DESCRIPTION
                "FXS Port Status Table"
            ::= { fxs-card 4 }

        fxsPortStatusEntry  OBJECT-TYPE
            SYNTAX  FxsPortStatusEntry
            ACCESS  not-accessible
            STATUS  mandatory
            DESCRIPTION
                "FXS Port Status entry"
            INDEX { fxsPortStatusIndex ,
                    fxsPortStatusItemIndex ,
                    fxsPortStatusPortIndex }
            ::= { fxsPortStatusTable 1 }

        FxsPortStatusEntry ::= SEQUENCE {
            fxsPortStatusIndex          LSSlotID,
            fxsPortStatusItemIndex      INTEGER,
            fxsPortStatusPortIndex      PortID,
            fxsPortStatusStatus         INTEGER
        }

        fxsPortStatusIndex  OBJECT-TYPE
            SYNTAX  LSSlotID
            ACCESS  read-only
            STATUS  mandatory
            DESCRIPTION
                "slot index"
            ::= { fxsPortStatusEntry 1 }

        fxsPortStatusItemIndex   OBJECT-TYPE
            SYNTAX  INTEGER {
                    off-hook(1),
                    metering-pulse(2),
                    tip-open(3),
                    ring-gnd(4),
                    plar-on(5),
                    ringing(6),
                    alarm-on(7)
                }
            ACCESS  read-only
            STATUS  mandatory
            DESCRIPTION
                "off-hook, ring-on, metering-pulse, tip-open, ring-gnd, plar-on, alarm-on"
            ::= { fxsPortStatusEntry 2 }

        fxsPortStatusPortIndex   OBJECT-TYPE
            SYNTAX  PortID
            ACCESS  read-only
            STATUS  mandatory
            DESCRIPTION
                " port index 1-12 "
            ::= { fxsPortStatusEntry 3 }

        fxsPortStatusStatus   OBJECT-TYPE
            SYNTAX  INTEGER {
                    no(1),
                    yes(2)
                }
            ACCESS  read-only
            STATUS  mandatory
            DESCRIPTION
                " Port Status "
            ::= { fxsPortStatusEntry 4 }


--
--      FXS Line Diagnostic Control Table
--

        fxsDiagTestControlTable  OBJECT-TYPE
            SYNTAX  SEQUENCE OF FxsDiagTestControlEntry
            ACCESS  not-accessible
            STATUS  mandatory
            DESCRIPTION
                "FXS Diagnostic Control Table."
            ::= { fxs-card 5 }

        fxsDiagTestControlEntry  OBJECT-TYPE
            SYNTAX  FxsDiagTestControlEntry
            ACCESS  not-accessible
            STATUS  mandatory
            DESCRIPTION
                "An entry of FXS diagnostic control table."
            INDEX { fxsDiagTestControlIndex }
            ::= { fxsDiagTestControlTable 1 }

        FxsDiagTestControlEntry ::= SEQUENCE {
            fxsDiagTestControlIndex     LSSlotID,
            fxsDiagTestControlType      INTEGER,
            fxsDiagTestControlRemainTime    INTEGER,
            fxsDiagTestControlTone      INTEGER,
            fxsDiagTestControlToneResult DisplayString
        }

        fxsDiagTestControlIndex  OBJECT-TYPE
            SYNTAX  LSSlotID
            ACCESS  read-only
            STATUS  mandatory
            DESCRIPTION
                "slot index"
            ::= { fxsDiagTestControlEntry 1 }

        fxsDiagTestControlType  OBJECT-TYPE
            SYNTAX  INTEGER {
                    stop(1),
                    ring-test(2),
--                      metering-pulse-test(3),
                    battery-reverse(4),
-- fxs dtmf
                    tone-test(5)
                }
            ACCESS  read-write
            STATUS  mandatory
            DESCRIPTION
                "FXS Test Button"
            ::= { fxsDiagTestControlEntry 2 }

        fxsDiagTestControlRemainTime  OBJECT-TYPE
            SYNTAX  INTEGER
            ACCESS  read-only
            STATUS  mandatory
            DESCRIPTION
                "Remain time (sec)"
            ::= { fxsDiagTestControlEntry 3 }

        fxsDiagTestControlTone  OBJECT-TYPE
            SYNTAX  INTEGER {
                    n1(2),
                    n2(3),
                    n3(4),
                    n4(5),
                    n5(6),
                    n6(7),
                    n7(8),
                    n8(9),
                    n9(10),
                    n0(11),
                    asterisk(12),
                    pound(13),
                    a(14),
                    b(15),
                    c(16),
                    d(1)

                }
            ACCESS  read-write
            STATUS  mandatory
            DESCRIPTION
                "FXS Test Tone"
            ::= { fxsDiagTestControlEntry 4 }

        fxsDiagTestControlToneResult  OBJECT-TYPE
            SYNTAX  DisplayString (SIZE (0..30) )
            ACCESS  read-only
            STATUS  mandatory
            DESCRIPTION
                "FXS Test Tone Result"
            ::= { fxsDiagTestControlEntry 5 }

--
--  FXS Command Control Table
--

        fxsCommandControlTable  OBJECT-TYPE
            SYNTAX  SEQUENCE OF FxsCommandControlEntry
            ACCESS  not-accessible
            STATUS  mandatory
            DESCRIPTION
                "The command control table."
            ::= { fxs-card 6 }

        fxsCommandControlEntry  OBJECT-TYPE
            SYNTAX  FxsCommandControlEntry
            ACCESS  not-accessible
            STATUS  mandatory
            DESCRIPTION
                "An entry in the command control table."
            INDEX { fxsCommandControlIndex }
            ::= { fxsCommandControlTable 1 }

        FxsCommandControlEntry ::= SEQUENCE {
            fxsCommandControlIndex      LSSlotID,
            fxsCommandControlReset      INTEGER,
            fxsCommandControlLoadDefault    INTEGER
        }

        fxsCommandControlIndex  OBJECT-TYPE
            SYNTAX  LSSlotID
            ACCESS  read-only
            STATUS  mandatory
            DESCRIPTION
                "slot index"
            ::= { fxsCommandControlEntry 1 }

        fxsCommandControlLoadDefault    OBJECT-TYPE
            SYNTAX  INTEGER {
                    load-default(1)
                }
            ACCESS  read-write
            STATUS  mandatory
            DESCRIPTION
                "Command: Load Default FXS CONF"
            ::= { fxsCommandControlEntry 2 }

        fxsCommandControlReset    OBJECT-TYPE
            SYNTAX  INTEGER {
                    reset(1)
                }
            ACCESS  read-write
            STATUS  mandatory
            DESCRIPTION
                "Command: FXS Card Reset"
            ::= { fxsCommandControlEntry 3 }

--
--      FXS Per Port Enable/Disable Control Table
--

        fxsPerPortEnableTable  OBJECT-TYPE
            SYNTAX  SEQUENCE OF FxsPerPortEnableEntry
            ACCESS  not-accessible
            STATUS  mandatory
            DESCRIPTION
                "FXS Per Port Enable Table"
            ::= { fxs-card 7 }

        fxsPerPortEnableEntry  OBJECT-TYPE
            SYNTAX  FxsPerPortEnableEntry
            ACCESS  not-accessible
            STATUS  mandatory
            DESCRIPTION
                "FXS Per Port Enable entry"
            INDEX { fxsPerPortEnableIndex ,
        fxsPerPortEnablePortIndex }
            ::= { fxsPerPortEnableTable 1 }

            FxsPerPortEnableEntry ::= SEQUENCE {
            fxsPerPortEnableIndex      LSSlotID,
            fxsPerPortEnablePortIndex  PortID,
            fxsPerPortEnable           INTEGER
        }

        fxsPerPortEnableIndex  OBJECT-TYPE
            SYNTAX  LSSlotID
            ACCESS  read-only
            STATUS  mandatory
            DESCRIPTION
            "slot index"
            ::= { fxsPerPortEnableEntry 1 }

        fxsPerPortEnablePortIndex   OBJECT-TYPE
            SYNTAX  PortID
            ACCESS  read-only
            STATUS  mandatory
            DESCRIPTION
                "port 1-12"
            ::= { fxsPerPortEnableEntry 2 }

        fxsPerPortEnable   OBJECT-TYPE
            SYNTAX  INTEGER   {
                    disable(1),
                    enable(2)
                }
            ACCESS  read-write
            STATUS  mandatory
            DESCRIPTION
                "FXS port enable/disable"
            ::= { fxsPerPortEnableEntry 3 }


        fxsTotalCard   OBJECT-TYPE
            SYNTAX  INTEGER
            ACCESS  read-only
            STATUS  mandatory
            DESCRIPTION
                "Total cards of FXS"
            ::= { fxs-card 100 }


--======================================================================--
--======================================================================--
--  fxo-card MIB
--======================================================================--
-- FXO Card

--      fxoAllPortConfigTable        OBJECT IDENTIFIER ::= { fxo-card 1 }
--      fxoAllPortSigConfigTable     OBJECT IDENTIFIER ::= { fxo-card 2 }
--      fxoPerPortConfigTable        OBJECT IDENTIFIER ::= { fxo-card 3 }
--      fxoPortStatusTable           OBJECT IDENTIFIER ::= { fxo-card 4 }
--      fxoDiagTestControlTable      OBJECT IDENTIFIER ::= { fxo-card 5 }
--      fxoCommandControlTable       OBJECT IDENTIFIER ::= { fxo-card 6 }
--======================================================================--

            FXOPulseDecodeLevel ::= INTEGER   {
        na(0),
--                      neg-18-dbm(18),
        neg-19-dbm(19),
        neg-20-dbm(20),
        neg-21-dbm(21),
        neg-22-dbm(22),
        neg-23-dbm(23),
        neg-24-dbm(24),
        neg-25-dbm(25),
        neg-26-dbm(26),
        neg-27-dbm(27),
        neg-28-dbm(28),
        neg-29-dbm(29),
        neg-30-dbm(30),
        neg-31-dbm(31),
        neg-32-dbm(32),
        neg-33-dbm(33),
        neg-34-dbm(34),
        neg-35-dbm(35),
        neg-36-dbm(36),
        neg-37-dbm(37),
        neg-38-dbm(38),
        neg-39-dbm(39),
        neg-40-dbm(40),
        neg-41-dbm(41),
        neg-42-dbm(42),
        neg-43-dbm(43),
        neg-44-dbm(44),
        neg-45-dbm(45),
        neg-46-dbm(46),
        neg-47-dbm(47)
    }

--
--      FXO All Port Config Control Table
--

        fxoAllPortConfigTable  OBJECT-TYPE
            SYNTAX  SEQUENCE OF FxoAllPortConfigEntry
            ACCESS  not-accessible
            STATUS  mandatory
            DESCRIPTION
                "FXO All Port Configuration Control Table"
            ::= { fxo-card 1 }

        fxoAllPortConfigEntry  OBJECT-TYPE
            SYNTAX  FxoAllPortConfigEntry
            ACCESS  not-accessible
            STATUS  mandatory
            DESCRIPTION
                "FXO all port configuration control entry"
            INDEX { fxoAllPortConfIndex }
            ::= { fxoAllPortConfigTable 1 }

        FxoAllPortConfigEntry ::= SEQUENCE {
            fxoAllPortConfIndex         LSSlotID,
            fxoAllPortConfA-u-law       INTEGER,
            fxoAllPortConfImpedance     INTEGER,
--             fxoAllPortConfTx-gain
--               DisplayString,
--             fxoAllPortConfRx-gain
--               DisplayString,
            fxoAllPortConfTrunkCond     INTEGER,
            fxoAllPortConfLinePolarity  INTEGER,
            fxoAllPortConfMeterPulseFreq    INTEGER,
            fxoAllPortConfPulseDetectMode   INTEGER
        }

        fxoAllPortConfIndex  OBJECT-TYPE
            SYNTAX  LSSlotID
            ACCESS  read-only
            STATUS  mandatory
            DESCRIPTION
                "FXO slot"
            ::= { fxoAllPortConfigEntry 1 }

        fxoAllPortConfA-u-law   OBJECT-TYPE
            SYNTAX  INTEGER {
                    u-law(1),
                    a-law(2)
                }
            ACCESS  read-write
            STATUS  mandatory
            DESCRIPTION
                " A/u LAW "
            ::= { fxoAllPortConfigEntry 2 }

        fxoAllPortConfImpedance   OBJECT-TYPE
            SYNTAX  INTEGER {
                    imp-900-ohm(1),
                    imp-600-ohm(2)
                }
            ACCESS  read-write
            STATUS  mandatory
            DESCRIPTION
                " IMPEDANCE "
            ::= { fxoAllPortConfigEntry 3 }

--       fxoAllPortConfTx-gain   OBJECT-TYPE
--           SYNTAX  DisplayString (SIZE (0..255))
--           ACCESS  read-write
--           STATUS  mandatory
--           DESCRIPTION
--              " TX-GAIN "
--           ::= { fxoAllPortConfigEntry 4 }

--       fxoAllPortConfRx-gain   OBJECT-TYPE
--           SYNTAX  DisplayString (SIZE (0..255))
--           ACCESS  read-write
--           STATUS  mandatory
--           DESCRIPTION
--              " RX-GAIN "
--           ::= { fxoAllPortConfigEntry 5 }

        fxoAllPortConfTrunkCond   OBJECT-TYPE
            SYNTAX  INTEGER {
                    on-hook(1),
                    off-hook(2),
                    unavail(3)
                }
            ACCESS  read-write
            STATUS  mandatory
            DESCRIPTION
                " Trunk Condition "
            ::= { fxoAllPortConfigEntry 6 }

        fxoAllPortConfLinePolarity   OBJECT-TYPE
            SYNTAX  INTEGER {
                    reverse(1),
                    normal(2),
                    unavail(3)
                }
            ACCESS  read-write
            STATUS  mandatory
            DESCRIPTION
                " Line Polarity "
            ::= { fxoAllPortConfigEntry 7 }

        fxoAllPortConfMeterPulseFreq   OBJECT-TYPE
            SYNTAX  INTEGER {
                    freq-16k-hz(1),
                    freq-12k-hz(2),
                    unavail(3)
                }
            ACCESS  read-write
            STATUS  mandatory
            DESCRIPTION
                " Metering Pulse Frequency "
            ::= { fxoAllPortConfigEntry 8 }

        fxoAllPortConfPulseDetectMode   OBJECT-TYPE
            SYNTAX  INTEGER {
                    packet(1),
                    normal(2),
                    unavail(3)
                }
            ACCESS  read-write
            STATUS  mandatory
            DESCRIPTION
                " Pulse Detect Mode "
            ::= { fxoAllPortConfigEntry 9 }



--
--      FXO All Port Signaling Config Control Table
--

        fxoAllPortSigConfigTable  OBJECT-TYPE
            SYNTAX  SEQUENCE OF FxoAllPortSigConfigEntry
            ACCESS  not-accessible
            STATUS  mandatory
            DESCRIPTION
                "FXO All Port Signaling Configuration Control Table"
            ::= { fxo-card 2 }

        fxoAllPortSigConfigEntry  OBJECT-TYPE
            SYNTAX  FxoAllPortSigConfigEntry
            ACCESS  not-accessible
            STATUS  mandatory
            DESCRIPTION
                "FXO all port signaling configuration control entry"
            INDEX { fxoAllPortSigConfigIndex ,
                    fxoAllPortSigConfigItemIndex ,
                    fxoAllPortSigConfigSigBitIndex }
            ::= { fxoAllPortSigConfigTable 1 }

        FxoAllPortSigConfigEntry ::= SEQUENCE {
            fxoAllPortSigConfigIndex    LSSlotID,
            fxoAllPortSigConfigItemIndex    INTEGER,
            fxoAllPortSigConfigSigBitIndex  INTEGER,
            fxoAllPortSigConfigSigBit       INTEGER
        }

        fxoAllPortSigConfigIndex  OBJECT-TYPE
            SYNTAX  LSSlotID
            ACCESS  read-only
            STATUS  mandatory
            DESCRIPTION
                "slot index"
            ::= { fxoAllPortSigConfigEntry 1 }

        fxoAllPortSigConfigItemIndex   OBJECT-TYPE
            SYNTAX  INTEGER {
                    ringing(1),
                    no-ring(2),
                    batt-rev(3),
                    pulse-on(4),
                    tip-open(5),
                    off-hook(6),
                    oos-alarm(7),
                    ring-gnd(8)
                }
            ACCESS  read-only
            STATUS  mandatory
            DESCRIPTION
                " ringing, no-ring, batt-rev, pulse-on, tip-open, off-hook, oos-on, ring-gnd "
            ::= { fxoAllPortSigConfigEntry 2 }

        fxoAllPortSigConfigSigBitIndex   OBJECT-TYPE
            SYNTAX  INTEGER {
                    a(1),
                    b(2),
                    c(3),
                    d(4)
                }
            ACCESS  read-only
            STATUS  mandatory
            DESCRIPTION
                " Signaling Bit Index "
            ::= { fxoAllPortSigConfigEntry 3 }

        fxoAllPortSigConfigSigBit   OBJECT-TYPE
            SYNTAX  INTEGER {
                    zero(0),
                    one(1),
                    do-not-care(2)
                }
            ACCESS  read-write
            STATUS  mandatory
            DESCRIPTION
                " Signaling Bit Setup 0/1 or don't care "
            ::= { fxoAllPortSigConfigEntry 4 }



--
--      FXO Per Port Config Control Table
--

        fxoPerPortConfigTable  OBJECT-TYPE
            SYNTAX  SEQUENCE OF FxoPerPortConfigEntry
            ACCESS  not-accessible
            STATUS  mandatory
            DESCRIPTION
                "FXO Per Port Configuration Control Table"
            ::= { fxo-card 3 }

        fxoPerPortConfigEntry  OBJECT-TYPE
            SYNTAX  FxoPerPortConfigEntry
            ACCESS  not-accessible
            STATUS  mandatory
            DESCRIPTION
                "FXO Per Port Configuration control entry"
            INDEX { fxoPerPortConfIndex ,
                    fxoPerPortConfPortIndex }
            ::= { fxoPerPortConfigTable 1 }

        FxoPerPortConfigEntry ::= SEQUENCE {
            fxoPerPortConfIndex         LSSlotID,
            fxoPerPortConfPortIndex     PortID,
            fxoPerPortConfPulseDecodeLv FXOPulseDecodeLevel,
            fxoPerPortConfDetPulseDecodeLv  FXOPulseDecodeLevel,
            fxoPerPortConfTx-gain           DisplayString,
            fxoPerPortConfRx-gain           DisplayString
        }

        fxoPerPortConfIndex  OBJECT-TYPE
            SYNTAX  LSSlotID
            ACCESS  read-only
            STATUS  mandatory
            DESCRIPTION
                "slot index"
            ::= { fxoPerPortConfigEntry 1 }

        fxoPerPortConfPortIndex   OBJECT-TYPE
            SYNTAX  PortID
            ACCESS  read-only
            STATUS  mandatory
            DESCRIPTION
                "port 1-12"
            ::= { fxoPerPortConfigEntry 2 }

        fxoPerPortConfPulseDecodeLv   OBJECT-TYPE
            SYNTAX  FXOPulseDecodeLevel
            ACCESS  read-write
            STATUS  mandatory
            DESCRIPTION
                " Per port Pulse Decode Level setting "
            ::= { fxoPerPortConfigEntry 3 }

        fxoPerPortConfDetPulseDecodeLv   OBJECT-TYPE
            SYNTAX  FXOPulseDecodeLevel
            ACCESS  read-only
            STATUS  mandatory
            DESCRIPTION
                " Detected Pulse Decode Level by Pulse Decode Level Scan "
            ::= { fxoPerPortConfigEntry 4 }

        fxoPerPortConfTx-gain   OBJECT-TYPE
            SYNTAX  DisplayString (SIZE (0..255))
            ACCESS  read-write
            STATUS  mandatory
            DESCRIPTION
                " Per port TX-GAIN setting "
            ::= { fxoPerPortConfigEntry 5 }

        fxoPerPortConfRx-gain   OBJECT-TYPE
            SYNTAX  DisplayString (SIZE (0..255))
            ACCESS  read-write
            STATUS  mandatory
            DESCRIPTION
                " Per port RX-GAIN setting "
            ::= { fxoPerPortConfigEntry 6 }


--
--      FXO Port Status Table
--

        fxoPortStatusTable  OBJECT-TYPE
            SYNTAX  SEQUENCE OF FxoPortStatusEntry
            ACCESS  not-accessible
            STATUS  mandatory
            DESCRIPTION
                "FXO Port Status Table"
            ::= { fxo-card 4 }

        fxoPortStatusEntry  OBJECT-TYPE
            SYNTAX  FxoPortStatusEntry
            ACCESS  not-accessible
            STATUS  mandatory
            DESCRIPTION
                "FXO Port Status entry"
            INDEX { fxoPortStatusIndex ,
                    fxoPortStatusItemIndex ,
                    fxoPortStatusPortIndex }
            ::= { fxoPortStatusTable 1 }

        FxoPortStatusEntry ::= SEQUENCE {
            fxoPortStatusIndex          LSSlotID,
            fxoPortStatusItemIndex      INTEGER,
            fxoPortStatusPortIndex      PortID,
            fxoPortStatusStatus         INTEGER
        }

        fxoPortStatusIndex  OBJECT-TYPE
            SYNTAX  LSSlotID
            ACCESS  read-only
            STATUS  mandatory
            DESCRIPTION
                "slot index"
            ::= { fxoPortStatusEntry 1 }

        fxoPortStatusItemIndex   OBJECT-TYPE
            SYNTAX  INTEGER {
                    ringing(1),
                    off-hook(2),
                    tip-open(3),
                    line-broken(4),
                    ring-gnd(5),
                    batt-rev(6),
                    pulse-on(7),
                    alarm-on(8)
                }
            ACCESS  read-only
            STATUS  mandatory
            DESCRIPTION
                "ringing, off-hook, tip-open, line-broken, ring-gnd, batt-rev, pulse-on, alarm-on"
            ::= { fxoPortStatusEntry 2 }

        fxoPortStatusPortIndex   OBJECT-TYPE
            SYNTAX  PortID
            ACCESS  read-only
            STATUS  mandatory
            DESCRIPTION
                " port index 1-12 "
            ::= { fxoPortStatusEntry 3 }

        fxoPortStatusStatus   OBJECT-TYPE
            SYNTAX  INTEGER {
                    no(1),
                    yes(2)
                }
            ACCESS  read-only
            STATUS  mandatory
            DESCRIPTION
                " Port Status "
            ::= { fxoPortStatusEntry 4 }


--
--      FXO Line Diagnostic Control Table
--

        fxoDiagTestControlTable  OBJECT-TYPE
            SYNTAX  SEQUENCE OF FxoDiagTestControlEntry
            ACCESS  not-accessible
            STATUS  mandatory
            DESCRIPTION
                "FXO Diagnostic Control Table."
            ::= { fxo-card 5 }

        fxoDiagTestControlEntry  OBJECT-TYPE
            SYNTAX  FxoDiagTestControlEntry
            ACCESS  not-accessible
            STATUS  mandatory
            DESCRIPTION
                "An entry of FXO diagnostic control table."
            INDEX { fxoDiagTestControlIndex }
            ::= { fxoDiagTestControlTable 1 }

        FxoDiagTestControlEntry ::= SEQUENCE {
            fxoDiagTestControlIndex     LSSlotID,
            fxoDiagTestControlType      INTEGER,
            fxoDiagTestControlRemainTime    INTEGER
        }

        fxoDiagTestControlIndex  OBJECT-TYPE
            SYNTAX  LSSlotID
            ACCESS  read-only
            STATUS  mandatory
            DESCRIPTION
                "slot index"
            ::= { fxoDiagTestControlEntry 1 }

        fxoDiagTestControlType  OBJECT-TYPE
            SYNTAX  INTEGER {
                    stop(1),
                    off-hook-test(2),
                    pulse-decode-level-scan(3),
                    apply-detected-pulse-decode-level(11)
                }
            ACCESS  read-write
            STATUS  mandatory
            DESCRIPTION
                "FXO Test Button"
            ::= { fxoDiagTestControlEntry 2 }

        fxoDiagTestControlRemainTime  OBJECT-TYPE
            SYNTAX  INTEGER
            ACCESS  read-only
            STATUS  mandatory
            DESCRIPTION
                "Remain time (sec)"
            ::= { fxoDiagTestControlEntry 3 }



--
--  FXO Command Control Table
--

        fxoCommandControlTable  OBJECT-TYPE
            SYNTAX  SEQUENCE OF FxoCommandControlEntry
            ACCESS  not-accessible
            STATUS  mandatory
            DESCRIPTION
                "The command control table."
            ::= { fxo-card 6 }

        fxoCommandControlEntry  OBJECT-TYPE
            SYNTAX  FxoCommandControlEntry
            ACCESS  not-accessible
            STATUS  mandatory
            DESCRIPTION
                "An entry in the command control table."
            INDEX { fxoCommandControlIndex }
            ::= { fxoCommandControlTable 1 }

        FxoCommandControlEntry ::= SEQUENCE {
            fxoCommandControlIndex      LSSlotID,
            fxoCommandControlReset      INTEGER,
            fxoCommandControlLoadDefault    INTEGER
        }

        fxoCommandControlIndex  OBJECT-TYPE
            SYNTAX  LSSlotID
            ACCESS  read-only
            STATUS  mandatory
            DESCRIPTION
                "slot index"
            ::= { fxoCommandControlEntry 1 }

        fxoCommandControlLoadDefault    OBJECT-TYPE
            SYNTAX  INTEGER {
                    load-default(1)
                }
            ACCESS  read-write
            STATUS  mandatory
            DESCRIPTION
                "Command: Load Default FXO CONF"
            ::= { fxoCommandControlEntry 2 }

        fxoCommandControlReset    OBJECT-TYPE
            SYNTAX  INTEGER {
                    reset(1)
                }
            ACCESS  read-write
            STATUS  mandatory
            DESCRIPTION
                "Command: FXO Card Reset"
            ::= { fxoCommandControlEntry 3 }

  --    FXO Per Port Signaling Config Control Table


        fxoNewPerPortSigSetTable  OBJECT-TYPE
            SYNTAX  SEQUENCE OF FxoNewPerPortSigSetEntry
            ACCESS  not-accessible
            STATUS  mandatory
            DESCRIPTION
                "FXO Per Port Signaling Configuration Control Table"
            ::= { fxo-card 7 }

        fxoNewPerPortSigSetEntry  OBJECT-TYPE
            SYNTAX  FxoNewPerPortSigSetEntry
            ACCESS  not-accessible
            STATUS  mandatory
            DESCRIPTION
                "FXO Per port signaling configuration control entry"
            INDEX { fxoNewPerPortSigSetIndex ,
                    fxoNewPerPortSigSetPort ,
                    fxoNewPerPortSigSetItemIndex }
            ::= { fxoNewPerPortSigSetTable 1 }

        FxoNewPerPortSigSetEntry ::= SEQUENCE {
            fxoNewPerPortSigSetIndex LSSlotID,
            fxoNewPerPortSigSetPort      PortID,
            fxoNewPerPortSigSetItemIndex INTEGER,
            fxoNewPerPortSigSetSigBit        DisplayString
        }

        fxoNewPerPortSigSetIndex  OBJECT-TYPE
            SYNTAX  LSSlotID
            ACCESS  read-only
            STATUS  mandatory
            DESCRIPTION
                "slot index"
            ::= { fxoNewPerPortSigSetEntry 1 }

        fxoNewPerPortSigSetPort   OBJECT-TYPE
            SYNTAX  PortID
            ACCESS  read-only
            STATUS  mandatory
            DESCRIPTION
                "port 1-12"
            ::= { fxoNewPerPortSigSetEntry 2 }

        fxoNewPerPortSigSetItemIndex   OBJECT-TYPE
            SYNTAX  INTEGER {
                    ringing(1),
                    no-ring(2),
                    batt-rev(3),
                    pulse-on(4),
                    tip-open(5),
                    off-hook(6),
                    oos-alarm(7),
                    ring-gnd(8)
                }
            ACCESS  read-only
            STATUS  mandatory
            DESCRIPTION
                " ringing, no-ring, batt-rev, pulse-on, tip-open, off-hook, oos-on, ring-gnd "
            ::= { fxoNewPerPortSigSetEntry 3 }

        fxoNewPerPortSigSetSigBit   OBJECT-TYPE
            SYNTAX  DisplayString (SIZE (0..255))
            ACCESS  read-write
            STATUS  mandatory
            DESCRIPTION
                " Signaling Bit Setup 0/1 or don't care "
            ::= { fxoNewPerPortSigSetEntry 4 }

--
--  FXO SigMode Control Table
--

        fxoNewSigModeSetTable  OBJECT-TYPE
            SYNTAX  SEQUENCE OF FxoNewSigModeSetEntry
            ACCESS  not-accessible
            STATUS  mandatory
            DESCRIPTION
                "The SigMode control table."
            ::= { fxo-card 8 }

        fxoNewSigModeSetEntry  OBJECT-TYPE
            SYNTAX  FxoNewSigModeSetEntry
            ACCESS  not-accessible
            STATUS  mandatory
            DESCRIPTION
                "An entry in the SigMode control table."
            INDEX { fxoNewSigModeSetIndex }
            ::= { fxoNewSigModeSetTable 1 }

        FxoNewSigModeSetEntry ::= SEQUENCE {
            fxoNewSigModeSetIndex      LSSlotID,
            fxoNewSigModeSetMode      INTEGER
        }

        fxoNewSigModeSetIndex  OBJECT-TYPE
            SYNTAX  LSSlotID
            ACCESS  read-only
            STATUS  mandatory
            DESCRIPTION
                "slot index"
            ::= { fxoNewSigModeSetEntry 1 }

        fxoNewSigModeSetMode    OBJECT-TYPE
            SYNTAX  INTEGER {
                    perCard(1),
                    perPort(2)
                }
            ACCESS  read-write
            STATUS  mandatory
            DESCRIPTION
                "SigMode Mode"
            ::= { fxoNewSigModeSetEntry 2 }


--
--      FXO NEW Per Port Config Control Table
--

        fxoNewPerPortSetTable  OBJECT-TYPE
            SYNTAX  SEQUENCE OF FxoNewPerPortSetEntry
            ACCESS  not-accessible
            STATUS  mandatory
            DESCRIPTION
                "FXO New Per Port Configuration Control Table"
            ::= { fxo-card 9 }

        fxoNewPerPortSetEntry  OBJECT-TYPE
            SYNTAX  FxoNewPerPortSetEntry
            ACCESS  not-accessible
            STATUS  mandatory
            DESCRIPTION
                "FXO Per Port Configuration control entry"
            INDEX { fxoNewPerPortSetIndex ,
                    fxoNewPerPortSetPortIndex }
            ::= { fxoNewPerPortSetTable 1 }

        FxoNewPerPortSetEntry ::= SEQUENCE {
            fxoNewPerPortSetIndex    LSSlotID,
            fxoNewPerPortSetPortIndex    PortID,
            fxoNewPerPortSetTrunk     INTEGER,
            fxoNewPerPortSetPolarity  INTEGER
        }

        fxoNewPerPortSetIndex  OBJECT-TYPE
            SYNTAX  LSSlotID
            ACCESS  read-only
            STATUS  mandatory
            DESCRIPTION
                "slot index"
            ::= { fxoNewPerPortSetEntry 1 }

        fxoNewPerPortSetPortIndex   OBJECT-TYPE
            SYNTAX  PortID
            ACCESS  read-only
            STATUS  mandatory
            DESCRIPTION
                "port 1-12"
            ::= { fxoNewPerPortSetEntry 2 }

        fxoNewPerPortSetTrunk       OBJECT-TYPE
            SYNTAX  INTEGER {
                    onHook(1),
                    offHook(2)
                }
            ACCESS  read-write
            STATUS  mandatory
            DESCRIPTION
                " Per port Trunk Condition "
            ::= { fxoNewPerPortSetEntry 3 }

        fxoNewPerPortSetPolarity   OBJECT-TYPE
            SYNTAX  INTEGER {
                    reverse(1),
                    normal(2)
                }
            ACCESS  read-write
            STATUS  mandatory
            DESCRIPTION
                " Per Port Line polarity "
            ::= { fxoNewPerPortSetEntry 4 }


--
--      FXOA Per Port Diag InfoTable
--

        fxoNewInfoTable  OBJECT-TYPE
            SYNTAX  SEQUENCE OF FxoNewInfoEntry
            ACCESS  not-accessible
            STATUS  mandatory
            DESCRIPTION
                "E&M Diag Info Table"
            ::= { fxo-card 10 }

        fxoNewInfoEntry  OBJECT-TYPE
            SYNTAX  FxoNewInfoEntry
            ACCESS  not-accessible
            STATUS  mandatory
            DESCRIPTION
                "FXO Diag Infoentry"
            INDEX { fxoNewInfoIndex ,
                    fxoNewInfoPortIndex }
            ::= { fxoNewInfoTable 1 }

        FxoNewInfoEntry ::= SEQUENCE {
            fxoNewInfoIndex              LSSlotID,
            fxoNewInfoPortIndex        PortID,
            fxoNewInfoRing            EMOffOn,
            fxoNewInfoOffHook           EMOffOn,
            fxoNewInfoLine               EMOffOn,
            fxoNewInfoRingGND              EMOffOn,
            fxoNewInfoBattRev              EMOffOn,
            fxoNewInfoPulseOn              EMOffOn,
            fxoNewInfoAlarm              EMOffOn,
            fxoNewInfoTx               DisplayString,
            fxoNewInfoRx              DisplayString,
            fxoNewInfoVoltage         DisplayString,
            fxoNewInfoTIP               EMOffOn
        }

        fxoNewInfoIndex OBJECT-TYPE
            SYNTAX  LSSlotID
            ACCESS  read-only
            STATUS  mandatory
            DESCRIPTION
                "slot index"
            ::= { fxoNewInfoEntry 1 }

        fxoNewInfoPortIndex    OBJECT-TYPE
            SYNTAX  PortID
            ACCESS  read-only
            STATUS  mandatory
            DESCRIPTION
                "port 1-12"
            ::= { fxoNewInfoEntry 2 }


        fxoNewInfoRing    OBJECT-TYPE
            SYNTAX  EMOffOn
            ACCESS  read-only
            STATUS  mandatory
            DESCRIPTION
                "ring "
            ::= { fxoNewInfoEntry 3}

        fxoNewInfoOffHook   OBJECT-TYPE
            SYNTAX  EMOffOn
            ACCESS  read-only
            STATUS  mandatory
            DESCRIPTION
                " off hook "
            ::= { fxoNewInfoEntry 4}

        fxoNewInfoLine     OBJECT-TYPE
            SYNTAX  EMOffOn
            ACCESS  read-only
            STATUS  mandatory
            DESCRIPTION
                " line broken "
            ::= { fxoNewInfoEntry 5}

        fxoNewInfoRingGND   OBJECT-TYPE
            SYNTAX  EMOffOn
            ACCESS  read-only
            STATUS  mandatory
            DESCRIPTION
                " ring ground "
            ::= { fxoNewInfoEntry 6}

        fxoNewInfoBattRev      OBJECT-TYPE
            SYNTAX  EMOffOn
            ACCESS  read-only
            STATUS  mandatory
            DESCRIPTION
                " Battery reverse "
            ::= { fxoNewInfoEntry 7}


        fxoNewInfoPulseOn     OBJECT-TYPE
            SYNTAX  EMOffOn
            ACCESS  read-only
            STATUS  mandatory
            DESCRIPTION
                " Pulse On "
            ::= { fxoNewInfoEntry 8}


        fxoNewInfoAlarm       OBJECT-TYPE
            SYNTAX  EMOffOn
            ACCESS  read-only
            STATUS  mandatory
            DESCRIPTION
                " Alarm"
            ::= { fxoNewInfoEntry 9}


        fxoNewInfoTx       OBJECT-TYPE
            SYNTAX  DisplayString (SIZE (0..255))
            ACCESS  read-only
            STATUS  mandatory
            DESCRIPTION
                " Per port TX-signal "
            ::= { fxoNewInfoEntry 10 }

        fxoNewInfoRx       OBJECT-TYPE
            SYNTAX  DisplayString (SIZE (0..255))
            ACCESS  read-only
            STATUS  mandatory
            DESCRIPTION
                " Per port RX-signal"
            ::= { fxoNewInfoEntry 11}

        fxoNewInfoVoltage       OBJECT-TYPE
            SYNTAX  DisplayString (SIZE (0..255))
            ACCESS  read-only
            STATUS  mandatory
            DESCRIPTION
                " Per port Line Voltage"
            ::= { fxoNewInfoEntry 12}

        fxoNewInfoTIP     OBJECT-TYPE
            SYNTAX  EMOffOn
            ACCESS  read-only
            STATUS  mandatory
            DESCRIPTION
                " TIP OPEN "
            ::= { fxoNewInfoEntry 13}


--
-- FXOA Line Diagnostic Control Table
--

        fxoNewDiagSetTable  OBJECT-TYPE
            SYNTAX  SEQUENCE OF FxoNewDiagSetEntry
            ACCESS  not-accessible
            STATUS  mandatory
            DESCRIPTION
                "FXOA Diagnostic Control Table."
            ::= { fxo-card 11 }

        fxoNewDiagSetEntry  OBJECT-TYPE
            SYNTAX  FxoNewDiagSetEntry
            ACCESS  not-accessible
            STATUS  mandatory
            DESCRIPTION
                "An entry of FXO diagnostic control table."
            INDEX { fxoNewDiagSetSlot }
            ::= { fxoNewDiagSetTable 1 }

        FxoNewDiagSetEntry ::= SEQUENCE {
            fxoNewDiagSetSlot          LSSlotID,
            fxoNewDiagSetTest           INTEGER,
            fxoNewDiagSetPeriod          INTEGER,
            fxoNewDiagSetRemain           INTEGER

    }

        fxoNewDiagSetSlot    OBJECT-TYPE
            SYNTAX  LSSlotID
            ACCESS  read-only
            STATUS  mandatory
            DESCRIPTION
                "slot index"
            ::= { fxoNewDiagSetEntry 1 }

        fxoNewDiagSetTest    OBJECT-TYPE
            SYNTAX  INTEGER {
                    stop(1),
                    offHookTest(2),
                    ringTest(3),
                    battRevTest(4),
                    pulseOnTest(5),
                    tipOpenTest(6)
                }
            ACCESS  read-write
            STATUS  mandatory
            DESCRIPTION
                "E&M  Test Button"
            ::= { fxoNewDiagSetEntry 2 }


        fxoNewDiagSetPeriod    OBJECT-TYPE
            SYNTAX  INTEGER {
                    sec10(1),
                    sec60(2)
                }
            ACCESS  read-write
            STATUS  mandatory
            DESCRIPTION
                "E&M  Test Button"
            ::= { fxoNewDiagSetEntry 3 }

        fxoNewDiagSetRemain    OBJECT-TYPE
            SYNTAX  INTEGER
            ACCESS  read-only
            STATUS  mandatory
            DESCRIPTION
                "remain time"
            ::= { fxoNewDiagSetEntry 4 }


--
--      FXO Per Port Enable/Disable Control Table
--

        fxoPortEnableTable  OBJECT-TYPE
            SYNTAX  SEQUENCE OF FxoPortEnableEntry
            ACCESS  not-accessible
            STATUS  mandatory
            DESCRIPTION
                "FXO Per Port Enable Table"
            ::= { fxo-card 12 }

        fxoPortEnableEntry  OBJECT-TYPE
            SYNTAX  FxoPortEnableEntry
            ACCESS  not-accessible
            STATUS  mandatory
            DESCRIPTION
                "FXO Per Port Enable entry"
            INDEX { fxoPortEnableIndex ,
        fxoPortEnablePort }
            ::= { fxoPortEnableTable 1 }

            FxoPortEnableEntry ::= SEQUENCE {
            fxoPortEnableIndex      LSSlotID,
            fxoPortEnablePort       PortID,
            fxoPortEnable           INTEGER
        }

        fxoPortEnableIndex  OBJECT-TYPE
            SYNTAX  LSSlotID
            ACCESS  read-only
            STATUS  mandatory
            DESCRIPTION
            "slot index"
            ::= { fxoPortEnableEntry 1 }

        fxoPortEnablePort   OBJECT-TYPE
            SYNTAX  PortID
            ACCESS  read-only
            STATUS  mandatory
            DESCRIPTION
                "port 1-12"
            ::= { fxoPortEnableEntry 2 }

        fxoPortEnable   OBJECT-TYPE
            SYNTAX  INTEGER   {
                    disable(1),
                    enable(2)
                }
            ACCESS  read-write
            STATUS  mandatory
            DESCRIPTION
                " port enable/disable"
            ::= { fxoPortEnableEntry 3 }


        fxoTotalCard   OBJECT-TYPE
            SYNTAX  INTEGER
            ACCESS  read-only
            STATUS  mandatory
            DESCRIPTION
                "Total cards of FXO"
            ::= { fxo-card 100 }

--======================================================================--
--======================================================================--
--  mag-card MIB
--======================================================================--
-- Magneto Card

--      magAllPortConfigTable        OBJECT IDENTIFIER ::= { mag-card 1 }
--      magAllPortSigConfigTable     OBJECT IDENTIFIER ::= { mag-card 2 }
--      magPerPortConfigTable        OBJECT IDENTIFIER ::= { mag-card 3 }
--      magPortStatusTable           OBJECT IDENTIFIER ::= { mag-card 4 }
--      magDiagTestControlTable      OBJECT IDENTIFIER ::= { mag-card 5 }
--      magCommandControlTable       OBJECT IDENTIFIER ::= { mag-card 6 }
--======================================================================--


--
--      MAG All Port Config Control Table
--

        magAllPortConfigTable  OBJECT-TYPE
            SYNTAX  SEQUENCE OF MagAllPortConfigEntry
            ACCESS  not-accessible
            STATUS  mandatory
            DESCRIPTION
                "MAG All Port Configuration Control Table"
            ::= { mag-card 1 }

        magAllPortConfigEntry  OBJECT-TYPE
            SYNTAX  MagAllPortConfigEntry
            ACCESS  not-accessible
            STATUS  mandatory
            DESCRIPTION
                "MAG all port configuration control entry"
            INDEX { magAllPortConfigIndex }
            ::= { magAllPortConfigTable 1 }

        MagAllPortConfigEntry ::= SEQUENCE {
            magAllPortConfigIndex       LSSlotID,
            magAllPortConfigRing-Mode   INTEGER,
            magAllPortConfigA-u-law     INTEGER,
            magAllPortConfigImpedance   INTEGER,
            magAllPortConfigTx-gain     DisplayString,
            magAllPortConfigRx-gain     DisplayString,
            magAllPortConfigRing-cadence    INTEGER
        }

        magAllPortConfigIndex  OBJECT-TYPE
            SYNTAX  LSSlotID
            ACCESS  read-only
            STATUS  mandatory
            DESCRIPTION
                "Mag slot"
            ::= { magAllPortConfigEntry 1 }

        magAllPortConfigRing-Mode   OBJECT-TYPE
            SYNTAX  INTEGER {
                    ring-across-l1-l2-only(2),
                    ring-across-l1-gnd-only(3),
                    ring-across-l1-l2-and-l1-gnd(4)
                }
            ACCESS  read-only
            STATUS  mandatory
            DESCRIPTION
                " Ring Mode "
            ::= { magAllPortConfigEntry 2 }

        magAllPortConfigA-u-law   OBJECT-TYPE
            SYNTAX  INTEGER {
                    u-law(1),
                    a-law(2)
                }
            ACCESS  read-write
            STATUS  mandatory
            DESCRIPTION
                " A/u LAW "
            ::= { magAllPortConfigEntry 3 }

        magAllPortConfigImpedance   OBJECT-TYPE
            SYNTAX  INTEGER {
                    imp-900-ohm(1),
                    imp-600-ohm(2)
                }
            ACCESS  read-write
            STATUS  mandatory
            DESCRIPTION
                " IMPEDANCE "
            ::= { magAllPortConfigEntry 4 }

        magAllPortConfigTx-gain   OBJECT-TYPE
            SYNTAX  DisplayString (SIZE (0..255))
            ACCESS  read-write
            STATUS  mandatory
            DESCRIPTION
                " TX-GAIN "
            ::= { magAllPortConfigEntry 5 }

        magAllPortConfigRx-gain   OBJECT-TYPE
            SYNTAX  DisplayString (SIZE (0..255))
            ACCESS  read-write
            STATUS  mandatory
            DESCRIPTION
                " RX-GAIN "
            ::= { magAllPortConfigEntry 6 }

        magAllPortConfigRing-cadence   OBJECT-TYPE
            SYNTAX  INTEGER {
                    cadence-1-on-2-off(1),
                    cadence-2-on-4-off(2)
                }
            ACCESS  read-write
            STATUS  mandatory
            DESCRIPTION
                " Ring Cadence "
            ::= { magAllPortConfigEntry 7 }


--
--      MAG All Port Signaling Config Control Table
--

        magAllPortSigConfigTable  OBJECT-TYPE
            SYNTAX  SEQUENCE OF MagAllPortSigConfigEntry
            ACCESS  not-accessible
            STATUS  mandatory
            DESCRIPTION
                "MAG All Port Signaling Configuration Control Table"
            ::= { mag-card 2 }

        magAllPortSigConfigEntry  OBJECT-TYPE
            SYNTAX  MagAllPortSigConfigEntry
            ACCESS  not-accessible
            STATUS  mandatory
            DESCRIPTION
                "MAG all port signaling configuration control entry"
            INDEX { magAllPortSigConfigIndex ,
                    magAllPortSigConfigItemIndex ,
                    magAllPortSigConfigSigBitIndex }
            ::= { magAllPortSigConfigTable 1 }

        MagAllPortSigConfigEntry ::= SEQUENCE {
            magAllPortSigConfigIndex    LSSlotID,
            magAllPortSigConfigItemIndex    INTEGER,
            magAllPortSigConfigSigBitIndex  INTEGER,
            magAllPortSigConfigSigBit       INTEGER
        }

        magAllPortSigConfigIndex  OBJECT-TYPE
            SYNTAX  LSSlotID
            ACCESS  read-only
            STATUS  mandatory
            DESCRIPTION
                "slot index"
            ::= { magAllPortSigConfigEntry 1 }

        magAllPortSigConfigItemIndex   OBJECT-TYPE
            SYNTAX  INTEGER {
                    tx-ring-l1-l2(1),
                    tx-ring-l1-gnd(2),
                    plar-tx-ring-l1-l2(3),
                    plar-tx-ring-l1-gnd(4),
                    no-tx-ring(5),
                    rx-ring-l1-l2(6),
                    rx-ring-l1-gnd(7),
                    plar-rx-ring-l1-l2(8),
                    plar-rx-ring-l1-gnd(9),
                    oos-alarm(10)
                }
            ACCESS  read-only
            STATUS  mandatory
            DESCRIPTION
                ""
            ::= { magAllPortSigConfigEntry 2 }

        magAllPortSigConfigSigBitIndex   OBJECT-TYPE
            SYNTAX  INTEGER {
                    a(1),
                    b(2),
                    c(3),
                    d(4)
                }
            ACCESS  read-only
            STATUS  mandatory
            DESCRIPTION
                " Signaling Bit Index "
            ::= { magAllPortSigConfigEntry 3 }

        magAllPortSigConfigSigBit   OBJECT-TYPE
            SYNTAX  INTEGER {
                    zero(0),
                    one(1),
                    do-not-care(2)
                }
            ACCESS  read-write
            STATUS  mandatory
            DESCRIPTION
                " Signaling Bit Setup 0/1 or don't care "
            ::= { magAllPortSigConfigEntry 4 }



--
--      MAG Per Port Config Control Table
--

        magPerPortConfigTable  OBJECT-TYPE
            SYNTAX  SEQUENCE OF MagPerPortConfigEntry
            ACCESS  not-accessible
            STATUS  mandatory
            DESCRIPTION
                "MAG Per Port Configuration Control Table"
            ::= { mag-card 3 }

        magPerPortConfigEntry  OBJECT-TYPE
            SYNTAX  MagPerPortConfigEntry
            ACCESS  not-accessible
            STATUS  mandatory
            DESCRIPTION
                "MAG Per Port Configuration control entry"
            INDEX { magPerPortConfigIndex ,
                    magPerPortConfigPortIndex }
            ::= { magPerPortConfigTable 1 }

        MagPerPortConfigEntry ::= SEQUENCE {
            magPerPortConfigIndex       LSSlotID,
            magPerPortConfigPortIndex   PortID,
            magPerPortConfigPLAR        INTEGER
        }

        magPerPortConfigIndex  OBJECT-TYPE
            SYNTAX  LSSlotID
            ACCESS  read-only
            STATUS  mandatory
            DESCRIPTION
                "slot index"
            ::= { magPerPortConfigEntry 1 }

        magPerPortConfigPortIndex   OBJECT-TYPE
            SYNTAX  PortID
            ACCESS  read-only
            STATUS  mandatory
            DESCRIPTION
                "port 1-12"
            ::= { magPerPortConfigEntry 2 }

        magPerPortConfigPLAR   OBJECT-TYPE
            SYNTAX INTEGER {
                    off(1),
                    on(2)
                }
            ACCESS  read-write
            STATUS  mandatory
            DESCRIPTION
                " Per port PLAR setting "
            ::= { magPerPortConfigEntry 3 }


--
--      MAG Port Status Table
--

        magPortStatusTable  OBJECT-TYPE
            SYNTAX  SEQUENCE OF MagPortStatusEntry
            ACCESS  not-accessible
            STATUS  mandatory
            DESCRIPTION
                "MAG Port Status Table"
            ::= { mag-card 4 }

        magPortStatusEntry  OBJECT-TYPE
            SYNTAX  MagPortStatusEntry
            ACCESS  not-accessible
            STATUS  mandatory
            DESCRIPTION
                "MAG Port Status entry"
            INDEX { magPortStatusIndex ,
                    magPortStatusItemIndex ,
                    magPortStatusPortIndex }
            ::= { magPortStatusTable 1 }

        MagPortStatusEntry ::= SEQUENCE {
            magPortStatusIndex          LSSlotID,
            magPortStatusItemIndex      INTEGER,
            magPortStatusPortIndex      PortID,
            magPortStatusStatus         INTEGER
        }

        magPortStatusIndex  OBJECT-TYPE
            SYNTAX  LSSlotID
            ACCESS  read-only
            STATUS  mandatory
            DESCRIPTION
                "slot index"
            ::= { magPortStatusEntry 1 }

        magPortStatusItemIndex   OBJECT-TYPE
            SYNTAX  INTEGER {
                    tx-ring-l1-l2(1),
                    tx-ring-l1-gnd(2),
                    rx-ring-l1-l2(3),
                    rx-ring-l1-gnd(4),
                    plar-on(5),
                    alarm-on(6)
                }
            ACCESS  read-only
            STATUS  mandatory
            DESCRIPTION
                ""
            ::= { magPortStatusEntry 2 }

        magPortStatusPortIndex   OBJECT-TYPE
            SYNTAX  PortID
            ACCESS  read-only
            STATUS  mandatory
            DESCRIPTION
                " port index 1-12 "
            ::= { magPortStatusEntry 3 }

        magPortStatusStatus   OBJECT-TYPE
            SYNTAX  INTEGER {
                    no(1),
                    yes(2)
                }
            ACCESS  read-only
            STATUS  mandatory
            DESCRIPTION
                " Port Status "
            ::= { magPortStatusEntry 4 }


--
--      MAG Line Diagnostic Control Table
--

        magDiagTestControlTable  OBJECT-TYPE
            SYNTAX  SEQUENCE OF MagDiagTestControlEntry
            ACCESS  not-accessible
            STATUS  mandatory
            DESCRIPTION
                "MAG Diagnostic Control Table."
            ::= { mag-card 5 }

        magDiagTestControlEntry  OBJECT-TYPE
            SYNTAX  MagDiagTestControlEntry
            ACCESS  not-accessible
            STATUS  mandatory
            DESCRIPTION
                "An entry of MAG diagnostic control table."
            INDEX { magDiagTestControlIndex }
            ::= { magDiagTestControlTable 1 }

        MagDiagTestControlEntry ::= SEQUENCE {
            magDiagTestControlIndex     LSSlotID,
            magDiagTestControlType      INTEGER,
            magDiagTestControlRemainTime    INTEGER
        }

        magDiagTestControlIndex  OBJECT-TYPE
            SYNTAX  LSSlotID
            ACCESS  read-only
            STATUS  mandatory
            DESCRIPTION
                "slot index"
            ::= { magDiagTestControlEntry 1 }

        magDiagTestControlType  OBJECT-TYPE
            SYNTAX  INTEGER {
                    stop(1),
                    rx-ring-l1-l2-test(2),
                    rx-ring-l1-gnd-test(3),
                    tx-ring-test(4)
                }
            ACCESS  read-write
            STATUS  mandatory
            DESCRIPTION
                "MAG Test"
            ::= { magDiagTestControlEntry 2 }

        magDiagTestControlRemainTime  OBJECT-TYPE
            SYNTAX  INTEGER
            ACCESS  read-only
            STATUS  mandatory
            DESCRIPTION
                "Remain time (sec)"
            ::= { magDiagTestControlEntry 3 }



--
--  MAG Command Control Table
--

        magCommandControlTable  OBJECT-TYPE
            SYNTAX  SEQUENCE OF MagCommandControlEntry
            ACCESS  not-accessible
            STATUS  mandatory
            DESCRIPTION
                "The command control table."
            ::= { mag-card 6 }

        magCommandControlEntry  OBJECT-TYPE
            SYNTAX  MagCommandControlEntry
            ACCESS  not-accessible
            STATUS  mandatory
            DESCRIPTION
                "An entry in the command control table."
            INDEX { magCommandControlIndex }
            ::= { magCommandControlTable 1 }

        MagCommandControlEntry ::= SEQUENCE {
            magCommandControlIndex      LSSlotID,
            magCommandControlReset      INTEGER,
            magCommandControlLoadDefault    INTEGER
        }

        magCommandControlIndex  OBJECT-TYPE
            SYNTAX  LSSlotID
            ACCESS  read-only
            STATUS  mandatory
            DESCRIPTION
                "slot index"
            ::= { magCommandControlEntry 1 }

        magCommandControlLoadDefault    OBJECT-TYPE
            SYNTAX  INTEGER {
                    load-default(1)
                }
            ACCESS  read-write
            STATUS  mandatory
            DESCRIPTION
                "Command: Load Default MAG CONF"
            ::= { magCommandControlEntry 2 }

        magCommandControlReset    OBJECT-TYPE
            SYNTAX  INTEGER {
                    reset(1)
                }
            ACCESS  read-write
            STATUS  mandatory
            DESCRIPTION
                "Command: MAG Card Reset"
            ::= { magCommandControlEntry 3 }


--
--      MAGA Per Port Enable/Disable Control Table
--

        magaPortEnableTable  OBJECT-TYPE
            SYNTAX  SEQUENCE OF MagaPortEnableEntry
            ACCESS  not-accessible
            STATUS  mandatory
            DESCRIPTION
                "MAGA Per Port Enable Table"
            ::= { mag-card 12 }

        magaPortEnableEntry  OBJECT-TYPE
            SYNTAX  MagaPortEnableEntry
            ACCESS  not-accessible
            STATUS  mandatory
            DESCRIPTION
                "MAGA Per Port Enable entry"
            INDEX { magaPortEnableIndex ,
        magaPortEnablePort }
            ::= { magaPortEnableTable 1 }

            MagaPortEnableEntry ::= SEQUENCE {
            magaPortEnableIndex      LSSlotID,
            magaPortEnablePort       PortID,
            magaPortEnable           INTEGER
        }

        magaPortEnableIndex  OBJECT-TYPE
            SYNTAX  LSSlotID
            ACCESS  read-only
            STATUS  mandatory
            DESCRIPTION
            "slot index"
            ::= { magaPortEnableEntry 1 }

        magaPortEnablePort   OBJECT-TYPE
            SYNTAX  PortID
            ACCESS  read-only
            STATUS  mandatory
            DESCRIPTION
                "port 1-12"
            ::= { magaPortEnableEntry 2 }

        magaPortEnable   OBJECT-TYPE
            SYNTAX  INTEGER   {
                    disable(1),
                    enable(2)
                }
            ACCESS  read-write
            STATUS  mandatory
            DESCRIPTION
                " port enable/disable"
            ::= { magaPortEnableEntry 3 }


        magTotalCard   OBJECT-TYPE
            SYNTAX  INTEGER
            ACCESS  read-only
            STATUS  mandatory
            DESCRIPTION
                "Total cards of MAG"
            ::= { mag-card 100 }

--======================================================================--
--======================================================================--
--  OCUDP MIB
--======================================================================--
--======================================================================--

--
--  SYSTEM Control Table
--

        ocuSystemControlTable  OBJECT-TYPE
            SYNTAX  SEQUENCE OF OcuSystemControlEntry
            ACCESS  not-accessible
            STATUS  mandatory
            DESCRIPTION
                "OCUDP control table."
            ::= { ocudp8Card 1 }

        ocuSystemControlEntry  OBJECT-TYPE
            SYNTAX  OcuSystemControlEntry
            ACCESS  not-accessible
            STATUS  mandatory
            DESCRIPTION
                "An entry in the OCUDP control table."
            INDEX { ocuSCslot , ocuSCport }
            ::= { ocuSystemControlTable 1 }

        OcuSystemControlEntry ::= SEQUENCE  {
            ocuSCslot                   LSSlotID,
            ocuSCport                   PortID,
            ocuDataRate                 INTEGER,
            ocuTransparent              INTEGER,
            ocuPortEnable               INTEGER
        }

        ocuSCslot  OBJECT-TYPE
            SYNTAX  LSSlotID
            ACCESS  read-only
            STATUS  mandatory
            DESCRIPTION
                "Slot index"
            ::= { ocuSystemControlEntry 1 }

        ocuSCport  OBJECT-TYPE
            SYNTAX  PortID
            ACCESS  read-only
            STATUS  mandatory
            DESCRIPTION
                "Port 1 to 8, total 8 ports."
            ::= { ocuSystemControlEntry 2 }

        ocuDataRate  OBJECT-TYPE
            SYNTAX  INTEGER   {
                    r64k(1),
                    r56k(2),
                    r19p2k(3),
                    r9p6k(4),
                    r4p8k(5),
                    r2p4k(6)
                    --r38p4k(7)
                }
            ACCESS  read-write
            STATUS  mandatory
            DESCRIPTION
                "OCUDP Data Rate"
            ::= { ocuSystemControlEntry 3 }

        ocuTransparent  OBJECT-TYPE
            SYNTAX  INTEGER   {
                    disable(1),
                    enable(2)
                }
            ACCESS  read-write
            STATUS  mandatory
            DESCRIPTION
                "OCUDP transparent carry data signal"
            ::= { ocuSystemControlEntry 4 }

        ocuPortEnable  OBJECT-TYPE
            SYNTAX  INTEGER   {
                    disable(1),
                    enable(2)
                }
            ACCESS  read-write
            STATUS  mandatory
            DESCRIPTION
                "OCUDP port enable/disable"
            ::= { ocuSystemControlEntry 5 }

--
--  User Define Code Table
--

        ocuUserDefineCodeTable  OBJECT-TYPE
            SYNTAX  SEQUENCE OF OcuUserDefineCodeEntry
            ACCESS  not-accessible
            STATUS  mandatory
            DESCRIPTION
                "OCUDP user define act/deact code table."
            ::= { ocudp8Card 2 }

        ocuUserDefineCodeEntry  OBJECT-TYPE
            SYNTAX  OcuUserDefineCodeEntry
            ACCESS  not-accessible
            STATUS  mandatory
            DESCRIPTION
                "An entry in the OCUDP user define code table."
            INDEX { ocuUDslot }
            ::= { ocuUserDefineCodeTable 1 }

        OcuUserDefineCodeEntry ::= SEQUENCE  {
            ocuUDslot                   LSSlotID,
            ocuActivationCodeLEN        INTEGER,
            ocuActivationCode           DisplayString,
            ocuDeActivationCodeLEN      INTEGER,
            ocuDeActivationCode         DisplayString
        }

        ocuUDslot  OBJECT-TYPE
            SYNTAX  LSSlotID
            ACCESS  read-only
            STATUS  mandatory
            DESCRIPTION
                "Slot index"
            ::= { ocuUserDefineCodeEntry 1 }

        ocuActivationCodeLEN  OBJECT-TYPE
            SYNTAX  INTEGER (3..8)
            ACCESS  read-write
            STATUS  mandatory
            DESCRIPTION
                "OCUDP Activation Code Length"
            ::= { ocuUserDefineCodeEntry 2 }

        ocuActivationCode  OBJECT-TYPE
            SYNTAX  DisplayString (SIZE (1..8))
            ACCESS  read-write
            STATUS  mandatory
            DESCRIPTION
                "OCUDP Activation Code"
            ::= { ocuUserDefineCodeEntry 3 }

        ocuDeActivationCodeLEN  OBJECT-TYPE
            SYNTAX  INTEGER (3..8)
            ACCESS  read-write
            STATUS  mandatory
            DESCRIPTION
                "OCUDP DeActivation Code Length"
            ::= { ocuUserDefineCodeEntry 4 }

        ocuDeActivationCode  OBJECT-TYPE
            SYNTAX  DisplayString (SIZE (1..8))
            ACCESS  read-write
            STATUS  mandatory
            DESCRIPTION
                "OCUDP DeActivation Code"
            ::= { ocuUserDefineCodeEntry 5 }

--
--  Status Table
--

        ocuStatusTable  OBJECT-TYPE
            SYNTAX  SEQUENCE OF OcuStatusEntry
            ACCESS  not-accessible
            STATUS  mandatory
            DESCRIPTION
                "The OCUDP status table."
            ::= { ocudp8Card 3 }

        ocuStatusEntry  OBJECT-TYPE
            SYNTAX  OcuStatusEntry
            ACCESS  not-accessible
            STATUS  mandatory
            DESCRIPTION
                "An entry in the OCUDP status table."
            INDEX { ocuSTslot , ocuSTport }
            ::= { ocuStatusTable 1 }

        OcuStatusEntry ::= SEQUENCE {
            ocuSTslot                   LSSlotID,
            ocuSTport                   PortID,
            ocuOOS                      INTEGER,
            ocuLOS                      INTEGER,
            ocuBitError                 INTEGER,
            ocuLOF                      INTEGER
        }

        ocuSTslot  OBJECT-TYPE
            SYNTAX  LSSlotID
            ACCESS  read-only
            STATUS  mandatory
            DESCRIPTION
                "Slot index"
            ::= { ocuStatusEntry 1 }

        ocuSTport  OBJECT-TYPE
            SYNTAX  PortID
            ACCESS  read-only
            STATUS  mandatory
            DESCRIPTION
                "Port 1 to 8, total 8 ports."
            ::= { ocuStatusEntry 2 }

        ocuOOS  OBJECT-TYPE
            SYNTAX  INTEGER {
                    no(1),
                    yes(2)
                }
            ACCESS  read-only
            STATUS  mandatory
            DESCRIPTION
                " OCUDP Out of Service "
            ::= { ocuStatusEntry 3 }

        ocuLOS  OBJECT-TYPE
            SYNTAX  INTEGER {
                    no(1),
                    yes(2)
                }
            ACCESS  read-only
            STATUS  mandatory
            DESCRIPTION
                " OCUDP Los of Signal "
            ::= { ocuStatusEntry 4 }

        ocuBitError  OBJECT-TYPE
            SYNTAX  INTEGER
            ACCESS  read-only
            STATUS  mandatory
            DESCRIPTION
                " OCUDP Bit Error Counter "
            ::= { ocuStatusEntry 5 }

        ocuLOF  OBJECT-TYPE
            SYNTAX  INTEGER {
                    no(1),
                    yes(2)
                }
            ACCESS  read-only
            STATUS  mandatory
            DESCRIPTION
                " OCUDP Out of Frame for 64K line rate "
            ::= { ocuStatusEntry 6 }

--
-- Diagnostic Control Table
--

        ocuDiagTable  OBJECT-TYPE
            SYNTAX  SEQUENCE OF OcuDiagEntry
            ACCESS  not-accessible
            STATUS  mandatory
            DESCRIPTION
                "Diagnostic Control Table"
            ::= { ocudp8Card 4 }

        ocuDiagEntry  OBJECT-TYPE
            SYNTAX  OcuDiagEntry
            ACCESS  not-accessible
            STATUS  mandatory
            DESCRIPTION
                "Diagnostic Control Table Entry"
            INDEX { ocuDIslot , ocuDIport }
            ::= { ocuDiagTable 1 }

        OcuDiagEntry ::= SEQUENCE {
            ocuDIslot                   LSSlotID,
            ocuDIport                   PortID,
            ocuLocalLoopback            INTEGER,
            ocuRemoteLoopback           INTEGER,
            ocuBertControl              INTEGER,
            ocuBertStatus               INTEGER,
            ocuElapseSeconds            INTEGER,
            ocuErrorSeconds             INTEGER,
            ocuErrorBits                INTEGER,
            ocuRemoteCallLoopback       INTEGER,
            ocuForceDisableRemCallLB    INTEGER
        }

        ocuDIslot  OBJECT-TYPE
            SYNTAX  LSSlotID
            ACCESS  read-only
            STATUS  mandatory
            DESCRIPTION
                "Slot index"
            ::= { ocuDiagEntry 1 }

        ocuDIport  OBJECT-TYPE
            SYNTAX  PortID
            ACCESS  read-only
            STATUS  mandatory
            DESCRIPTION
                "Port 1 to 8, total 8 ports."
            ::= { ocuDiagEntry 2 }

        ocuLocalLoopback  OBJECT-TYPE
            SYNTAX  INTEGER {
                    off(1),
                    lineLoopback(2),
                    localLoopback(3),
                    biDirectLoopback(4),
                    payloadLoopback(5)
                }
            ACCESS  read-write
            STATUS  mandatory
            DESCRIPTION
                "Local Loopback Type"
            ::= { ocuDiagEntry 3 }

        ocuRemoteLoopback  OBJECT-TYPE
            SYNTAX  INTEGER {
                    off(1),
                    t1410(2),
                    v54(3),
                    userDefine(4)
                }
            ACCESS  read-write
            STATUS  mandatory
            DESCRIPTION
                "Remote Loopback Type"
            ::= { ocuDiagEntry 4 }

        ocuBertControl  OBJECT-TYPE
            SYNTAX  INTEGER {
                    bertOff(1),
                    allZero(2),
                    allOne(3),
                    patt63(4),
                    patt511(5),
                    patt2047(6),
                    reset(7)
                }
            ACCESS  read-write
            STATUS  mandatory
            DESCRIPTION
                "BERT Test Control"
            ::= { ocuDiagEntry 5 }

        ocuBertStatus  OBJECT-TYPE
            SYNTAX  INTEGER {
                    bertSync(1),
                    bertUnsync(2),
                    bertNotActive(3)
                }
            ACCESS  read-only
            STATUS  mandatory
            DESCRIPTION
                "BERT Status"
            ::= { ocuDiagEntry 6 }

        ocuElapseSeconds  OBJECT-TYPE
            SYNTAX  INTEGER
            ACCESS  read-only
            STATUS  mandatory
            DESCRIPTION
                "Elapse seconds"
            ::= { ocuDiagEntry 7 }

        ocuErrorSeconds OBJECT-TYPE
            SYNTAX  INTEGER
            ACCESS  read-only
            STATUS  mandatory
            DESCRIPTION
                "Error seconds"
            ::= { ocuDiagEntry 8 }

        ocuErrorBits  OBJECT-TYPE
            SYNTAX  INTEGER
            ACCESS  read-only
            STATUS  mandatory
            DESCRIPTION
                "Error bits"
            ::= { ocuDiagEntry 9 }

        ocuRemoteCallLoopback  OBJECT-TYPE
            SYNTAX  INTEGER {
                    no(1),
                    yes(2)
                }
            ACCESS  read-only
            STATUS  mandatory
            DESCRIPTION
                "Remote Call Loopback Status"
            ::= { ocuDiagEntry 10 }

        ocuForceDisableRemCallLB  OBJECT-TYPE
            SYNTAX  INTEGER {
                    no(1),
                    yes(2)
                }
            ACCESS  read-write
            STATUS  mandatory
            DESCRIPTION
                "Force Disable Remote Call Loopback"
            ::= { ocuDiagEntry 11 }


--
-- Alarm Status Table
--

        ocuAlmStatusTable  OBJECT-TYPE
            SYNTAX  SEQUENCE OF OcuAlmStatusEntry
            ACCESS  not-accessible
            STATUS  mandatory
            DESCRIPTION
                "Alarm Status Table"
            ::= { ocudp8Card 5 }

        ocuAlmStatusEntry  OBJECT-TYPE
            SYNTAX  OcuAlmStatusEntry
            ACCESS  not-accessible
            STATUS  mandatory
            DESCRIPTION
                "Alarm Status Table Entry"
            INDEX { ocuASslot , ocuASport , ocuAlmNumber }
            ::= { ocuAlmStatusTable 1 }

        OcuAlmStatusEntry ::= SEQUENCE {
            ocuASslot                   LSSlotID,
            ocuASport                   PortID,
            ocuAlmNumber                INTEGER,
            ocuAlmString                DisplayString,
            ocuAlmState                 INTEGER,
            ocuAlmCount                 INTEGER,
            ocuAlmThreshold             INTEGER,
            ocuAlmEnable                LsAlarmSeverity
        }

        ocuASslot  OBJECT-TYPE
            SYNTAX  LSSlotID
            ACCESS  read-only
            STATUS  mandatory
            DESCRIPTION
                "Slot index"
            ::= { ocuAlmStatusEntry 1 }

        ocuASport  OBJECT-TYPE
            SYNTAX  PortID
            ACCESS  read-only
            STATUS  mandatory
            DESCRIPTION
                "Port 1 to 8, total 8 ports."
            ::= { ocuAlmStatusEntry 2 }

        ocuAlmNumber  OBJECT-TYPE
            SYNTAX  INTEGER (1..40)
            ACCESS  read-only
            STATUS  mandatory
            DESCRIPTION
                "Alarm Status Index"
            ::= { ocuAlmStatusEntry 3 }

        ocuAlmString  OBJECT-TYPE
            SYNTAX  DisplayString (SIZE (0..80))
            ACCESS  read-only
            STATUS  mandatory
            DESCRIPTION
                "Alarm Type String"
            ::= { ocuAlmStatusEntry 4 }

        ocuAlmState  OBJECT-TYPE
            SYNTAX  INTEGER {
                    ok(1),
                    alarm(2),
                    disable(3),
                    portDisabled(4)
                }
            ACCESS  read-only
            STATUS  mandatory
            DESCRIPTION
                "Alarm Current State"
            ::= { ocuAlmStatusEntry 5 }

        ocuAlmCount  OBJECT-TYPE
            SYNTAX  INTEGER
            ACCESS  read-only
            STATUS  mandatory
            DESCRIPTION
                "Alarm Count which happened"
            ::= { ocuAlmStatusEntry 6 }

        ocuAlmThreshold  OBJECT-TYPE
            SYNTAX  INTEGER
            ACCESS  read-write
            STATUS  mandatory
            DESCRIPTION
                "Alarm Threshold"
            ::= { ocuAlmStatusEntry 7 }

        ocuAlmEnable  OBJECT-TYPE
            SYNTAX  LsAlarmSeverity
            ACCESS  read-write
            STATUS  mandatory
            DESCRIPTION
                "Alarm is enabled or not"
            ::= { ocuAlmStatusEntry 8 }

--
--  Command Control Table
--

        ocuCommandControlTable  OBJECT-TYPE
            SYNTAX  SEQUENCE OF OcuCommandControlEntry
            ACCESS  not-accessible
            STATUS  mandatory
            DESCRIPTION
                "The command control table."
            ::= { ocudp8Card 6 }

        ocuCommandControlEntry  OBJECT-TYPE
            SYNTAX  OcuCommandControlEntry
            ACCESS  not-accessible
            STATUS  mandatory
            DESCRIPTION
                "An entry in the command control table."
            INDEX { ocuCCslot }
            ::= { ocuCommandControlTable 1 }

        OcuCommandControlEntry ::= SEQUENCE {
            ocuCCslot                   LSSlotID,
            ocuClearCardAlarmHistory    INTEGER,
            ocuClearCardPerformanceData INTEGER,
            ocuCardLoadDefault          INTEGER,
            ocuCardReset                INTEGER,
            ocuPortReset                INTEGER
        }

        ocuCCslot  OBJECT-TYPE
            SYNTAX  LSSlotID
            ACCESS  read-only
            STATUS  mandatory
            DESCRIPTION
                "Slot index"
            ::= { ocuCommandControlEntry 1 }

        ocuClearCardAlarmHistory    OBJECT-TYPE
            SYNTAX  INTEGER {
                    clear(1)
                }
            ACCESS  read-write
            STATUS  mandatory
            DESCRIPTION
                "Clear Card Alarm History"
            ::= { ocuCommandControlEntry 2 }

        ocuClearCardPerformanceData    OBJECT-TYPE
            SYNTAX  INTEGER {
                    clear(1)
                }
            ACCESS  read-write
            STATUS  mandatory
            DESCRIPTION
                "Clear card performance data"
            ::= { ocuCommandControlEntry 3 }

        ocuCardLoadDefault    OBJECT-TYPE
            SYNTAX  INTEGER {
                    loadDefault(1)
                }
            ACCESS  read-write
            STATUS  mandatory
            DESCRIPTION
                "Card Load Default"
            ::= { ocuCommandControlEntry 4 }

        ocuCardReset    OBJECT-TYPE
            SYNTAX  INTEGER {
                    reset(1)
                }
            ACCESS  read-write
            STATUS  mandatory
            DESCRIPTION
                "Card Reset"
            ::= { ocuCommandControlEntry 5 }

        ocuPortReset    OBJECT-TYPE
            SYNTAX  INTEGER {
                    resetPort1(1),
                    resetPort2(2),
                    resetPort3(3),
                    resetPort4(4),
                    resetPort5(5),
                    resetPort6(6),
                    resetPort7(7),
                    resetPort8(8)
                }
            ACCESS  read-write
            STATUS  mandatory
            DESCRIPTION
                "Port Reset"
            ::= { ocuCommandControlEntry 6 }

--
--  SYSTEM Information Table
--

        ocuSystemInfoTable  OBJECT-TYPE
            SYNTAX  SEQUENCE OF OcuSystemInfoEntry
            ACCESS  not-accessible
            STATUS  mandatory
            DESCRIPTION
                "The system information table."
            ::= {ocudp8Card 7 }

        ocuSystemInfoEntry  OBJECT-TYPE
            SYNTAX  OcuSystemInfoEntry
            ACCESS  not-accessible
            STATUS  mandatory
            DESCRIPTION
                "An entry in the system information table."
            INDEX { ocuSIslot }
            ::= { ocuSystemInfoTable 1 }

        OcuSystemInfoEntry ::= SEQUENCE {
            ocuSIslot                   LSSlotID,
            ocuFPGAVersion              DisplayString,
            ocuPCBVersion               DisplayString
        }

        ocuSIslot  OBJECT-TYPE
            SYNTAX  LSSlotID
            ACCESS  read-only
            STATUS  mandatory
            DESCRIPTION
                "Slot index"
            ::= { ocuSystemInfoEntry 1 }

        ocuFPGAVersion  OBJECT-TYPE
            SYNTAX  DisplayString (SIZE (0..255) )
            ACCESS  read-only
            STATUS  mandatory
            DESCRIPTION
                "FPGA Version"
            ::= { ocuSystemInfoEntry 2 }

        ocuPCBVersion  OBJECT-TYPE
            SYNTAX  DisplayString (SIZE (0..255) )
            ACCESS  read-only
            STATUS  mandatory
            DESCRIPTION
                "PCB Version"
            ::= { ocuSystemInfoEntry 3 }

--
--  Performance Table
--
    ocuPerformanceReport    OBJECT IDENTIFIER ::= { ocudp8Card 8 }

--
-- Current Performance Table
--
        ocuCurrentPerfTable  OBJECT-TYPE
            SYNTAX  SEQUENCE OF OcuCurrentPerfEntry
            ACCESS  not-accessible
            STATUS  mandatory
            DESCRIPTION
                "Current Performance Table"
            ::= { ocuPerformanceReport 1 }

        ocuCurrentPerfEntry  OBJECT-TYPE
            SYNTAX  OcuCurrentPerfEntry
            ACCESS  not-accessible
            STATUS  mandatory
            DESCRIPTION
                "Current performance entry"
            INDEX { ocuCPslot , ocuCPport , ocuCurrPerfRegType }
            ::= { ocuCurrentPerfTable 1 }

        OcuCurrentPerfEntry ::= SEQUENCE  {
            ocuCPslot                   LSSlotID,
            ocuCPport                   PortID,
            ocuCurrPerfRegType          INTEGER,
            ocuCurrentPerfES            INTEGER,
            ocuCurrentPerfSES           INTEGER,
            ocuCurrentPerfUAS           INTEGER,
            ocuCurr15MinTimeElapsed     INTEGER,
            ocuValid15MinInterval       INTEGER
        }

        ocuCPslot  OBJECT-TYPE
            SYNTAX  LSSlotID
            ACCESS  read-only
            STATUS  mandatory
            DESCRIPTION
                "Slot index"
            ::= { ocuCurrentPerfEntry 1 }

        ocuCPport  OBJECT-TYPE
            SYNTAX  PortID
            ACCESS  read-only
            STATUS  mandatory
            DESCRIPTION
                "Port 1 to 8, total 8 ports."
            ::= { ocuCurrentPerfEntry 2 }

        ocuCurrPerfRegType  OBJECT-TYPE
            SYNTAX  INTEGER {
                    user(1),
                    line(2)
                }
            ACCESS  read-only
            STATUS  mandatory
            DESCRIPTION
                " Performance Register Type "
            ::= { ocuCurrentPerfEntry 3 }

        ocuCurrentPerfES  OBJECT-TYPE
            SYNTAX  INTEGER
            ACCESS  read-only
            STATUS  mandatory
            DESCRIPTION
                " ESS Error Counter "
            ::= { ocuCurrentPerfEntry 4 }

        ocuCurrentPerfSES  OBJECT-TYPE
            SYNTAX  INTEGER
            ACCESS  read-only
            STATUS  mandatory
            DESCRIPTION
                " SES Error Counter "
            ::= { ocuCurrentPerfEntry 5 }

        ocuCurrentPerfUAS  OBJECT-TYPE
            SYNTAX  INTEGER
            ACCESS  read-only
            STATUS  mandatory
            DESCRIPTION
                " UAS Error Counter "
            ::= { ocuCurrentPerfEntry 6 }

        ocuCurr15MinTimeElapsed  OBJECT-TYPE
            SYNTAX  INTEGER
            ACCESS  read-only
            STATUS  mandatory
            DESCRIPTION
                " Current 15-minute time elapsed"
            ::= { ocuCurrentPerfEntry 7 }

        ocuValid15MinInterval  OBJECT-TYPE
            SYNTAX  INTEGER
            ACCESS  read-only
            STATUS  mandatory
            DESCRIPTION
                " Current 1-day Valid 15-min interval"
            ::= { ocuCurrentPerfEntry 8 }

--
--  Interval Performance Table
--

        ocuIntervalPerfTable  OBJECT-TYPE
            SYNTAX  SEQUENCE OF OcuIntervalPerfEntry
            ACCESS  not-accessible
            STATUS  mandatory
            DESCRIPTION
                "Interval Performance Table"
            ::= { ocuPerformanceReport 2 }

        ocuIntervalPerfEntry  OBJECT-TYPE
            SYNTAX  OcuIntervalPerfEntry
            ACCESS  not-accessible
            STATUS  mandatory
            DESCRIPTION
                "FOM Optical interval performance entry"
            INDEX { ocuIPslot , ocuIPport ,
                    ocuIntvPerfRegType , ocuIntervalPerfNumber }
            ::= { ocuIntervalPerfTable 1 }

        OcuIntervalPerfEntry ::= SEQUENCE {
            ocuIPslot                   LSSlotID,
            ocuIPport                   PortID,
            ocuIntvPerfRegType          INTEGER,
            ocuIntervalPerfNumber       INTEGER,
            ocuIntervalPerfES           INTEGER,
            ocuIntervalPerfSES          INTEGER,
            ocuIntervalPerfUAS          INTEGER
        }

        ocuIPslot  OBJECT-TYPE
            SYNTAX  LSSlotID
            ACCESS  read-only
            STATUS  mandatory
            DESCRIPTION
                "Slot index"
            ::= { ocuIntervalPerfEntry 1 }

        ocuIPport  OBJECT-TYPE
            SYNTAX  PortID
            ACCESS  read-only
            STATUS  mandatory
            DESCRIPTION
                "Port 1 to 8, total 8 ports."
            ::= { ocuIntervalPerfEntry 2 }

        ocuIntvPerfRegType  OBJECT-TYPE
            SYNTAX  INTEGER {
                    user(1),
                    line(2)
                }
            ACCESS  read-only
            STATUS  mandatory
            DESCRIPTION
                " Performance Register Type "
            ::= { ocuIntervalPerfEntry 3 }

        ocuIntervalPerfNumber  OBJECT-TYPE
            SYNTAX  INTEGER (1..96)
            ACCESS  read-only
            STATUS  mandatory
            DESCRIPTION
                " Interval Index "
            ::= { ocuIntervalPerfEntry 4 }

        ocuIntervalPerfES  OBJECT-TYPE
            SYNTAX  INTEGER
            ACCESS  read-only
            STATUS  mandatory
            DESCRIPTION
                " ES Error Counter "
            ::= { ocuIntervalPerfEntry 5 }

        ocuIntervalPerfSES  OBJECT-TYPE
            SYNTAX  INTEGER
            ACCESS  read-only
            STATUS  mandatory
            DESCRIPTION
                " SES Error Counter "
            ::= { ocuIntervalPerfEntry 6 }

        ocuIntervalPerfUAS  OBJECT-TYPE
            SYNTAX  INTEGER
            ACCESS  read-only
            STATUS  mandatory
            DESCRIPTION
                " UAS Error Counter "
            ::= { ocuIntervalPerfEntry 7 }

--
--  Total Performance Table
--

        ocuTotalPerfTable  OBJECT-TYPE
            SYNTAX  SEQUENCE OF OcuTotalPerfEntry
            ACCESS  not-accessible
            STATUS  mandatory
            DESCRIPTION
                "Total Performance Table"
            ::= { ocuPerformanceReport 3 }

        ocuTotalPerfEntry  OBJECT-TYPE
            SYNTAX  OcuTotalPerfEntry
            ACCESS  not-accessible
            STATUS  mandatory
            DESCRIPTION
                "Total performance table"
            INDEX { ocuTPslot , ocuTPport , ocuTotalPerfRegType }
            ::= { ocuTotalPerfTable 1 }

        OcuTotalPerfEntry ::= SEQUENCE  {
            ocuTPslot                   LSSlotID,
            ocuTPport                   PortID,
            ocuTotalPerfRegType         INTEGER,
            ocuTotalPerfES              INTEGER,
            ocuTotalPerfSES             INTEGER,
            ocuTotalPerfUAS             INTEGER
        }

        ocuTPslot  OBJECT-TYPE
            SYNTAX  LSSlotID
            ACCESS  read-only
            STATUS  mandatory
            DESCRIPTION
                "Slot index"
            ::= { ocuTotalPerfEntry 1 }

        ocuTPport  OBJECT-TYPE
            SYNTAX  PortID
            ACCESS  read-only
            STATUS  mandatory
            DESCRIPTION
                "Port 1 to 8, total 8 ports."
            ::= { ocuTotalPerfEntry 2 }

        ocuTotalPerfRegType  OBJECT-TYPE
            SYNTAX  INTEGER {
                    user(1),
                    line(2)
                }
            ACCESS  read-only
            STATUS  mandatory
            DESCRIPTION
                " Performance Register Type "
            ::= { ocuTotalPerfEntry 3 }

        ocuTotalPerfES  OBJECT-TYPE
            SYNTAX  INTEGER
            ACCESS  read-only
            STATUS  mandatory
            DESCRIPTION
                " ES Error Counter "
            ::= { ocuTotalPerfEntry 4 }

        ocuTotalPerfSES  OBJECT-TYPE
            SYNTAX  INTEGER
            ACCESS  read-only
            STATUS  mandatory
            DESCRIPTION
                " SES Error Counter "
            ::= { ocuTotalPerfEntry 5 }

        ocuTotalPerfUAS  OBJECT-TYPE
            SYNTAX  INTEGER
            ACCESS  read-only
            STATUS  mandatory
            DESCRIPTION
                " UAS Error Counter "
            ::= { ocuTotalPerfEntry 6 }

--
--  Seven Days Performance Table
--
        ocuSevenDaysPerfTable  OBJECT-TYPE
            SYNTAX  SEQUENCE OF OcuSevenDaysPerfEntry
            ACCESS  not-accessible
            STATUS  mandatory
            DESCRIPTION
                "7 Days Performance Table"
            ::= { ocuPerformanceReport 4 }

        ocuSevenDaysPerfEntry  OBJECT-TYPE
            SYNTAX  OcuSevenDaysPerfEntry
            ACCESS  not-accessible
            STATUS  mandatory
            DESCRIPTION
                "7 days performance entry"
            INDEX { ocuSDslot , ocuSDport ,
                    ocuSevenDaysPerfRegType , ocuDaysIndex }
            ::= { ocuSevenDaysPerfTable 1 }

        OcuSevenDaysPerfEntry ::= SEQUENCE  {
            ocuSDslot                   LSSlotID,
            ocuSDport                   PortID,
            ocuSevenDaysPerfRegType     INTEGER,
            ocuDaysIndex                INTEGER,
            ocuDateStrIndex             DisplayString,
            ocuSevenDaysPerfES          INTEGER,
            ocuSevenDaysPerfSES         INTEGER,
            ocuSevenDaysPerfUAS         INTEGER
        }

        ocuSDslot  OBJECT-TYPE
            SYNTAX  LSSlotID
            ACCESS  read-only
            STATUS  mandatory
            DESCRIPTION
                "Slot index"
            ::= { ocuSevenDaysPerfEntry 1 }

        ocuSDport  OBJECT-TYPE
            SYNTAX  PortID
            ACCESS  read-only
            STATUS  mandatory
            DESCRIPTION
                "Port 1 to 8, total 8 ports."
            ::= { ocuSevenDaysPerfEntry 2 }

        ocuSevenDaysPerfRegType  OBJECT-TYPE
            SYNTAX  INTEGER {
                    user(1),
                    line(2)
                }
            ACCESS  read-only
            STATUS  mandatory
            DESCRIPTION
                " Performance Register Type "
            ::= { ocuSevenDaysPerfEntry 3 }

        ocuDaysIndex  OBJECT-TYPE
            SYNTAX  INTEGER (1..7)
            ACCESS  read-only
            STATUS  mandatory
            DESCRIPTION
                "Seven Days index "
            ::= { ocuSevenDaysPerfEntry 4 }

        ocuDateStrIndex  OBJECT-TYPE
            SYNTAX  DisplayString (SIZE (0..255) )
            ACCESS  read-only
            STATUS  mandatory
            DESCRIPTION
                "Seven Days String "
            ::= { ocuSevenDaysPerfEntry 5 }

        ocuSevenDaysPerfES  OBJECT-TYPE
            SYNTAX  INTEGER
            ACCESS  read-only
            STATUS  mandatory
            DESCRIPTION
                " ES Error Counter "
            ::= { ocuSevenDaysPerfEntry 6 }

        ocuSevenDaysPerfSES  OBJECT-TYPE
            SYNTAX  INTEGER
            ACCESS  read-only
            STATUS  mandatory
            DESCRIPTION
                " SES Error Counter "
            ::= { ocuSevenDaysPerfEntry 7 }

        ocuSevenDaysPerfUAS  OBJECT-TYPE
            SYNTAX  INTEGER
            ACCESS  read-only
            STATUS  mandatory
            DESCRIPTION
                " UAS Error Counter "
            ::= { ocuSevenDaysPerfEntry 8 }

        ocudpTotalCard   OBJECT-TYPE
            SYNTAX  INTEGER
            ACCESS  read-only
            STATUS  mandatory
            DESCRIPTION
                "Total cards of OCUDP"
            ::= { ocudp8Card 100 }


--======================================================================--
--======================================================================--
--  quad-e1-card MIB
--======================================================================--
--======================================================================--

--
--  Line Control Table
--

        qe1LineControlTable  OBJECT-TYPE
            SYNTAX  SEQUENCE OF QE1LineControlEntry
            ACCESS  not-accessible
            STATUS  mandatory
            DESCRIPTION
                "The DS1 line control table."
            ::= { qe1-card 1 }

        qe1LineControlEntry  OBJECT-TYPE
            SYNTAX  QE1LineControlEntry
            ACCESS  not-accessible
            STATUS  mandatory
            DESCRIPTION
                "An entry in the DS1 line control table."
            INDEX { qe1LCSlotIndex , qe1LCPortIndex }
            ::= { qe1LineControlTable 1 }

        QE1LineControlEntry ::= SEQUENCE  {
            qe1LCSlotIndex              LSSlotID,
            qe1LCPortIndex              PortID,
            qe1LineFrame                INTEGER,
            qe1LineCoding               INTEGER,
            qe1Interface                INTEGER,
            qe1FDL                      INTEGER,
            qe1FDLSabit                 INTEGER,
            qe1AIS                      INTEGER,
            qe1RAI                      INTEGER,
            qe1CRC                      INTEGER,
            qe1IdleCode                 INTEGER,
            qe1CASMode                  INTEGER,
            qe1SignallingMode           INTEGER,
            qe1CGA                      INTEGER,
            qe1OutOfService             INTEGER,
            qe1Protect                  INTEGER,
            qe1Master                   INTEGER,
            qe1PortEnable               INTEGER
        }

        qe1LCSlotIndex  OBJECT-TYPE
            SYNTAX  LSSlotID
            ACCESS  read-only
            STATUS  mandatory
            DESCRIPTION
                "Qe1 slot"
            ::= { qe1LineControlEntry 1 }

        qe1LCPortIndex  OBJECT-TYPE
            SYNTAX  PortID
            ACCESS  read-only
            STATUS  mandatory
            DESCRIPTION
                "Port 1 to 4, total 4 ports."
            ::= { qe1LineControlEntry 2 }

        qe1LineFrame  OBJECT-TYPE
            SYNTAX  INTEGER   {
                    on(1),
                    off(2)
                }
            ACCESS  read-write
            STATUS  mandatory
            DESCRIPTION
                "Line frame format"
            ::= { qe1LineControlEntry 3 }

        qe1LineCoding  OBJECT-TYPE
            SYNTAX  INTEGER   {
                    ami(1),
                    hdb3(2)
                }
            ACCESS  read-write
            STATUS  mandatory
            DESCRIPTION
                "Line Coding type"
            ::= { qe1LineControlEntry 4 }

        qe1Interface  OBJECT-TYPE
            SYNTAX  INTEGER   {
                    twisted-pair(1),
                    coaxial-cable(2)
                }
            ACCESS  read-only
            STATUS  mandatory
            DESCRIPTION
                "Interface indicates that QE1 line use 75/120 Ohm Cable."
            ::= { qe1LineControlEntry 5 }

        qe1FDL  OBJECT-TYPE
            SYNTAX  INTEGER   {
                    fdl(1),
                    off(2),
                    hdlc(3),
                    ssm(4)
--                        ssm-hdlc(5)
                }
            ACCESS  read-write
            STATUS  mandatory
            DESCRIPTION
                "QE1 Facility Data Link ON/OFF"
            ::= { qe1LineControlEntry 6 }

        qe1FDLSabit  OBJECT-TYPE
            SYNTAX  INTEGER   {
                    sa4(1),
                    sa5(2),
                    sa6(3),
                    sa7(4),
                    sa8(5),
                    sa4-5(6)
                }
            ACCESS  read-write
            STATUS  mandatory
            DESCRIPTION
                "QE1 Facility Data Link use Sax bit"
            ::= { qe1LineControlEntry 7 }

        qe1AIS  OBJECT-TYPE
            SYNTAX  INTEGER   {
                    frame(1),
--                    unframe(2),
                    off(3)
                }
            ACCESS  read-write
            STATUS  mandatory
            DESCRIPTION
                "QE1 line Alarm Indication Signal."
            ::= { qe1LineControlEntry 8 }

        qe1RAI  OBJECT-TYPE
            SYNTAX  INTEGER   {
                    on(1),
                    off(2)
                }
            ACCESS  read-write
            STATUS  mandatory
            DESCRIPTION
                "RAI-ON indicates that RAI (Remote Alarm Indication) ON."
            ::= { qe1LineControlEntry 9 }

        qe1CRC  OBJECT-TYPE
            SYNTAX  INTEGER   {
                    on(1),
                    off(2)
                }
            ACCESS  read-write
            STATUS  mandatory
            DESCRIPTION
                "QE1 Cycle Redundancy Check ON/OFF"
            ::= { qe1LineControlEntry 10 }

        qe1IdleCode  OBJECT-TYPE
            SYNTAX  INTEGER
            ACCESS  read-write
            STATUS  mandatory
            DESCRIPTION
                "Line Idle Code Value"
            ::= { qe1LineControlEntry 11 }

        qe1CASMode  OBJECT-TYPE
            SYNTAX  INTEGER   {
                    on(1),
                    off(2)
                }
            ACCESS  read-write
            STATUS  mandatory
            DESCRIPTION
                "CAS or CCS"
            ::= { qe1LineControlEntry 12 }

        qe1SignallingMode  OBJECT-TYPE
            SYNTAX  INTEGER   {
                    trans(1),
                    cd01(2)
                }
            ACCESS  read-write
            STATUS  mandatory
            DESCRIPTION
                "TRANS or CD01"
            ::= { qe1LineControlEntry 13 }

        qe1CGA  OBJECT-TYPE
            SYNTAX  INTEGER   {
                    norm(1)
                }
            ACCESS  read-write
            STATUS  mandatory
            DESCRIPTION
                "Method used to signal the Carrier Group Alarm state
                to the other end of the selected link."
            ::= { qe1LineControlEntry 14 }

        qe1OutOfService  OBJECT-TYPE
            SYNTAX  INTEGER   {
                    busy(1),
                    idle(2),
                    ais(3)
                }
            ACCESS  read-write
            STATUS  mandatory
            DESCRIPTION
                "When NORM (CGA) is select, the parameter determines the
                state of the A, B signaling bits during the
                Out-of-Service periods."
            ::= { qe1LineControlEntry 15 }

        qe1Protect  OBJECT-TYPE
            SYNTAX  INTEGER   {
                    disable(1),
                    circuit(2),
                    line(3)
                }
            ACCESS  read-only
            STATUS  mandatory
            DESCRIPTION
                "disable or enable."
            ::= { qe1LineControlEntry 16 }

        qe1Master  OBJECT-TYPE
            SYNTAX  INTEGER   {
                    xxxx(1),
                    slave(2),
                    master(3)
                }
            ACCESS  read-only
            STATUS  mandatory
            DESCRIPTION
                "master or slave"
            ::= { qe1LineControlEntry 17 }

        qe1PortEnable  OBJECT-TYPE
            SYNTAX  INTEGER   {
                    disable(1),
                    enable(2)
                }
            ACCESS  read-write
            STATUS  mandatory
            DESCRIPTION
                "QE1 port enable/disable"
            ::= { qe1LineControlEntry 19 }


--
--  User Current Performance Table
--

        qe1UserCurrentPerfTable  OBJECT-TYPE
            SYNTAX  SEQUENCE OF QE1UserCurrentPerfEntry
            ACCESS  not-accessible
            STATUS  mandatory
            DESCRIPTION
                "User Current Performance Table"
            ::= { qe1-card 2 }

        qe1UserCurrentPerfEntry  OBJECT-TYPE
            SYNTAX  QE1UserCurrentPerfEntry
            ACCESS  not-accessible
            STATUS  mandatory
            DESCRIPTION
                "User current performance entry"
            INDEX { qe1UCPSlotIndex , qe1UCPPortIndex }
            ::= { qe1UserCurrentPerfTable 1 }

        QE1UserCurrentPerfEntry ::= SEQUENCE  {
            qe1UCPSlotIndex             LSSlotID,
            qe1UCPPortIndex             PortID,
            qe1UserCurrentPerfES        INTEGER,
            qe1UserCurrentPerfSES       INTEGER,
            qe1UserCurrentPerfBES       INTEGER,
            qe1UserCurrentPerfUAS       INTEGER,
            qe1UserCurrentPerfCSS       INTEGER,
            qe1UserCurrentPerfBPV       INTEGER,
            qe1UserCurrentPerfDMs       INTEGER,
            qe1UserCurr15MinTimeElapsed INTEGER,
            qe1UserValid15MinInterval   INTEGER
        }

        qe1UCPSlotIndex  OBJECT-TYPE
            SYNTAX  LSSlotID
            ACCESS  read-only
            STATUS  mandatory
            DESCRIPTION
                "Qe1 slot"
            ::= { qe1UserCurrentPerfEntry 1 }

        qe1UCPPortIndex  OBJECT-TYPE
            SYNTAX  PortID
            ACCESS  read-only
            STATUS  mandatory
            DESCRIPTION
                "Port 1 to 4, total 4 ports."
            ::= { qe1UserCurrentPerfEntry 2 }

        qe1UserCurrentPerfES  OBJECT-TYPE
            SYNTAX  INTEGER
            ACCESS  read-only
            STATUS  mandatory
            DESCRIPTION
                " ES Error Counter "
            ::= { qe1UserCurrentPerfEntry 3 }

        qe1UserCurrentPerfSES  OBJECT-TYPE
            SYNTAX  INTEGER
            ACCESS  read-only
            STATUS  mandatory
            DESCRIPTION
                " SES Error Counter "
            ::= { qe1UserCurrentPerfEntry 4 }

        qe1UserCurrentPerfBES  OBJECT-TYPE
            SYNTAX  INTEGER
            ACCESS  read-only
            STATUS  mandatory
            DESCRIPTION
                " BES Error Counter "
            ::= { qe1UserCurrentPerfEntry 5 }

        qe1UserCurrentPerfUAS  OBJECT-TYPE
            SYNTAX  INTEGER
            ACCESS  read-only
            STATUS  mandatory
            DESCRIPTION
                " UAS Error Counter "
            ::= { qe1UserCurrentPerfEntry 6 }

        qe1UserCurrentPerfCSS  OBJECT-TYPE
            SYNTAX  INTEGER
            ACCESS  read-only
            STATUS  mandatory
            DESCRIPTION
                " CS Error Counter "
            ::= { qe1UserCurrentPerfEntry 7 }

        qe1UserCurrentPerfBPV  OBJECT-TYPE
            SYNTAX  INTEGER
            ACCESS  read-only
            STATUS  mandatory
            DESCRIPTION
                " BPV Error Counter "
            ::= { qe1UserCurrentPerfEntry 8 }

        qe1UserCurrentPerfDMs  OBJECT-TYPE
            SYNTAX  INTEGER
            ACCESS  read-only
            STATUS  mandatory
            DESCRIPTION
                " DM Error Counter "
            ::= { qe1UserCurrentPerfEntry 9 }

        qe1UserCurr15MinTimeElapsed  OBJECT-TYPE
            SYNTAX  INTEGER
            ACCESS  read-only
            STATUS  mandatory
            DESCRIPTION
                " Current 15-minute time elapsed"
            ::= { qe1UserCurrentPerfEntry 11 }

        qe1UserValid15MinInterval  OBJECT-TYPE
            SYNTAX  INTEGER
            ACCESS  read-only
            STATUS  mandatory
            DESCRIPTION
                " Current 1-day Valid 15-min interval"
            ::= { qe1UserCurrentPerfEntry 12 }


--
--  User Interval Performance Table
--

        qe1UserIntervalPerfTable  OBJECT-TYPE
            SYNTAX  SEQUENCE OF QE1UserIntervalPerfEntry
            ACCESS  not-accessible
            STATUS  mandatory
            DESCRIPTION
                "User Interval Performance Table"
            ::= { qe1-card 3 }

        qe1UserIntervalPerfEntry  OBJECT-TYPE
            SYNTAX  QE1UserIntervalPerfEntry
            ACCESS  not-accessible
            STATUS  mandatory
            DESCRIPTION
                "User interval performance entry"
            INDEX { qe1UIPSlotIndex , qe1UIPPortIndex ,
                    qe1UserIntervalPerfNumber }
            ::= { qe1UserIntervalPerfTable 1 }

        QE1UserIntervalPerfEntry ::= SEQUENCE  {
            qe1UIPSlotIndex             LSSlotID,
            qe1UIPPortIndex             PortID,
            qe1UserIntervalPerfNumber   INTEGER  (1..96),
            qe1UserIntervalPerfES       INTEGER,
            qe1UserIntervalPerfSES      INTEGER,
            qe1UserIntervalPerfBES      INTEGER,
            qe1UserIntervalPerfUAS      INTEGER,
            qe1UserIntervalPerfCSS      INTEGER,
            qe1UserIntervalPerfBPV      INTEGER,
            qe1UserIntervalPerfDMs      INTEGER
        }

        qe1UIPSlotIndex  OBJECT-TYPE
            SYNTAX  LSSlotID
            ACCESS  read-only
            STATUS  mandatory
            DESCRIPTION
                "Qe1 slot"
            ::= { qe1UserIntervalPerfEntry 1 }

        qe1UIPPortIndex  OBJECT-TYPE
            SYNTAX  PortID
            ACCESS  read-only
            STATUS  mandatory
            DESCRIPTION
                "Port 1 to 4, total 4 ports."
            ::= { qe1UserIntervalPerfEntry 2 }

        qe1UserIntervalPerfNumber  OBJECT-TYPE
            SYNTAX  INTEGER (1..96)
            ACCESS  read-only
            STATUS  mandatory
            DESCRIPTION
                "Interval Index"
            ::= { qe1UserIntervalPerfEntry 3 }

        qe1UserIntervalPerfES  OBJECT-TYPE
            SYNTAX  INTEGER
            ACCESS  read-only
            STATUS  mandatory
            DESCRIPTION
                " ES Error Counter "
            ::= { qe1UserIntervalPerfEntry 4 }

        qe1UserIntervalPerfSES  OBJECT-TYPE
            SYNTAX  INTEGER
            ACCESS  read-only
            STATUS  mandatory
            DESCRIPTION
                " SES Error Counter "
            ::= { qe1UserIntervalPerfEntry 5 }

        qe1UserIntervalPerfBES  OBJECT-TYPE
            SYNTAX  INTEGER
            ACCESS  read-only
            STATUS  mandatory
            DESCRIPTION
                " BES Error Counter "
            ::= { qe1UserIntervalPerfEntry 6 }

        qe1UserIntervalPerfUAS  OBJECT-TYPE
            SYNTAX  INTEGER
            ACCESS  read-only
            STATUS  mandatory
            DESCRIPTION
                " UAS Error Counter "
            ::= { qe1UserIntervalPerfEntry 7 }

        qe1UserIntervalPerfCSS  OBJECT-TYPE
            SYNTAX  INTEGER
            ACCESS  read-only
            STATUS  mandatory
            DESCRIPTION
                " CSS Error Counter "
            ::= { qe1UserIntervalPerfEntry 8 }

        qe1UserIntervalPerfBPV  OBJECT-TYPE
            SYNTAX  INTEGER
            ACCESS  read-only
            STATUS  mandatory
            DESCRIPTION
                " BPV Error Counter "
            ::= { qe1UserIntervalPerfEntry 9 }

        qe1UserIntervalPerfDMs   OBJECT-TYPE
            SYNTAX  INTEGER
            ACCESS  read-only
            STATUS  mandatory
            DESCRIPTION
                " DM Error Counter "
            ::= { qe1UserIntervalPerfEntry 10 }


--
--  User Total Performance Table
--
        qe1UserTotalPerfTable  OBJECT-TYPE
            SYNTAX  SEQUENCE OF QE1UserTotalPerfEntry
            ACCESS  not-accessible
            STATUS  mandatory
            DESCRIPTION
                "User Total Performance Table"
            ::= { qe1-card 4 }

        qe1UserTotalPerfEntry  OBJECT-TYPE
            SYNTAX  QE1UserTotalPerfEntry
            ACCESS  not-accessible
            STATUS  mandatory
            DESCRIPTION
                "User total performance entry"
            INDEX { qe1UTPSlotIndex , qe1UTPPortIndex }
            ::= { qe1UserTotalPerfTable 1 }

        QE1UserTotalPerfEntry ::= SEQUENCE  {
            qe1UTPSlotIndex             LSSlotID,
            qe1UTPPortIndex             PortID,
            qe1UserTotalPerfES          INTEGER,
            qe1UserTotalPerfSES         INTEGER,
            qe1UserTotalPerfBES         INTEGER,
            qe1UserTotalPerfUAS         INTEGER,
            qe1UserTotalPerfCSS         INTEGER,
            qe1UserTotalPerfBPV         INTEGER,
            qe1UserTotalPerfDMs         INTEGER
        }

        qe1UTPSlotIndex  OBJECT-TYPE
            SYNTAX  LSSlotID
            ACCESS  read-only
            STATUS  mandatory
            DESCRIPTION
                "Qe1 slot"
            ::= { qe1UserTotalPerfEntry 1 }

        qe1UTPPortIndex  OBJECT-TYPE
            SYNTAX  PortID
            ACCESS  read-only
            STATUS  mandatory
            DESCRIPTION
                "Port 1 to 4, total 4 ports."
            ::= { qe1UserTotalPerfEntry 2 }

        qe1UserTotalPerfES  OBJECT-TYPE
            SYNTAX  INTEGER
            ACCESS  read-only
            STATUS  mandatory
            DESCRIPTION
                " ES Error Counter "
            ::= { qe1UserTotalPerfEntry 3 }

        qe1UserTotalPerfSES  OBJECT-TYPE
            SYNTAX  INTEGER
            ACCESS  read-only
            STATUS  mandatory
            DESCRIPTION
                " SES Error Counter "
            ::= { qe1UserTotalPerfEntry 4 }

        qe1UserTotalPerfBES  OBJECT-TYPE
            SYNTAX  INTEGER
            ACCESS  read-only
            STATUS  mandatory
            DESCRIPTION
                " BES Error Counter "
            ::= { qe1UserTotalPerfEntry 5 }

        qe1UserTotalPerfUAS  OBJECT-TYPE
            SYNTAX  INTEGER
            ACCESS  read-only
            STATUS  mandatory
            DESCRIPTION
                " UAS Error Counter "
            ::= { qe1UserTotalPerfEntry 6 }

        qe1UserTotalPerfCSS  OBJECT-TYPE
            SYNTAX  INTEGER
            ACCESS  read-only
            STATUS  mandatory
            DESCRIPTION
                " CSS Error Counter "
            ::= { qe1UserTotalPerfEntry 7 }

        qe1UserTotalPerfBPV  OBJECT-TYPE
            SYNTAX  INTEGER
            ACCESS  read-only
            STATUS  mandatory
            DESCRIPTION
                " BPV Error Counter "
            ::= { qe1UserTotalPerfEntry 8 }

        qe1UserTotalPerfDMs  OBJECT-TYPE
            SYNTAX  INTEGER
            ACCESS  read-only
            STATUS  mandatory
            DESCRIPTION
                " DM Error Counter "
            ::= { qe1UserTotalPerfEntry 9 }


--
--  User Seven Days Performance Table
--
        qe1User7DaysPerfTable  OBJECT-TYPE
            SYNTAX  SEQUENCE OF QE1User7DaysPerfEntry
            ACCESS  not-accessible
            STATUS  mandatory
            DESCRIPTION
                "User 7 Days Performance Table"
            ::= { qe1-card 5 }

        qe1User7DaysPerfEntry  OBJECT-TYPE
            SYNTAX  QE1User7DaysPerfEntry
            ACCESS  not-accessible
            STATUS  mandatory
            DESCRIPTION
                "User 7 days performance table"
            INDEX { qe1UDPSlotIndex , qe1UDPPortIndex ,
                    qe1UserDaysIndex }
            ::= { qe1User7DaysPerfTable 1 }

        QE1User7DaysPerfEntry ::= SEQUENCE  {
            qe1UDPSlotIndex             LSSlotID,
            qe1UDPPortIndex             PortID,
            qe1UserDaysIndex            INTEGER (1..7),
            qe1UserDateStrIndex         DisplayString (SIZE (0..255) ),
            qe1UserSevenDaysPerfES      INTEGER,
            qe1UserSevenDaysPerfSES     INTEGER,
            qe1UserSevenDaysPerfBES     INTEGER,
            qe1UserSevenDaysPerfUAS     INTEGER,
            qe1UserSevenDaysPerfCSS     INTEGER,
            qe1UserSevenDaysPerfDMs     INTEGER,
            qe1UserSevenDaysPerfBPV     INTEGER
        }

        qe1UDPSlotIndex  OBJECT-TYPE
            SYNTAX  LSSlotID
            ACCESS  read-only
            STATUS  mandatory
            DESCRIPTION
                "Qe1 slot"
            ::= { qe1User7DaysPerfEntry 1 }

        qe1UDPPortIndex  OBJECT-TYPE
            SYNTAX  PortID
            ACCESS  read-only
            STATUS  mandatory
            DESCRIPTION
                "Port 1 to 4, total 4 ports."
            ::= { qe1User7DaysPerfEntry 2 }

        qe1UserDaysIndex  OBJECT-TYPE
            SYNTAX  INTEGER (1..7)
            ACCESS  read-only
            STATUS  mandatory
            DESCRIPTION
                "Seven Days index "
            ::= { qe1User7DaysPerfEntry 3 }

        qe1UserDateStrIndex  OBJECT-TYPE
            SYNTAX  DisplayString (SIZE (0..255) )
            ACCESS  read-only
            STATUS  mandatory
            DESCRIPTION
                "Seven Days String "
            ::= { qe1User7DaysPerfEntry 4 }

        qe1UserSevenDaysPerfES  OBJECT-TYPE
            SYNTAX  INTEGER
            ACCESS  read-only
            STATUS  mandatory
            DESCRIPTION
                " ES Error Counter "
            ::= { qe1User7DaysPerfEntry 5 }

        qe1UserSevenDaysPerfSES  OBJECT-TYPE
            SYNTAX  INTEGER
            ACCESS  read-only
            STATUS  mandatory
            DESCRIPTION
                " SES Error Counter "
            ::= { qe1User7DaysPerfEntry 6 }

        qe1UserSevenDaysPerfBES  OBJECT-TYPE
            SYNTAX  INTEGER
            ACCESS  read-only
            STATUS  mandatory
            DESCRIPTION
                " BES Error Counter "
            ::= { qe1User7DaysPerfEntry 7 }

        qe1UserSevenDaysPerfUAS  OBJECT-TYPE
            SYNTAX  INTEGER
            ACCESS  read-only
            STATUS  mandatory
            DESCRIPTION
                " UAS Error Counter "
            ::= { qe1User7DaysPerfEntry 8 }

        qe1UserSevenDaysPerfCSS  OBJECT-TYPE
            SYNTAX  INTEGER
            ACCESS  read-only
            STATUS  mandatory
            DESCRIPTION
                " CSS Error Counter "
            ::= { qe1User7DaysPerfEntry 9 }

        qe1UserSevenDaysPerfDMs  OBJECT-TYPE
            SYNTAX  INTEGER
            ACCESS  read-only
            STATUS  mandatory
            DESCRIPTION
                " DM Error Counter "
            ::= { qe1User7DaysPerfEntry 10 }

        qe1UserSevenDaysPerfBPV  OBJECT-TYPE
            SYNTAX  INTEGER
            ACCESS  read-only
            STATUS  mandatory
            DESCRIPTION
                " BPV Error Counter "
            ::= { qe1User7DaysPerfEntry 11 }


--
--  Line Current Performance Table
--

        qe1LineCurrentPerfTable  OBJECT-TYPE
            SYNTAX  SEQUENCE OF QE1LineCurrentPerfEntry
            ACCESS  not-accessible
            STATUS  mandatory
            DESCRIPTION
                "Line Current Performance Table"
            ::= { qe1-card 10 }

        qe1LineCurrentPerfEntry  OBJECT-TYPE
            SYNTAX  QE1LineCurrentPerfEntry
            ACCESS  not-accessible
            STATUS  mandatory
            DESCRIPTION
                "Line current performance entry"
            INDEX { qe1LCPSlotIndex , qe1LCPPortIndex }
            ::= { qe1LineCurrentPerfTable 1 }

        QE1LineCurrentPerfEntry ::= SEQUENCE  {
            qe1LCPSlotIndex             LSSlotID,
            qe1LCPPortIndex             PortID,
            qe1LineCurrentPerfES        INTEGER,
            qe1LineCurrentPerfSES       INTEGER,
            qe1LineCurrentPerfBES       INTEGER,
            qe1LineCurrentPerfUAS       INTEGER,
            qe1LineCurrentPerfCSS       INTEGER,
            qe1LineCurrentPerfBPV       INTEGER,
            qe1LineCurrentPerfDMs       INTEGER,
            qe1LineCurr15MinTimeElapsed INTEGER,
            qe1LineValid15MinInterval   INTEGER
        }

        qe1LCPSlotIndex  OBJECT-TYPE
            SYNTAX  LSSlotID
            ACCESS  read-only
            STATUS  mandatory
            DESCRIPTION
                "Qe1 slot"
            ::= { qe1LineCurrentPerfEntry 1 }

        qe1LCPPortIndex  OBJECT-TYPE
            SYNTAX  PortID
            ACCESS  read-only
            STATUS  mandatory
            DESCRIPTION
                "Port 1 to 4, total 4 ports."
            ::= { qe1LineCurrentPerfEntry 2 }

        qe1LineCurrentPerfES  OBJECT-TYPE
            SYNTAX  INTEGER
            ACCESS  read-only
            STATUS  mandatory
            DESCRIPTION
                " ESS Error Counter "
            ::= { qe1LineCurrentPerfEntry 3 }

        qe1LineCurrentPerfSES  OBJECT-TYPE
            SYNTAX  INTEGER
            ACCESS  read-only
            STATUS  mandatory
            DESCRIPTION
                " SES Error Counter "
            ::= { qe1LineCurrentPerfEntry 4 }

        qe1LineCurrentPerfBES  OBJECT-TYPE
            SYNTAX  INTEGER
            ACCESS  read-only
            STATUS  mandatory
            DESCRIPTION
                " BES Error Counter "
            ::= { qe1LineCurrentPerfEntry 5 }

        qe1LineCurrentPerfUAS  OBJECT-TYPE
            SYNTAX  INTEGER
            ACCESS  read-only
            STATUS  mandatory
            DESCRIPTION
                " UAS Error Counter "
            ::= { qe1LineCurrentPerfEntry 6 }

        qe1LineCurrentPerfCSS  OBJECT-TYPE
            SYNTAX  INTEGER
            ACCESS  read-only
            STATUS  mandatory
            DESCRIPTION
                " CSS Error Counter "
            ::= { qe1LineCurrentPerfEntry 7 }

        qe1LineCurrentPerfBPV  OBJECT-TYPE
            SYNTAX  INTEGER
            ACCESS  read-only
            STATUS  mandatory
            DESCRIPTION
                " BPV Error Counter "
            ::= { qe1LineCurrentPerfEntry 8 }

        qe1LineCurrentPerfDMs  OBJECT-TYPE
            SYNTAX  INTEGER
            ACCESS  read-only
            STATUS  mandatory
            DESCRIPTION
                " DM Error Counter "
            ::= { qe1LineCurrentPerfEntry 9 }

        qe1LineCurr15MinTimeElapsed  OBJECT-TYPE
            SYNTAX  INTEGER
            ACCESS  read-only
            STATUS  mandatory
            DESCRIPTION
                " Current 15-minute time elapsed"
            ::= { qe1LineCurrentPerfEntry 11 }

        qe1LineValid15MinInterval  OBJECT-TYPE
            SYNTAX  INTEGER
            ACCESS  read-only
            STATUS  mandatory
            DESCRIPTION
                " Current 1-day Valid 15-min interval"
            ::= { qe1LineCurrentPerfEntry 12 }


--
--  Line Interval Performance Table
--

        qe1LineIntervalPerfTable  OBJECT-TYPE
            SYNTAX  SEQUENCE OF QE1LineIntervalPerfEntry
            ACCESS  not-accessible
            STATUS  mandatory
            DESCRIPTION
                "Line Interval Performance Table"
            ::= { qe1-card 11 }

        qe1LineIntervalPerfEntry  OBJECT-TYPE
            SYNTAX  QE1LineIntervalPerfEntry
            ACCESS  not-accessible
            STATUS  mandatory
            DESCRIPTION
                "Line interval performance entry"
            INDEX { qe1LIPSlotIndex , qe1LIPPortIndex ,
                    qe1LineIntervalPerfNumber }
            ::= { qe1LineIntervalPerfTable 1 }

        QE1LineIntervalPerfEntry ::= SEQUENCE {
            qe1LIPSlotIndex             LSSlotID,
            qe1LIPPortIndex             PortID,
            qe1LineIntervalPerfNumber   INTEGER  (1..96),
            qe1LineIntervalPerfES       INTEGER,
            qe1LineIntervalPerfSES      INTEGER,
            qe1LineIntervalPerfBES      INTEGER,
            qe1LineIntervalPerfUAS      INTEGER,
            qe1LineIntervalPerfCSS      INTEGER,
            qe1LineIntervalPerfBPV      INTEGER,
            qe1LineIntervalPerfDMs      INTEGER,
            qe1LineIntvAvailable        INTEGER
        }

        qe1LIPSlotIndex  OBJECT-TYPE
            SYNTAX  LSSlotID
            ACCESS  read-only
            STATUS  mandatory
            DESCRIPTION
                "Qe1 slot"
            ::= { qe1LineIntervalPerfEntry 1 }

        qe1LIPPortIndex  OBJECT-TYPE
            SYNTAX  PortID
            ACCESS  read-only
            STATUS  mandatory
            DESCRIPTION
                "Port 1 to 4, total 4 ports."
            ::= { qe1LineIntervalPerfEntry 2 }

        qe1LineIntervalPerfNumber  OBJECT-TYPE
            SYNTAX  INTEGER (1..96)
            ACCESS  read-only
            STATUS  mandatory
            DESCRIPTION
                " Interval Index "
            ::= { qe1LineIntervalPerfEntry 3 }

        qe1LineIntervalPerfES  OBJECT-TYPE
            SYNTAX  INTEGER
            ACCESS  read-only
            STATUS  mandatory
            DESCRIPTION
                " ES Error Counter "
            ::= { qe1LineIntervalPerfEntry 4 }

        qe1LineIntervalPerfSES  OBJECT-TYPE
            SYNTAX  INTEGER
            ACCESS  read-only
            STATUS  mandatory
            DESCRIPTION
                " SES Error Counter "
            ::= { qe1LineIntervalPerfEntry 5 }

        qe1LineIntervalPerfBES  OBJECT-TYPE
            SYNTAX  INTEGER
            ACCESS  read-only
            STATUS  mandatory
            DESCRIPTION
                " BES Error Counter "
            ::= { qe1LineIntervalPerfEntry 6 }

        qe1LineIntervalPerfUAS  OBJECT-TYPE
            SYNTAX  INTEGER
            ACCESS  read-only
            STATUS  mandatory
            DESCRIPTION
                " UAS Error Counter "
            ::= { qe1LineIntervalPerfEntry 7 }

        qe1LineIntervalPerfCSS  OBJECT-TYPE
            SYNTAX  INTEGER
            ACCESS  read-only
            STATUS  mandatory
            DESCRIPTION
                " CSS Error Counter "
            ::= { qe1LineIntervalPerfEntry 8 }

        qe1LineIntervalPerfBPV  OBJECT-TYPE
            SYNTAX  INTEGER
            ACCESS  read-only
            STATUS  mandatory
            DESCRIPTION
                " BPV Error Counter "
            ::= { qe1LineIntervalPerfEntry 9 }

        qe1LineIntervalPerfDMs  OBJECT-TYPE
            SYNTAX  INTEGER
            ACCESS  read-only
            STATUS  mandatory
            DESCRIPTION
                " BPV Error Counter "
            ::= { qe1LineIntervalPerfEntry 10 }

        qe1LineIntvAvailable  OBJECT-TYPE
            SYNTAX  INTEGER   {
                    available(1),
                    na(2)
                }
            ACCESS  read-only
            STATUS  mandatory
            DESCRIPTION
                " Interval Available "
            ::= { qe1LineIntervalPerfEntry 11 }


--
--  Line Total Performance Table
--

        qe1LineTotalPerfTable  OBJECT-TYPE
            SYNTAX  SEQUENCE OF QE1LineTotalPerfEntry
            ACCESS  not-accessible
            STATUS  mandatory
            DESCRIPTION
                "Line Total Performance Table"
            ::= { qe1-card 12 }

        qe1LineTotalPerfEntry  OBJECT-TYPE
            SYNTAX  QE1LineTotalPerfEntry
            ACCESS  not-accessible
            STATUS  mandatory
            DESCRIPTION
                "Line total performance table"
            INDEX { qe1LTPSlotIndex , qe1LTPPortIndex }
            ::= { qe1LineTotalPerfTable 1 }

        QE1LineTotalPerfEntry ::= SEQUENCE  {
            qe1LTPSlotIndex             LSSlotID,
            qe1LTPPortIndex             PortID,
            qe1LineTotalPerfES          INTEGER,
            qe1LineTotalPerfSES         INTEGER,
            qe1LineTotalPerfBES         INTEGER,
            qe1LineTotalPerfUAS         INTEGER,
            qe1LineTotalPerfCSS         INTEGER,
            qe1LineTotalPerfBPV         INTEGER,
            qe1LineTotalPerfDMs         INTEGER
        }

        qe1LTPSlotIndex  OBJECT-TYPE
            SYNTAX  LSSlotID
            ACCESS  read-only
            STATUS  mandatory
            DESCRIPTION
                "Qe1 slot"
            ::= { qe1LineTotalPerfEntry 1 }

        qe1LTPPortIndex  OBJECT-TYPE
            SYNTAX  PortID
            ACCESS  read-only
            STATUS  mandatory
            DESCRIPTION
                "Port 1 to 4, total 4 ports."
            ::= { qe1LineTotalPerfEntry 2 }

        qe1LineTotalPerfES  OBJECT-TYPE
            SYNTAX  INTEGER
            ACCESS  read-only
            STATUS  mandatory
            DESCRIPTION
                " ES Error Counter "
            ::= { qe1LineTotalPerfEntry 3 }

        qe1LineTotalPerfSES  OBJECT-TYPE
            SYNTAX  INTEGER
            ACCESS  read-only
            STATUS  mandatory
            DESCRIPTION
                " SES Error Counter "
            ::= { qe1LineTotalPerfEntry 4 }

        qe1LineTotalPerfBES  OBJECT-TYPE
            SYNTAX  INTEGER
            ACCESS  read-only
            STATUS  mandatory
            DESCRIPTION
                " BES Error Counter "
            ::= { qe1LineTotalPerfEntry 5 }

        qe1LineTotalPerfUAS  OBJECT-TYPE
            SYNTAX  INTEGER
            ACCESS  read-only
            STATUS  mandatory
            DESCRIPTION
                " UAS Error Counter "
            ::= { qe1LineTotalPerfEntry 6 }

        qe1LineTotalPerfCSS  OBJECT-TYPE
            SYNTAX  INTEGER
            ACCESS  read-only
            STATUS  mandatory
            DESCRIPTION
                " CSS Error Counter "
            ::= { qe1LineTotalPerfEntry 7 }

        qe1LineTotalPerfBPV  OBJECT-TYPE
            SYNTAX  INTEGER
            ACCESS  read-only
            STATUS  mandatory
            DESCRIPTION
                " BPV Error Counter "
            ::= { qe1LineTotalPerfEntry 8 }

        qe1LineTotalPerfDMs  OBJECT-TYPE
            SYNTAX  INTEGER
            ACCESS  read-only
            STATUS  mandatory
            DESCRIPTION
                " DM Error Counter "
            ::= { qe1LineTotalPerfEntry 9 }


--
--  Line Seven Days Performance Table
--
        qe1Line7DaysPerfTable  OBJECT-TYPE
            SYNTAX  SEQUENCE OF QE1Line7DaysPerfEntry
            ACCESS  not-accessible
            STATUS  mandatory
            DESCRIPTION
                "Line 7 Days Performance Table"
            ::= { qe1-card 13 }

        qe1Line7DaysPerfEntry  OBJECT-TYPE
            SYNTAX  QE1Line7DaysPerfEntry
            ACCESS  not-accessible
            STATUS  mandatory
            DESCRIPTION
                "Line 7 days performance entry"
            INDEX { qe1LDPSlotIndex , qe1LDPPortIndex ,
                    qe1LineDaysIndex }
            ::= { qe1Line7DaysPerfTable 1 }

        QE1Line7DaysPerfEntry ::= SEQUENCE  {
            qe1LDPSlotIndex             LSSlotID,
            qe1LDPPortIndex             PortID,
            qe1LineDaysIndex            INTEGER (1..7),
            qe1LineDateStrIndex         DisplayString (SIZE (0..255) ),
            qe1LineSevenDaysPerfES      INTEGER,
            qe1LineSevenDaysPerfSES     INTEGER,
            qe1LineSevenDaysPerfBES     INTEGER,
            qe1LineSevenDaysPerfUAS     INTEGER,
            qe1LineSevenDaysPerfCSS     INTEGER,
            qe1LineSevenDaysPerfDMs     INTEGER,
            qe1LineSevenDaysPerfBPV     INTEGER
        }

        qe1LDPSlotIndex  OBJECT-TYPE
            SYNTAX  LSSlotID
            ACCESS  read-only
            STATUS  mandatory
            DESCRIPTION
                "Qe1 slot"
            ::= { qe1Line7DaysPerfEntry 1 }

        qe1LDPPortIndex  OBJECT-TYPE
            SYNTAX  PortID
            ACCESS  read-only
            STATUS  mandatory
            DESCRIPTION
                "Port 1 to 4, total 4 ports."
            ::= { qe1Line7DaysPerfEntry 2 }

        qe1LineDaysIndex  OBJECT-TYPE
            SYNTAX  INTEGER (1..7)
            ACCESS  read-only
            STATUS  mandatory
            DESCRIPTION
                "Seven Days index "
            ::= { qe1Line7DaysPerfEntry 3 }

        qe1LineDateStrIndex  OBJECT-TYPE
            SYNTAX  DisplayString (SIZE (0..255) )
            ACCESS  read-only
            STATUS  mandatory
            DESCRIPTION
                "Seven Days String "
            ::= { qe1Line7DaysPerfEntry 4 }

        qe1LineSevenDaysPerfES  OBJECT-TYPE
            SYNTAX  INTEGER
            ACCESS  read-only
            STATUS  mandatory
            DESCRIPTION
                " ES Error Counter "
            ::= { qe1Line7DaysPerfEntry 5 }

        qe1LineSevenDaysPerfSES  OBJECT-TYPE
            SYNTAX  INTEGER
            ACCESS  read-only
            STATUS  mandatory
            DESCRIPTION
                " SES Error Counter "
            ::= { qe1Line7DaysPerfEntry 6 }

        qe1LineSevenDaysPerfBES  OBJECT-TYPE
            SYNTAX  INTEGER
            ACCESS  read-only
            STATUS  mandatory
            DESCRIPTION
                " BES Error Counter "
            ::= { qe1Line7DaysPerfEntry 7 }

        qe1LineSevenDaysPerfUAS  OBJECT-TYPE
            SYNTAX  INTEGER
            ACCESS  read-only
            STATUS  mandatory
            DESCRIPTION
                " UAS Error Counter "
            ::= { qe1Line7DaysPerfEntry 8 }

        qe1LineSevenDaysPerfCSS  OBJECT-TYPE
            SYNTAX  INTEGER
            ACCESS  read-only
            STATUS  mandatory
            DESCRIPTION
                " CSS Error Counter "
            ::= { qe1Line7DaysPerfEntry 9 }

        qe1LineSevenDaysPerfDMs  OBJECT-TYPE
            SYNTAX  INTEGER
            ACCESS  read-only
            STATUS  mandatory
            DESCRIPTION
                " DM Error Counter "
            ::= { qe1Line7DaysPerfEntry 10 }

        qe1LineSevenDaysPerfBPV  OBJECT-TYPE
            SYNTAX  INTEGER
            ACCESS  read-only
            STATUS  mandatory
            DESCRIPTION
                " BPV Error Counter "
            ::= { qe1Line7DaysPerfEntry 11 }


--
--  Alarm Queue Table
--

--         qe1AlarmQueueTable  OBJECT-TYPE
--             SYNTAX  SEQUENCE OF QE1AlarmQueueEntry
--             ACCESS  not-accessible
--             STATUS  mandatory
--             DESCRIPTION
--                " Alarm Queue Table "
--             ::= { qe1-card 14 }
--
--         qe1AlarmQueueEntry  OBJECT-TYPE
--             SYNTAX  QE1AlarmQueueEntry
--             ACCESS  not-accessible
--             STATUS  mandatory
--             DESCRIPTION
--                "Alarm queue entry"
--             INDEX  { qe1AQSlotIndex, qe1AQPortIndex,
--                      qe1AlarmQueueIndex }
--             ::= { qe1AlarmQueueTable 1 }
--
--         QE1AlarmQueueEntry ::=
--             SEQUENCE {
--               qe1AlarmQueueIndex
--                 INTEGER (1..40),
--               qe1AlarmQueueString
--                 DisplayString (SIZE(0..255))
--             }
--
--         qe1AlarmQueueIndex  OBJECT-TYPE
--             SYNTAX  INTEGER (1..40)
--             ACCESS  read-only
--             STATUS  mandatory
--             DESCRIPTION
--                "Select Alarm Queue Index(1-40)"
--             ::= { qe1AlarmQueueEntry 2 }
--
--         qe1AlarmQueueString  OBJECT-TYPE
--             SYNTAX  DisplayString (SIZE (0..255))
--             ACCESS  read-only
--             STATUS  mandatory
--             DESCRIPTION
--                "Alarm Queue String"
--             ::= { qe1AlarmQueueEntry 3 }

--
--  Alarm History Table
--

        qe1AlarmHistoryTable  OBJECT-TYPE
            SYNTAX  SEQUENCE OF QE1AlarmHistoryEntry
            ACCESS  not-accessible
            STATUS  mandatory
            DESCRIPTION
                "Alarm History Table"
            ::= { qe1-card 15 }

        qe1AlarmHistoryEntry  OBJECT-TYPE
            SYNTAX  QE1AlarmHistoryEntry
            ACCESS  not-accessible
            STATUS  mandatory
            DESCRIPTION
                "Alarm history entry"
            INDEX { qe1AHSlotIndex , qe1AHPortIndex ,
                    qe1AlarmHistoryIndex }
            ::= { qe1AlarmHistoryTable 1 }

        QE1AlarmHistoryEntry ::= SEQUENCE {
            qe1AHSlotIndex              LSSlotID,
            qe1AHPortIndex              PortID,
            qe1AlarmHistoryIndex        INTEGER,
            qe1Threshold                INTEGER,
            qe1CurrentState             INTEGER,
            qe1CurrentCount             INTEGER,
            qe1Alarm                    LsAlarmSeverity
        }

        qe1AHSlotIndex  OBJECT-TYPE
            SYNTAX  LSSlotID
            ACCESS  read-only
            STATUS  mandatory
            DESCRIPTION
                "Qe1 slot"
            ::= { qe1AlarmHistoryEntry 1 }

        qe1AHPortIndex  OBJECT-TYPE
            SYNTAX  PortID
            ACCESS  read-only
            STATUS  mandatory
            DESCRIPTION
                "Port 1 to 4, total 4 ports."
            ::= { qe1AlarmHistoryEntry 2 }

        qe1AlarmHistoryIndex  OBJECT-TYPE
            SYNTAX  INTEGER {
                    rai-line(1),
                    ais-line(2),
                    los-line(3),
                    lof-line(4),
                    bpv-line(5),
                    ess-line(6),
                    uas-line(7),
                    css-line(8)
                }
            ACCESS  read-only
            STATUS  mandatory
            DESCRIPTION
                " Alarm History Index "
            ::= { qe1AlarmHistoryEntry 3 }

        qe1Threshold  OBJECT-TYPE
            SYNTAX  INTEGER
            ACCESS  read-only
            STATUS  mandatory
            DESCRIPTION
                " Alarm History Threshold Value "
            ::= { qe1AlarmHistoryEntry 4 }

        qe1CurrentState  OBJECT-TYPE
            SYNTAX  INTEGER {
                    ok(1),
                    alarm(2),
                    disable(3),
                    portDisabled(4)
                }
            ACCESS  read-only
            STATUS  mandatory
            DESCRIPTION
                " Alarm History Current State"
            ::= { qe1AlarmHistoryEntry 5 }

        qe1CurrentCount  OBJECT-TYPE
            SYNTAX  INTEGER
            ACCESS  read-only
            STATUS  mandatory
            DESCRIPTION
                " Alarm History Current Count "
            ::= { qe1AlarmHistoryEntry 6 }

        qe1Alarm  OBJECT-TYPE
            SYNTAX  LsAlarmSeverity
            ACCESS  read-only
            STATUS  mandatory
            DESCRIPTION
                "Alarm History Alarm State"
            ::= { qe1AlarmHistoryEntry 7 }


--
--  Line Availability Table
--

        qe1LineAvailabilityTable  OBJECT-TYPE
            SYNTAX  SEQUENCE OF QE1LineAvailabilityEntry
            ACCESS  not-accessible
            STATUS  mandatory
            DESCRIPTION
                "The DS1 line control table."
            ::= { qe1-card 16 }

        qe1LineAvailabilityEntry  OBJECT-TYPE
            SYNTAX  QE1LineAvailabilityEntry
            ACCESS  not-accessible
            STATUS  mandatory
            DESCRIPTION
                "An entry in the DS1 line control table."
            INDEX { qe1LASlotIndex , qe1LAPortIndex }
            ::= { qe1LineAvailabilityTable 1 }

        QE1LineAvailabilityEntry ::= SEQUENCE {
            qe1LASlotIndex              LSSlotID,
            qe1LAPortIndex              PortID,
            qe1AvailableSeconds         DisplayString,
            qe1UnavailableSeconds       DisplayString,
            qe1LineAvailability         DisplayString
        }

        qe1LASlotIndex  OBJECT-TYPE
            SYNTAX  LSSlotID
            ACCESS  read-only
            STATUS  mandatory
            DESCRIPTION
                "Qe1 slot"
            ::= { qe1LineAvailabilityEntry 1 }

        qe1LAPortIndex  OBJECT-TYPE
            SYNTAX  PortID
            ACCESS  read-only
            STATUS  mandatory
            DESCRIPTION
                "Port 1 to 4, total 4 ports."
            ::= { qe1LineAvailabilityEntry 2 }

        qe1AvailableSeconds  OBJECT-TYPE
            SYNTAX  DisplayString (SIZE(0..255))
            ACCESS  read-only
            STATUS  mandatory
            DESCRIPTION
                "Line Available Seconds"
            ::= { qe1LineAvailabilityEntry 3 }

        qe1UnavailableSeconds  OBJECT-TYPE
            SYNTAX  DisplayString (SIZE(0..255))
            ACCESS  read-only
            STATUS  mandatory
            DESCRIPTION
                "Line Unavailable Seconds"
            ::= { qe1LineAvailabilityEntry 4 }

        qe1LineAvailability  OBJECT-TYPE
            SYNTAX  DisplayString (SIZE(0..255))
            ACCESS  read-only
            STATUS  mandatory
            DESCRIPTION
                "Line Available Percentage"
            ::= { qe1LineAvailabilityEntry 5 }


--
--  Alarm Control Table
--

        qe1AlarmControlTable  OBJECT-TYPE
            SYNTAX  SEQUENCE OF QE1AlarmControlEntry
            ACCESS  not-accessible
            STATUS  mandatory
            DESCRIPTION
                "The alarm control table."
            ::= { qe1-card 17 }

        qe1AlarmControlEntry  OBJECT-TYPE
            SYNTAX  QE1AlarmControlEntry
            ACCESS  not-accessible
            STATUS  mandatory
            DESCRIPTION
                "An entry in the DS1 alarm control table."
            INDEX { qe1ACSlotIndex , qe1ACPortIndex }
            ::= { qe1AlarmControlTable 1 }

        QE1AlarmControlEntry ::= SEQUENCE {
            qe1ACSlotIndex              LSSlotID,
            qe1ACPortIndex              PortID,
            qe1RAI-Line                 LsAlarmSeverity,
            qe1AIS-Line                 LsAlarmSeverity,
            qe1LOS-Line                 LsAlarmSeverity,
            qe1LOF-Line                 LsAlarmSeverity,
            qe1BPV-Line                 LsAlarmSeverity,
            qe1ESS-Line                 LsAlarmSeverity,
            qe1UAS-Line                 LsAlarmSeverity,
            qe1CSS-Line                 LsAlarmSeverity
        }

        qe1ACSlotIndex  OBJECT-TYPE
            SYNTAX  LSSlotID
            ACCESS  read-only
            STATUS  mandatory
            DESCRIPTION
                "Qe1 slot"
            ::= { qe1AlarmControlEntry 1 }

        qe1ACPortIndex  OBJECT-TYPE
            SYNTAX  PortID
            ACCESS  read-only
            STATUS  mandatory
            DESCRIPTION
                "Port 1 to 4, total 4 ports."
            ::= { qe1AlarmControlEntry 2 }

        qe1RAI-Line  OBJECT-TYPE
            SYNTAX  LsAlarmSeverity
            ACCESS  read-write
            STATUS  mandatory
            DESCRIPTION
                "RAI-Line State"
            ::= { qe1AlarmControlEntry 3 }

        qe1AIS-Line  OBJECT-TYPE
            SYNTAX  LsAlarmSeverity
            ACCESS  read-write
            STATUS  mandatory
            DESCRIPTION
                "AIS-Line State"
            ::= { qe1AlarmControlEntry 4 }

        qe1LOS-Line  OBJECT-TYPE
            SYNTAX  LsAlarmSeverity
            ACCESS  read-write
            STATUS  mandatory
            DESCRIPTION
                "LOS-line State"
            ::= { qe1AlarmControlEntry 5 }

        qe1LOF-Line  OBJECT-TYPE
            SYNTAX  LsAlarmSeverity
            ACCESS  read-write
            STATUS  mandatory
            DESCRIPTION
                "LOF-Line State"
            ::= { qe1AlarmControlEntry 6 }

        qe1BPV-Line  OBJECT-TYPE
            SYNTAX  LsAlarmSeverity
            ACCESS  read-write
            STATUS  mandatory
            DESCRIPTION
                "BPV-Line State"
            ::= { qe1AlarmControlEntry 7 }

        qe1ESS-Line  OBJECT-TYPE
            SYNTAX  LsAlarmSeverity
            ACCESS  read-write
            STATUS  mandatory
            DESCRIPTION
                "ESS-Line State"
            ::= { qe1AlarmControlEntry 8 }

        qe1UAS-Line  OBJECT-TYPE
            SYNTAX  LsAlarmSeverity
            ACCESS  read-write
            STATUS  mandatory
            DESCRIPTION
                "UAS-Line State"
            ::= { qe1AlarmControlEntry 9 }

        qe1CSS-Line  OBJECT-TYPE
            SYNTAX  LsAlarmSeverity
            ACCESS  read-write
            STATUS  mandatory
            DESCRIPTION
                "CS-Line State"
            ::= { qe1AlarmControlEntry 10 }


--
--  Threshold Control Table
--

        qe1ThresholdControlTable  OBJECT-TYPE
            SYNTAX  SEQUENCE OF QE1ThresholdControlEntry
            ACCESS  not-accessible
            STATUS  mandatory
            DESCRIPTION
                "The alarm control table."
            ::= { qe1-card 18 }

        qe1ThresholdControlEntry  OBJECT-TYPE
            SYNTAX  QE1ThresholdControlEntry
            ACCESS  not-accessible
            STATUS  mandatory
            DESCRIPTION
                "An entry in the DS1 threshold control table."
            INDEX { qe1TCSlotIndex , qe1TCPortIndex }
            ::= { qe1ThresholdControlTable 1 }

        QE1ThresholdControlEntry ::= SEQUENCE {
            qe1TCSlotIndex              LSSlotID,
            qe1TCPortIndex              PortID,
            qe1ThresholdBPV-Line        INTEGER,
            qe1ThresholdESS-Line        INTEGER,
            qe1ThresholdUAS-Line        INTEGER,
            qe1ThresholdCSS-Line        INTEGER
        }

        qe1TCSlotIndex  OBJECT-TYPE
            SYNTAX  LSSlotID
            ACCESS  read-only
            STATUS  mandatory
            DESCRIPTION
                "Qe1 slot"
            ::= { qe1ThresholdControlEntry 1 }

        qe1TCPortIndex  OBJECT-TYPE
            SYNTAX  PortID
            ACCESS  read-only
            STATUS  mandatory
            DESCRIPTION
                "Port 1 to 4, total 4 ports."
            ::= { qe1ThresholdControlEntry 2 }

        qe1ThresholdBPV-Line  OBJECT-TYPE
            SYNTAX  INTEGER
            ACCESS  read-write
            STATUS  mandatory
            DESCRIPTION
                " Threshold of BPV-Line "
            ::= { qe1ThresholdControlEntry 3 }

        qe1ThresholdESS-Line  OBJECT-TYPE
            SYNTAX  INTEGER
            ACCESS  read-write
            STATUS  mandatory
            DESCRIPTION
                " Threshold of ESS-Line "
            ::= { qe1ThresholdControlEntry 4 }

        qe1ThresholdUAS-Line  OBJECT-TYPE
            SYNTAX  INTEGER
            ACCESS  read-write
            STATUS  mandatory
            DESCRIPTION
                " Threshold of UAS-Line "
            ::= { qe1ThresholdControlEntry 5 }

        qe1ThresholdCSS-Line  OBJECT-TYPE
            SYNTAX  INTEGER
            ACCESS  read-write
            STATUS  mandatory
            DESCRIPTION
                " Threshold of CS-Line "
            ::= { qe1ThresholdControlEntry 6 }


--
-- Line Diagnostic Control Table
--

        qe1LineDiagControlTable  OBJECT-TYPE
            SYNTAX  SEQUENCE OF QE1LineDiagControlEntry
            ACCESS  not-accessible
            STATUS  mandatory
            DESCRIPTION
                "The alarm control table."
            ::= { qe1-card 19 }

        qe1LineDiagControlEntry  OBJECT-TYPE
            SYNTAX  QE1LineDiagControlEntry
            ACCESS  not-accessible
            STATUS  mandatory
            DESCRIPTION
                "An entry in the DS1 threshold control table."
            INDEX { qe1DCSlotIndex , qe1DCPortIndex }
            ::= { qe1LineDiagControlTable 1 }

        QE1LineDiagControlEntry ::= SEQUENCE {
            qe1DCSlotIndex              LSSlotID,
            qe1DCPortIndex              PortID,
            qe1LoopbackType             INTEGER,
            qe1LoopbackStatus           INTEGER,
            qe1PRBSControl              INTEGER,
            qe1PRBSStatus               INTEGER,
            qe1PRBSElapseSeconds        INTEGER,
            qe1PRBSErrorSeconds         INTEGER,
            qe1PRBSErrorCounts          INTEGER,
            qe1InbandLoopbackPeriod     INTEGER
        }

        qe1DCSlotIndex  OBJECT-TYPE
            SYNTAX  LSSlotID
            ACCESS  read-only
            STATUS  mandatory
            DESCRIPTION
                "Qe1 slot"
            ::= { qe1LineDiagControlEntry 1 }

        qe1DCPortIndex  OBJECT-TYPE
            SYNTAX  PortID
            ACCESS  read-only
            STATUS  mandatory
            DESCRIPTION
                "Port 1 to 4, total 4 ports."
            ::= { qe1LineDiagControlEntry 2 }

        qe1LoopbackType  OBJECT-TYPE
            SYNTAX  INTEGER {
                    no-loopback(1),
                    local-loopback(2),
                    payload-loopback(3),
                    line-loopback(4),
                    remote-PLB-Active(5),
                    remote-LLB-Active(6),
                    remote-PLB-Deactive(7),
                    remote-LLB-Deactive(8)
                }
            ACCESS  read-write
            STATUS  mandatory
            DESCRIPTION
                "qe1 Loopback Type"
            ::= { qe1LineDiagControlEntry 3 }

        qe1LoopbackStatus  OBJECT-TYPE
            SYNTAX  INTEGER {
                    success(1),
                    fail(2),
                    loopback-not-active(3)
                }
            ACCESS  read-only
            STATUS  mandatory
            DESCRIPTION
                "qe1 Loopback Status"
            ::= { qe1LineDiagControlEntry 4 }

        qe1PRBSControl  OBJECT-TYPE
            SYNTAX  INTEGER {
                    prbs-deactive(1),
                    prbs-active-full(2),
                    prbs-reset-error-count(3),
                    prbs-inject-error(4)
                }
            ACCESS  read-write
            STATUS  mandatory
            DESCRIPTION
                "qe1 PRBS Control"
            ::= { qe1LineDiagControlEntry 5 }

        qe1PRBSStatus  OBJECT-TYPE
            SYNTAX  INTEGER {
                    prbs-sync(1),
                    prbs-unsync(2),
                    prbs-not-active(3)
                }
            ACCESS  read-only
            STATUS  mandatory
            DESCRIPTION
                "qe1 PRBS Status"
            ::= { qe1LineDiagControlEntry 6 }

        qe1PRBSElapseSeconds  OBJECT-TYPE
            SYNTAX  INTEGER
            ACCESS  read-only
            STATUS  mandatory
            DESCRIPTION
                "qe1 PRBS Elapse Seconds"
            ::= { qe1LineDiagControlEntry 7 }

        qe1PRBSErrorSeconds  OBJECT-TYPE
            SYNTAX  INTEGER
            ACCESS  read-only
            STATUS  mandatory
            DESCRIPTION
                "qe1 PRBS Error Seconds"
            ::= { qe1LineDiagControlEntry 8 }

        qe1PRBSErrorCounts  OBJECT-TYPE
            SYNTAX  INTEGER
            ACCESS  read-only
            STATUS  mandatory
            DESCRIPTION
                "qe1 PRBS Error Counts"
            ::= { qe1LineDiagControlEntry 9 }

        qe1InbandLoopbackPeriod  OBJECT-TYPE
            SYNTAX  INTEGER
            ACCESS  read-write
            STATUS  mandatory
            DESCRIPTION
                "period(in seconds) of QE1 inband local, payload, or line loopback"
            ::= { qe1LineDiagControlEntry 10 }

--
--  Command Control Table
--

        qe1CommandControlTable  OBJECT-TYPE
            SYNTAX  SEQUENCE OF QE1CommandControlEntry
            ACCESS  not-accessible
            STATUS  mandatory
            DESCRIPTION
                "The command control table."
            ::= { qe1-card 20 }

        qe1CommandControlEntry  OBJECT-TYPE
            SYNTAX  QE1CommandControlEntry
            ACCESS  not-accessible
            STATUS  mandatory
            DESCRIPTION
                "An entry in the command control table."
            INDEX { qe1CCSlotIndex , qe1CCPortIndex }
            ::= { qe1CommandControlTable 1 }

        QE1CommandControlEntry ::= SEQUENCE {
            qe1CCSlotIndex              LSSlotID,
            qe1CCPortIndex              PortID,
            qe1UserPerfReset            INTEGER,
--               qe1AlarmHistoryReset
--                 INTEGER,
            qe1PortReset                INTEGER,
            qe1PortLoadDefault          INTEGER
        }

        qe1CCSlotIndex  OBJECT-TYPE
            SYNTAX  LSSlotID
            ACCESS  read-only
            STATUS  mandatory
            DESCRIPTION
                "Qe1 slot"
            ::= { qe1CommandControlEntry 1 }

        qe1CCPortIndex  OBJECT-TYPE
            SYNTAX  PortID
            ACCESS  read-only
            STATUS  mandatory
            DESCRIPTION
                "Port 1 to 4, total 4 ports."
            ::= { qe1CommandControlEntry 2 }

        qe1UserPerfReset    OBJECT-TYPE
            SYNTAX  INTEGER {
                    reset(1)
                }
            ACCESS  read-write
            STATUS  mandatory
            DESCRIPTION
                "Command: Reset User Performance"
            ::= { qe1CommandControlEntry 4 }

--         qe1AlarmHistoryReset    OBJECT-TYPE
--             SYNTAX  INTEGER {
--                         reset(1)
--                     }
--             ACCESS  read-write
--             STATUS  mandatory
--             DESCRIPTION
--                "Command: Reset Alarm History"
--             ::= { qe1CommandControlEntry 5 }

        qe1PortReset    OBJECT-TYPE
            SYNTAX  INTEGER {
                    reset(1)
                }
            ACCESS  read-write
            STATUS  mandatory
            DESCRIPTION
                "Command: Reset QE1 Port"
            ::= { qe1CommandControlEntry 6 }

        qe1PortLoadDefault    OBJECT-TYPE
            SYNTAX  INTEGER {
                    load-default(1)
                }
            ACCESS  read-write
            STATUS  mandatory
            DESCRIPTION
                "Command: Load Default QE1 Port"
            ::= { qe1CommandControlEntry 7 }


--
--  SYSTEM Information Table
--

        qe1SystemInfoTable  OBJECT-TYPE
            SYNTAX  SEQUENCE OF QE1SystemInformationEntry
            ACCESS  not-accessible
            STATUS  mandatory
            DESCRIPTION
                "The system information table."
            ::= { qe1-card 21 }

        qe1SystemInformationEntry  OBJECT-TYPE
            SYNTAX  QE1SystemInformationEntry
            ACCESS  not-accessible
            STATUS  mandatory
            DESCRIPTION
                "An entry in the system information table."
            INDEX { qe1SISlotIndex }
            ::= { qe1SystemInfoTable 1 }

        QE1SystemInformationEntry ::= SEQUENCE {
            qe1SISlotIndex              LSSlotID,
            qe1PROMVersion              DisplayString,
            qe1HardwareVersion          DisplayString
        }

        qe1SISlotIndex  OBJECT-TYPE
            SYNTAX  LSSlotID
            ACCESS  read-only
            STATUS  mandatory
            DESCRIPTION
                "Qe1 slot"
            ::= { qe1SystemInformationEntry 1 }

        qe1PROMVersion  OBJECT-TYPE
            SYNTAX  DisplayString (SIZE (0..255) )
            ACCESS  read-only
            STATUS  mandatory
            DESCRIPTION
                " qe1 PROM Version"
            ::= { qe1SystemInformationEntry 2 }

        qe1HardwareVersion  OBJECT-TYPE
            SYNTAX  DisplayString (SIZE (0..255) )
            ACCESS  read-only
            STATUS  mandatory
            DESCRIPTION
                " qe1 Hardware Version"
            ::= { qe1SystemInformationEntry 3 }


--
--  QE1 Customer Information Table
--

        qe1CustomerInfoTable  OBJECT-TYPE
            SYNTAX  SEQUENCE OF QE1CustomerInfoEntry
            ACCESS  not-accessible
            STATUS  mandatory
            DESCRIPTION
                "The Customer Information table."
            ::= { qe1-card 99 }

        qe1CustomerInfoEntry  OBJECT-TYPE
            SYNTAX  QE1CustomerInfoEntry
            ACCESS  not-accessible
            STATUS  mandatory
            DESCRIPTION
                "An entry in the Customer Information table."
            INDEX { qe1CISlotIndex , qe1CIPortIndex }
            ::= { qe1CustomerInfoTable 1 }

        QE1CustomerInfoEntry ::= SEQUENCE {
            qe1CISlotIndex              LSSlotID,
            qe1CIPortIndex              PortID,
            qe1CICustomerInfo           DisplayString (SIZE(0..64))
        }

        qe1CISlotIndex    OBJECT-TYPE
            SYNTAX  LSSlotID
            ACCESS  read-only
            STATUS  mandatory
            DESCRIPTION
                "QE1 slot index"
            ::= { qe1CustomerInfoEntry 1 }

        qe1CIPortIndex    OBJECT-TYPE
            SYNTAX  PortID
            ACCESS  read-only
            STATUS  mandatory
            DESCRIPTION
                "Port number"
            ::= { qe1CustomerInfoEntry 2 }

        qe1CICustomerInfo  OBJECT-TYPE
            SYNTAX  DisplayString (SIZE (0..64) )
            ACCESS  read-write
            STATUS  mandatory
            DESCRIPTION
                "Customer information"
            ::= { qe1CustomerInfoEntry 3 }


--
--  Remote Link Identification Table
--

        qe1RemoteLinkIDTable  OBJECT-TYPE
            SYNTAX  SEQUENCE OF QE1RemoteLinkIDEntry
            ACCESS  not-accessible
            STATUS  mandatory
            DESCRIPTION
                "Remote Link Identification Table"
            ::= { qe1-card 22 }

        qe1RemoteLinkIDEntry  OBJECT-TYPE
            SYNTAX  QE1RemoteLinkIDEntry
            ACCESS  not-accessible
            STATUS  mandatory
            DESCRIPTION
                "Remote Link Identification entry"
            INDEX { qe1RLSlotIndex ,
                    qe1RLPortIndex }
            ::= { qe1RemoteLinkIDTable 1 }

        QE1RemoteLinkIDEntry ::= SEQUENCE {
            qe1RLSlotIndex              LSSlotID,
            qe1RLPortIndex              PortID,
            qe1RemoteLinkIDType         INTEGER,
            qe1RemoteLinkIDRack         INTEGER,
            qe1RemoteLinkIDSlotNumber   INTEGER,
            qe1RemoteLinkIDPort         INTEGER,
            qe1RemoteLinkIDSerialNumber INTEGER,
            qe1RemoteLinkIDBackupSlotNUM    INTEGER,
            qe1RemoteLinkIDBackupPort       INTEGER
        }

        qe1RLSlotIndex  OBJECT-TYPE
            SYNTAX  LSSlotID
            ACCESS  read-only
            STATUS  mandatory
            DESCRIPTION
                "Qe1 slot"
            ::= { qe1RemoteLinkIDEntry 1 }

        qe1RLPortIndex  OBJECT-TYPE
            SYNTAX  PortID
            ACCESS  read-only
            STATUS  mandatory
            DESCRIPTION
                "Port 1 to 4, total 4 ports."
            ::= { qe1RemoteLinkIDEntry 2 }

        qe1RemoteLinkIDType  OBJECT-TYPE
            SYNTAX  INTEGER {
                    notAvailable(0),
                    cpe(1),
                    an(2)
                }
            ACCESS  read-only
            STATUS  mandatory
            DESCRIPTION
                "Type of remote site."
            ::= { qe1RemoteLinkIDEntry 3 }

        qe1RemoteLinkIDRack  OBJECT-TYPE
            SYNTAX  INTEGER {
                    notAvailable(0)
                }
            ACCESS  read-only
            STATUS  mandatory
            DESCRIPTION
                "Remote Link Identification Rack"
            ::= { qe1RemoteLinkIDEntry 4 }

        qe1RemoteLinkIDSlotNumber  OBJECT-TYPE
            SYNTAX  INTEGER {
                    notAvailable(0)
                }
            ACCESS  read-only
            STATUS  mandatory
            DESCRIPTION
                "Remote Link Identification SlotNumber"
            ::= { qe1RemoteLinkIDEntry 5 }

        qe1RemoteLinkIDPort  OBJECT-TYPE
            SYNTAX  INTEGER {
                    notAvailable(0)
                }
            ACCESS  read-only
            STATUS  mandatory
            DESCRIPTION
                "Remote Link Identification Port"
            ::= { qe1RemoteLinkIDEntry 6 }

        qe1RemoteLinkIDSerialNumber  OBJECT-TYPE
            SYNTAX  INTEGER {
                    notAvailable(0)
                }
            ACCESS  read-only
            STATUS  mandatory
            DESCRIPTION
                "Remote Link Identification Serial Number"
            ::= { qe1RemoteLinkIDEntry 7 }

        qe1RemoteLinkIDBackupSlotNUM  OBJECT-TYPE
            SYNTAX  INTEGER {
                    notAvailable(0)
                }
            ACCESS  read-only
            STATUS  mandatory
            DESCRIPTION
                "Remote Link Identification Backup Slot Number"
            ::= { qe1RemoteLinkIDEntry 8 }

        qe1RemoteLinkIDBackupPort  OBJECT-TYPE
            SYNTAX  INTEGER {
                    notAvailable(0)
                }
            ACCESS  read-only
            STATUS  mandatory
            DESCRIPTION
                "Remote Link Identification Backup Port"
            ::= { qe1RemoteLinkIDEntry 9 }

        qe1TotalCard   OBJECT-TYPE
            SYNTAX  INTEGER
            ACCESS  read-only
            STATUS  mandatory
            DESCRIPTION
                "Total cards of QE1"
            ::= { qe1-card 100 }


--======================================================================--
--======================================================================--
--  quad-t1-card MIB
--======================================================================--
--======================================================================--


--
--  Line Control Table
--

        qt1LineControlTable  OBJECT-TYPE
            SYNTAX  SEQUENCE OF QT1LineControlEntry
            ACCESS  not-accessible
            STATUS  mandatory
            DESCRIPTION
                "The DS1 line control table."
            ::= { qt1-card 1 }

        qt1LineControlEntry  OBJECT-TYPE
            SYNTAX  QT1LineControlEntry
            ACCESS  not-accessible
            STATUS  mandatory
            DESCRIPTION
                "An entry in the DS1 line control table."
            INDEX { qt1LCSlotIndex , qt1LCPortIndex }
            ::= { qt1LineControlTable 1 }

        QT1LineControlEntry ::= SEQUENCE  {
            qt1LCSlotIndex              LSSlotID,
            qt1LCPortIndex              PortID,
            qt1LineFrame                INTEGER,
            qt1LineCoding               INTEGER,
            qt1Interface                INTEGER,
            qt1LineBuildOut             INTEGER,
            qt1Equalizer                INTEGER,
            qt1AIS                      INTEGER,
            qt1YEL                      INTEGER,
            qt1Inband                   INTEGER,
            qt1IdleCode                 INTEGER,
            qt1CASMode                  INTEGER,
            qt1SignallingMode           INTEGER,
            qt1CGA                      INTEGER,
            qt1OutOfService             INTEGER,
            qt1FDL                      INTEGER,
            qt1Protect                  INTEGER,
            qt1Master                   INTEGER,
            qt1PortEnable               INTEGER
        }

        qt1LCSlotIndex  OBJECT-TYPE
            SYNTAX  LSSlotID
            ACCESS  read-only
            STATUS  mandatory
            DESCRIPTION
                "Qt1 slot"
            ::= { qt1LineControlEntry 1 }

        qt1LCPortIndex  OBJECT-TYPE
            SYNTAX  PortID
            ACCESS  read-only
            STATUS  mandatory
            DESCRIPTION
                "Port 1 to 4, total 4 ports."
            ::= { qt1LineControlEntry 2 }

        qt1LineFrame  OBJECT-TYPE
            SYNTAX  INTEGER   {
                    d4(1),
                    esf(2),
                    esf-t1-403(3),
                    none(4)
                }
            ACCESS  read-write
            STATUS  mandatory
            DESCRIPTION
                "Line frame format"
            ::= { qt1LineControlEntry 3 }

        qt1LineCoding  OBJECT-TYPE
            SYNTAX  INTEGER   {
                    ami(1),
                    b8zs(2)
                }
            ACCESS  read-write
            STATUS  mandatory
            DESCRIPTION
                "Line Coding type"
            ::= { qt1LineControlEntry 4 }

        qt1Interface  OBJECT-TYPE
            SYNTAX  INTEGER   {
                    long-haul(1),
                    short-haul(2)
                }
            ACCESS  read-write
            STATUS  mandatory
            DESCRIPTION
                "Interface indicates that QT1 line use Long/Short haul."
            ::= { qt1LineControlEntry 5 }

        qt1LineBuildOut  OBJECT-TYPE
            SYNTAX  INTEGER   {
                    lbo-0-0dB(1),
                    lbo-7-5dB(2),
                    lbo-15dB(3)
--                        lbo-0.0dB(1),
--                        lbo-7.5dB(2),
--                        lbo-15dB(3)
                }
            ACCESS  read-write
            STATUS  mandatory
            DESCRIPTION
                "QT1 line build out."
            ::= { qt1LineControlEntry 6 }

        qt1Equalizer  OBJECT-TYPE
            SYNTAX  INTEGER   {
                    equ-0-110Ft(1),
                    equ-110-220ft(2),
                    equ-220-330ft(3),
                    equ-330-440ft(4),
                    equ-440-550ft(5),
                    equ-550-660ft(6)
                }
            ACCESS  read-write
            STATUS  mandatory
            DESCRIPTION
                "QT1 line equalizer."
            ::= { qt1LineControlEntry 7 }

        qt1AIS  OBJECT-TYPE
            SYNTAX  INTEGER   {
                    frame(1),
--                    unframe(2),
                    off(3)
                }
            ACCESS  read-write
            STATUS  mandatory
            DESCRIPTION
                "QT1 line Alarm Indication Signal."
            ::= { qt1LineControlEntry 8 }

        qt1YEL  OBJECT-TYPE
            SYNTAX  INTEGER   {
                    on(1),
                    off(2)
                }
            ACCESS  read-write
            STATUS  mandatory
            DESCRIPTION
                "YEL-ON indicates that yellow alarm ON."
            ::= { qt1LineControlEntry 9 }

        qt1Inband  OBJECT-TYPE
            SYNTAX  INTEGER   {
                    on(1),
                    off(2)
                }
            ACCESS  read-write
            STATUS  mandatory
            DESCRIPTION
                "QT1 line inband ON/OFF"
            ::= { qt1LineControlEntry 10 }

        qt1IdleCode  OBJECT-TYPE
            SYNTAX  INTEGER
            ACCESS  read-write
            STATUS  mandatory
            DESCRIPTION
                "Line Idle Code Value"
            ::= { qt1LineControlEntry 11 }

        qt1CASMode  OBJECT-TYPE
            SYNTAX  INTEGER   {
                    on(1),
                    off(2)
                }
            ACCESS  read-write
            STATUS  mandatory
            DESCRIPTION
                "CAS or CCS"
            ::= { qt1LineControlEntry 12 }

        qt1SignallingMode  OBJECT-TYPE
            SYNTAX  INTEGER   {
                    trans(1)
                }
            ACCESS  read-write
            STATUS  mandatory
            DESCRIPTION
                "TRANS"
            ::= { qt1LineControlEntry 13 }

        qt1CGA  OBJECT-TYPE
            SYNTAX  INTEGER   {
                    norm(1)
                }
            ACCESS  read-write
            STATUS  mandatory
            DESCRIPTION
                "Method used to signal the Carrier Group Alarm state
                to the other end of the selected link."
            ::= { qt1LineControlEntry 14 }

        qt1OutOfService  OBJECT-TYPE
            SYNTAX  INTEGER   {
                    busy(1),
                    idle(2),
                    ais(3)
                }
            ACCESS  read-write
            STATUS  mandatory
            DESCRIPTION
                "When NORM (CGA) is select, the parameter determines the
                state of the A, B signaling bits during the
                Out-of-Service periods."
            ::= { qt1LineControlEntry 15 }

        qt1FDL  OBJECT-TYPE
            SYNTAX  INTEGER   {
                    on(1),
                    off(2)
                }
            ACCESS  read-write
            STATUS  mandatory
            DESCRIPTION
                "QT1 Facility Data Link ON/OFF"
            ::= { qt1LineControlEntry 16 }

        qt1Protect  OBJECT-TYPE
            SYNTAX  INTEGER   {
                    disable(1),
                    circuit(2),
                    line(3)
                }
            ACCESS  read-only
            STATUS  mandatory
            DESCRIPTION
                "disable or enable."
            ::= { qt1LineControlEntry 17 }

        qt1Master  OBJECT-TYPE
            SYNTAX  INTEGER   {
                    xxxx(1),
                    slave(2),
                    master(3)
                }
            ACCESS  read-only
            STATUS  mandatory
            DESCRIPTION
                "master or slave"
            ::= { qt1LineControlEntry 18 }

        qt1PortEnable  OBJECT-TYPE
            SYNTAX  INTEGER   {
                    disable(1),
                    enable(2)
                }
            ACCESS  read-write
            STATUS  mandatory
            DESCRIPTION
                "QT1 port enable/disable"
            ::= { qt1LineControlEntry 19 }


--
--  User Current Performance Table
--

        qt1UserCurrentPerfTable  OBJECT-TYPE
            SYNTAX  SEQUENCE OF QT1UserCurrentPerfEntry
            ACCESS  not-accessible
            STATUS  mandatory
            DESCRIPTION
                "User Current Performance Table"
            ::= { qt1-card 2 }

        qt1UserCurrentPerfEntry  OBJECT-TYPE
            SYNTAX  QT1UserCurrentPerfEntry
            ACCESS  not-accessible
            STATUS  mandatory
            DESCRIPTION
                "User current performance entry"
            INDEX { qt1UCPSlotIndex , qt1UCPPortIndex }
            ::= { qt1UserCurrentPerfTable 1 }

        QT1UserCurrentPerfEntry ::= SEQUENCE  {
            qt1UCPSlotIndex             LSSlotID,
            qt1UCPPortIndex             PortID,
            qt1UserCurrentPerfES        INTEGER,
            qt1UserCurrentPerfSES       INTEGER,
            qt1UserCurrentPerfBES       INTEGER,
            qt1UserCurrentPerfUAS       INTEGER,
            qt1UserCurrentPerfCSS       INTEGER,
            qt1UserCurrentPerfBPV       INTEGER,
            qt1UserCurrentPerfLOFC      INTEGER,
            qt1UserCurr15MinTimeElapsed INTEGER,
            qt1UserValid15MinInterval   INTEGER
        }

        qt1UCPSlotIndex  OBJECT-TYPE
            SYNTAX  LSSlotID
            ACCESS  read-only
            STATUS  mandatory
            DESCRIPTION
                "Qt1 slot"
            ::= { qt1UserCurrentPerfEntry 1 }

        qt1UCPPortIndex  OBJECT-TYPE
            SYNTAX  PortID
            ACCESS  read-only
            STATUS  mandatory
            DESCRIPTION
                "Port 1 to 4, total 4 ports."
            ::= { qt1UserCurrentPerfEntry 2 }

        qt1UserCurrentPerfES  OBJECT-TYPE
            SYNTAX  INTEGER
            ACCESS  read-only
            STATUS  mandatory
            DESCRIPTION
                " ES Error Counter "
            ::= { qt1UserCurrentPerfEntry 3 }

        qt1UserCurrentPerfSES  OBJECT-TYPE
            SYNTAX  INTEGER
            ACCESS  read-only
            STATUS  mandatory
            DESCRIPTION
                " SES Error Counter "
            ::= { qt1UserCurrentPerfEntry 4 }

        qt1UserCurrentPerfBES  OBJECT-TYPE
            SYNTAX  INTEGER
            ACCESS  read-only
            STATUS  mandatory
            DESCRIPTION
                " BES Error Counter "
            ::= { qt1UserCurrentPerfEntry 5 }

        qt1UserCurrentPerfUAS  OBJECT-TYPE
            SYNTAX  INTEGER
            ACCESS  read-only
            STATUS  mandatory
            DESCRIPTION
                " UAS Error Counter "
            ::= { qt1UserCurrentPerfEntry 6 }

        qt1UserCurrentPerfCSS  OBJECT-TYPE
            SYNTAX  INTEGER
            ACCESS  read-only
            STATUS  mandatory
            DESCRIPTION
                " CS Error Counter "
            ::= { qt1UserCurrentPerfEntry 7 }

        qt1UserCurrentPerfBPV  OBJECT-TYPE
            SYNTAX  INTEGER
            ACCESS  read-only
            STATUS  mandatory
            DESCRIPTION
                " BPV Error Counter "
            ::= { qt1UserCurrentPerfEntry 8 }

        qt1UserCurrentPerfLOFC  OBJECT-TYPE
            SYNTAX  INTEGER
            ACCESS  read-only
            STATUS  mandatory
            DESCRIPTION
                " LOFC Error Counter "
            ::= { qt1UserCurrentPerfEntry 9 }

        qt1UserCurr15MinTimeElapsed  OBJECT-TYPE
            SYNTAX  INTEGER
            ACCESS  read-only
            STATUS  mandatory
            DESCRIPTION
                " Current 15-minute time elapsed"
            ::= { qt1UserCurrentPerfEntry 11 }

        qt1UserValid15MinInterval  OBJECT-TYPE
            SYNTAX  INTEGER
            ACCESS  read-only
            STATUS  mandatory
            DESCRIPTION
                " Current 1-day Valid 15-min interval"
            ::= { qt1UserCurrentPerfEntry 12 }


--
--  User Interval Performance Table
--

        qt1UserIntervalPerfTable  OBJECT-TYPE
            SYNTAX  SEQUENCE OF QT1UserIntervalPerfEntry
            ACCESS  not-accessible
            STATUS  mandatory
            DESCRIPTION
                "User Interval Performance Table"
            ::= { qt1-card 3 }

        qt1UserIntervalPerfEntry  OBJECT-TYPE
            SYNTAX  QT1UserIntervalPerfEntry
            ACCESS  not-accessible
            STATUS  mandatory
            DESCRIPTION
                "User interval performance entry"
            INDEX { qt1UIPSlotIndex , qt1UIPPortIndex ,
                    qt1UserIntervalPerfNumber }
            ::= { qt1UserIntervalPerfTable 1 }

        QT1UserIntervalPerfEntry ::= SEQUENCE  {
            qt1UIPSlotIndex             LSSlotID,
            qt1UIPPortIndex             PortID,
            qt1UserIntervalPerfNumber   INTEGER  (1..96),
            qt1UserIntervalPerfES       INTEGER,
            qt1UserIntervalPerfSES      INTEGER,
            qt1UserIntervalPerfBES      INTEGER,
            qt1UserIntervalPerfUAS      INTEGER,
            qt1UserIntervalPerfCSS      INTEGER,
            qt1UserIntervalPerfBPV      INTEGER,
            qt1UserIntervalPerfLOFC     INTEGER
        }

        qt1UIPSlotIndex  OBJECT-TYPE
            SYNTAX  LSSlotID
            ACCESS  read-only
            STATUS  mandatory
            DESCRIPTION
                "Qt1 slot"
            ::= { qt1UserIntervalPerfEntry 1 }

        qt1UIPPortIndex  OBJECT-TYPE
            SYNTAX  PortID
            ACCESS  read-only
            STATUS  mandatory
            DESCRIPTION
                "Port 1 to 4, total 4 ports."
            ::= { qt1UserIntervalPerfEntry 2 }

        qt1UserIntervalPerfNumber  OBJECT-TYPE
            SYNTAX  INTEGER (1..96)
            ACCESS  read-only
            STATUS  mandatory
            DESCRIPTION
                " Interval Index "
            ::= { qt1UserIntervalPerfEntry 3 }

        qt1UserIntervalPerfES  OBJECT-TYPE
            SYNTAX  INTEGER
            ACCESS  read-only
            STATUS  mandatory
            DESCRIPTION
                " ES Error Counter "
            ::= { qt1UserIntervalPerfEntry 4 }

        qt1UserIntervalPerfSES  OBJECT-TYPE
            SYNTAX  INTEGER
            ACCESS  read-only
            STATUS  mandatory
            DESCRIPTION
                " SES Error Counter "
            ::= { qt1UserIntervalPerfEntry 5 }

        qt1UserIntervalPerfBES  OBJECT-TYPE
            SYNTAX  INTEGER
            ACCESS  read-only
            STATUS  mandatory
            DESCRIPTION
                " BES Error Counter "
            ::= { qt1UserIntervalPerfEntry 6 }

        qt1UserIntervalPerfUAS  OBJECT-TYPE
            SYNTAX  INTEGER
            ACCESS  read-only
            STATUS  mandatory
            DESCRIPTION
                " UAS Error Counter "
            ::= { qt1UserIntervalPerfEntry 7 }

        qt1UserIntervalPerfCSS  OBJECT-TYPE
            SYNTAX  INTEGER
            ACCESS  read-only
            STATUS  mandatory
            DESCRIPTION
                " CSS Error Counter "
            ::= { qt1UserIntervalPerfEntry 8 }

        qt1UserIntervalPerfBPV  OBJECT-TYPE
            SYNTAX  INTEGER
            ACCESS  read-only
            STATUS  mandatory
            DESCRIPTION
                " BPV Error Counter "
            ::= { qt1UserIntervalPerfEntry 9 }

        qt1UserIntervalPerfLOFC  OBJECT-TYPE
            SYNTAX  INTEGER
            ACCESS  read-only
            STATUS  mandatory
            DESCRIPTION
                " LOFC Error Counter "
            ::= { qt1UserIntervalPerfEntry 10 }


--
--  User Total Performance Table
--
        qt1UserTotalPerfTable  OBJECT-TYPE
            SYNTAX  SEQUENCE OF QT1UserTotalPerfEntry
            ACCESS  not-accessible
            STATUS  mandatory
            DESCRIPTION
                "User Total Performance Table"
            ::= { qt1-card 4 }

        qt1UserTotalPerfEntry  OBJECT-TYPE
            SYNTAX  QT1UserTotalPerfEntry
            ACCESS  not-accessible
            STATUS  mandatory
            DESCRIPTION
                "User total performance entry"
            INDEX { qt1UTPSlotIndex , qt1UTPPortIndex }
            ::= { qt1UserTotalPerfTable 1 }

        QT1UserTotalPerfEntry ::= SEQUENCE  {
            qt1UTPSlotIndex             LSSlotID,
            qt1UTPPortIndex             PortID,
            qt1UserTotalPerfES          INTEGER,
            qt1UserTotalPerfSES         INTEGER,
            qt1UserTotalPerfBES         INTEGER,
            qt1UserTotalPerfUAS         INTEGER,
            qt1UserTotalPerfCSS         INTEGER,
            qt1UserTotalPerfBPV         INTEGER,
            qt1UserTotalPerfLOFC        INTEGER
        }

        qt1UTPSlotIndex  OBJECT-TYPE
            SYNTAX  LSSlotID
            ACCESS  read-only
            STATUS  mandatory
            DESCRIPTION
                "Qt1 slot"
            ::= { qt1UserTotalPerfEntry 1 }

        qt1UTPPortIndex  OBJECT-TYPE
            SYNTAX  PortID
            ACCESS  read-only
            STATUS  mandatory
            DESCRIPTION
                "Port 1 to 4, total 4 ports."
            ::= { qt1UserTotalPerfEntry 2 }

        qt1UserTotalPerfES  OBJECT-TYPE
            SYNTAX  INTEGER
            ACCESS  read-only
            STATUS  mandatory
            DESCRIPTION
                " ES Error Counter "
            ::= { qt1UserTotalPerfEntry 3 }

        qt1UserTotalPerfSES  OBJECT-TYPE
            SYNTAX  INTEGER
            ACCESS  read-only
            STATUS  mandatory
            DESCRIPTION
                " SES Error Counter "
            ::= { qt1UserTotalPerfEntry 4 }

        qt1UserTotalPerfBES  OBJECT-TYPE
            SYNTAX  INTEGER
            ACCESS  read-only
            STATUS  mandatory
            DESCRIPTION
                " BES Error Counter "
            ::= { qt1UserTotalPerfEntry 5 }

        qt1UserTotalPerfUAS  OBJECT-TYPE
            SYNTAX  INTEGER
            ACCESS  read-only
            STATUS  mandatory
            DESCRIPTION
                " UAS Error Counter "
            ::= { qt1UserTotalPerfEntry 6 }

        qt1UserTotalPerfCSS  OBJECT-TYPE
            SYNTAX  INTEGER
            ACCESS  read-only
            STATUS  mandatory
            DESCRIPTION
                " CSS Error Counter "
            ::= { qt1UserTotalPerfEntry 7 }

        qt1UserTotalPerfBPV  OBJECT-TYPE
            SYNTAX  INTEGER
            ACCESS  read-only
            STATUS  mandatory
            DESCRIPTION
                " BPV Error Counter "
            ::= { qt1UserTotalPerfEntry 8 }

        qt1UserTotalPerfLOFC  OBJECT-TYPE
            SYNTAX  INTEGER
            ACCESS  read-only
            STATUS  mandatory
            DESCRIPTION
                " LOFC Error Counter "
            ::= { qt1UserTotalPerfEntry 9 }


--
--  User Seven Days Performance Table
--
        qt1User7DaysPerfTable  OBJECT-TYPE
            SYNTAX  SEQUENCE OF QT1User7DaysPerfEntry
            ACCESS  not-accessible
            STATUS  mandatory
            DESCRIPTION
                "User 7 Days Performance Table"
            ::= { qt1-card 22 }

        qt1User7DaysPerfEntry  OBJECT-TYPE
            SYNTAX  QT1User7DaysPerfEntry
            ACCESS  not-accessible
            STATUS  mandatory
            DESCRIPTION
                "User 7 days performance entry"
            INDEX { qt1U7DPSlotIndex , qt1U7DPPortIndex ,
                    qt1UserDaysIndex }
            ::= { qt1User7DaysPerfTable 1 }

        QT1User7DaysPerfEntry ::= SEQUENCE  {
            qt1U7DPSlotIndex        LSSlotID,
            qt1U7DPPortIndex        PortID,
            qt1UserDaysIndex        INTEGER (1..7),
            qt1UserDateStrIndex     DisplayString (SIZE (0..255) ),
            qt1User7DaysPerfES      INTEGER,
            qt1User7DaysPerfSES     INTEGER,
            qt1User7DaysPerfBES     INTEGER,
            qt1User7DaysPerfUAS     INTEGER,
            qt1User7DaysPerfCSS     INTEGER
--            qt1User7DaysPerfLOFC    INTEGER


    }

        qt1U7DPSlotIndex  OBJECT-TYPE
            SYNTAX  LSSlotID
            ACCESS  read-only
            STATUS  mandatory
            DESCRIPTION
                "Qt1 slot"
            ::= { qt1User7DaysPerfEntry 1 }

        qt1U7DPPortIndex  OBJECT-TYPE
            SYNTAX  PortID
            ACCESS  read-only
            STATUS  mandatory
            DESCRIPTION
                "Port 1 to 4, total 4 ports."
            ::= { qt1User7DaysPerfEntry 2 }

        qt1UserDaysIndex  OBJECT-TYPE
            SYNTAX  INTEGER (1..7)
            ACCESS  read-only
            STATUS  mandatory
            DESCRIPTION
                "Seven Days index "
            ::= { qt1User7DaysPerfEntry 3 }

        qt1UserDateStrIndex  OBJECT-TYPE
            SYNTAX  DisplayString (SIZE (0..255) )
            ACCESS  read-only
            STATUS  mandatory
            DESCRIPTION
                "Seven Days String "
            ::= { qt1User7DaysPerfEntry 4 }

        qt1User7DaysPerfES  OBJECT-TYPE
            SYNTAX  INTEGER
            ACCESS  read-only
            STATUS  mandatory
            DESCRIPTION
                " ES Error Counter "
            ::= { qt1User7DaysPerfEntry 5 }

        qt1User7DaysPerfSES  OBJECT-TYPE
            SYNTAX  INTEGER
            ACCESS  read-only
            STATUS  mandatory
            DESCRIPTION
                " SES Error Counter "
            ::= { qt1User7DaysPerfEntry 6 }

        qt1User7DaysPerfBES  OBJECT-TYPE
            SYNTAX  INTEGER
            ACCESS  read-only
            STATUS  mandatory
            DESCRIPTION
                " BES Error Counter "
            ::= { qt1User7DaysPerfEntry 7 }

        qt1User7DaysPerfUAS  OBJECT-TYPE
            SYNTAX  INTEGER
            ACCESS  read-only
            STATUS  mandatory
            DESCRIPTION
                " UAS Error Counter "
            ::= { qt1User7DaysPerfEntry 8 }

        qt1User7DaysPerfCSS  OBJECT-TYPE
            SYNTAX  INTEGER
            ACCESS  read-only
            STATUS  mandatory
            DESCRIPTION
                " CSS Error Counter "
            ::= { qt1User7DaysPerfEntry 9 }

--        qt1User7DaysPerfLOFC  OBJECT-TYPE
--            SYNTAX  INTEGER
--            ACCESS  read-only
--            STATUS  mandatory
--            DESCRIPTION
--                " LOFC Counter "
--            ::= { qt1User7DaysPerfEntry 10 }


--
--  Line Current Performance Table
--

        qt1LineCurrentPerfTable  OBJECT-TYPE
            SYNTAX  SEQUENCE OF QT1LineCurrentPerfEntry
            ACCESS  not-accessible
            STATUS  mandatory
            DESCRIPTION
                "Line Current Performance Table"
            ::= { qt1-card 8 }

        qt1LineCurrentPerfEntry  OBJECT-TYPE
            SYNTAX  QT1LineCurrentPerfEntry
            ACCESS  not-accessible
            STATUS  mandatory
            DESCRIPTION
                "Line current performance entry"
            INDEX { qt1LCPSlotIndex , qt1LCPPortIndex }
            ::= { qt1LineCurrentPerfTable 1 }

        QT1LineCurrentPerfEntry ::= SEQUENCE  {
            qt1LCPSlotIndex             LSSlotID,
            qt1LCPPortIndex             PortID,
            qt1LineCurrentPerfES        INTEGER,
            qt1LineCurrentPerfSES       INTEGER,
            qt1LineCurrentPerfBES       INTEGER,
            qt1LineCurrentPerfUAS       INTEGER,
            qt1LineCurrentPerfCSS       INTEGER,
            qt1LineCurrentPerfBPV       INTEGER,
            qt1LineCurrentPerfLOFC      INTEGER,
            qt1LineCurr15MinTimeElapsed INTEGER,
            qt1LineValid15MinInterval   INTEGER
        }

        qt1LCPSlotIndex  OBJECT-TYPE
            SYNTAX  LSSlotID
            ACCESS  read-only
            STATUS  mandatory
            DESCRIPTION
                "Qt1 slot"
            ::= { qt1LineCurrentPerfEntry 1 }

        qt1LCPPortIndex  OBJECT-TYPE
            SYNTAX  PortID
            ACCESS  read-only
            STATUS  mandatory
            DESCRIPTION
                "Port 1 to 4, total 4 ports."
            ::= { qt1LineCurrentPerfEntry 2 }

        qt1LineCurrentPerfES  OBJECT-TYPE
            SYNTAX  INTEGER
            ACCESS  read-only
            STATUS  mandatory
            DESCRIPTION
                " ESS Error Counter "
            ::= { qt1LineCurrentPerfEntry 3 }

        qt1LineCurrentPerfSES  OBJECT-TYPE
            SYNTAX  INTEGER
            ACCESS  read-only
            STATUS  mandatory
            DESCRIPTION
                " SES Error Counter "
            ::= { qt1LineCurrentPerfEntry 4 }

        qt1LineCurrentPerfBES  OBJECT-TYPE
            SYNTAX  INTEGER
            ACCESS  read-only
            STATUS  mandatory
            DESCRIPTION
                " BES Error Counter "
            ::= { qt1LineCurrentPerfEntry 5 }

        qt1LineCurrentPerfUAS  OBJECT-TYPE
            SYNTAX  INTEGER
            ACCESS  read-only
            STATUS  mandatory
            DESCRIPTION
                " UAS Error Counter "
            ::= { qt1LineCurrentPerfEntry 6 }

        qt1LineCurrentPerfCSS  OBJECT-TYPE
            SYNTAX  INTEGER
            ACCESS  read-only
            STATUS  mandatory
            DESCRIPTION
                " CSS Error Counter "
            ::= { qt1LineCurrentPerfEntry 7 }

        qt1LineCurrentPerfBPV  OBJECT-TYPE
            SYNTAX  INTEGER
            ACCESS  read-only
            STATUS  mandatory
            DESCRIPTION
                " BPV Error Counter "
            ::= { qt1LineCurrentPerfEntry 8 }

        qt1LineCurrentPerfLOFC  OBJECT-TYPE
            SYNTAX  INTEGER
            ACCESS  read-only
            STATUS  mandatory
            DESCRIPTION
                " LOFC Error Counter "
            ::= { qt1LineCurrentPerfEntry 9 }

        qt1LineCurr15MinTimeElapsed  OBJECT-TYPE
            SYNTAX  INTEGER
            ACCESS  read-only
            STATUS  mandatory
            DESCRIPTION
                " Current 15-minute time elapsed"
            ::= { qt1LineCurrentPerfEntry 11 }

        qt1LineValid15MinInterval  OBJECT-TYPE
            SYNTAX  INTEGER
            ACCESS  read-only
            STATUS  mandatory
            DESCRIPTION
                " Current 1-day Valid 15-min interval"
            ::= { qt1LineCurrentPerfEntry 12 }


--
--  Line Interval Performance Table
--

        qt1LineIntervalPerfTable  OBJECT-TYPE
            SYNTAX  SEQUENCE OF QT1LineIntervalPerfEntry
            ACCESS  not-accessible
            STATUS  mandatory
            DESCRIPTION
                "Line Interval Performance Table"
            ::= { qt1-card 9 }

        qt1LineIntervalPerfEntry  OBJECT-TYPE
            SYNTAX  QT1LineIntervalPerfEntry
            ACCESS  not-accessible
            STATUS  mandatory
            DESCRIPTION
                "Line interval performance entry"
            INDEX { qt1LIPSlotIndex , qt1LIPPortIndex ,
                    qt1LineIntervalPerfNumber }
            ::= { qt1LineIntervalPerfTable 1 }

        QT1LineIntervalPerfEntry ::= SEQUENCE {
            qt1LIPSlotIndex             LSSlotID,
            qt1LIPPortIndex             PortID,
            qt1LineIntervalPerfNumber   INTEGER  (1..96),
            qt1LineIntervalPerfES       INTEGER,
            qt1LineIntervalPerfSES      INTEGER,
            qt1LineIntervalPerfBES      INTEGER,
            qt1LineIntervalPerfUAS      INTEGER,
            qt1LineIntervalPerfCSS      INTEGER,
            qt1LineIntervalPerfBPV      INTEGER,
            qt1LineIntervalPerfLOFC     INTEGER,
            qt1LineIntvAvailable        INTEGER
        }

        qt1LIPSlotIndex  OBJECT-TYPE
            SYNTAX  LSSlotID
            ACCESS  read-only
            STATUS  mandatory
            DESCRIPTION
                "Qt1 slot"
            ::= { qt1LineIntervalPerfEntry 1 }

        qt1LIPPortIndex  OBJECT-TYPE
            SYNTAX  PortID
            ACCESS  read-only
            STATUS  mandatory
            DESCRIPTION
                "Port 1 to 4, total 4 ports."
            ::= { qt1LineIntervalPerfEntry 2 }

        qt1LineIntervalPerfNumber  OBJECT-TYPE
            SYNTAX  INTEGER (1..96)
            ACCESS  read-only
            STATUS  mandatory
            DESCRIPTION
                "Interval Index "
            ::= { qt1LineIntervalPerfEntry 3 }

        qt1LineIntervalPerfES  OBJECT-TYPE
            SYNTAX  INTEGER
            ACCESS  read-only
            STATUS  mandatory
            DESCRIPTION
                " ES Error Counter "
            ::= { qt1LineIntervalPerfEntry 4 }

        qt1LineIntervalPerfSES  OBJECT-TYPE
            SYNTAX  INTEGER
            ACCESS  read-only
            STATUS  mandatory
            DESCRIPTION
                " SES Error Counter "
            ::= { qt1LineIntervalPerfEntry 5 }

        qt1LineIntervalPerfBES  OBJECT-TYPE
            SYNTAX  INTEGER
            ACCESS  read-only
            STATUS  mandatory
            DESCRIPTION
                " BES Error Counter "
            ::= { qt1LineIntervalPerfEntry 6 }

        qt1LineIntervalPerfUAS  OBJECT-TYPE
            SYNTAX  INTEGER
            ACCESS  read-only
            STATUS  mandatory
            DESCRIPTION
                " UAS Error Counter "
            ::= { qt1LineIntervalPerfEntry 7 }

        qt1LineIntervalPerfCSS  OBJECT-TYPE
            SYNTAX  INTEGER
            ACCESS  read-only
            STATUS  mandatory
            DESCRIPTION
                " CSS Error Counter "
            ::= { qt1LineIntervalPerfEntry 8 }

        qt1LineIntervalPerfBPV  OBJECT-TYPE
            SYNTAX  INTEGER
            ACCESS  read-only
            STATUS  mandatory
            DESCRIPTION
                " BPV Error Counter "
            ::= { qt1LineIntervalPerfEntry 9 }

        qt1LineIntervalPerfLOFC  OBJECT-TYPE
            SYNTAX  INTEGER
            ACCESS  read-only
            STATUS  mandatory
            DESCRIPTION
                " LOFC Error Counter "
            ::= { qt1LineIntervalPerfEntry 10 }

        qt1LineIntvAvailable  OBJECT-TYPE
            SYNTAX  INTEGER   {
                    available(1),
                    na(2)
                }
            ACCESS  read-only
            STATUS  mandatory
            DESCRIPTION
                " Interval Available "
            ::= { qt1LineIntervalPerfEntry 11 }


--
--  Line Total Performance Table
--

        qt1LineTotalPerfTable  OBJECT-TYPE
            SYNTAX  SEQUENCE OF QT1LineTotalPerfEntry
            ACCESS  not-accessible
            STATUS  mandatory
            DESCRIPTION
                "Line Total Performance Table"
            ::= { qt1-card 10 }

        qt1LineTotalPerfEntry  OBJECT-TYPE
            SYNTAX  QT1LineTotalPerfEntry
            ACCESS  not-accessible
            STATUS  mandatory
            DESCRIPTION
                "Line total performance entry"
            INDEX { qt1LTPSlotIndex , qt1LTPPortIndex }
            ::= { qt1LineTotalPerfTable 1 }

        QT1LineTotalPerfEntry ::= SEQUENCE  {
            qt1LTPSlotIndex             LSSlotID,
            qt1LTPPortIndex             PortID,
            qt1LineTotalPerfES          INTEGER,
            qt1LineTotalPerfSES         INTEGER,
            qt1LineTotalPerfBES         INTEGER,
            qt1LineTotalPerfUAS         INTEGER,
            qt1LineTotalPerfCSS         INTEGER,
            qt1LineTotalPerfBPV         INTEGER,
            qt1LineTotalPerfLOFC        INTEGER
        }

        qt1LTPSlotIndex  OBJECT-TYPE
            SYNTAX  LSSlotID
            ACCESS  read-only
            STATUS  mandatory
            DESCRIPTION
                "Qt1 slot"
            ::= { qt1LineTotalPerfEntry 1 }

        qt1LTPPortIndex  OBJECT-TYPE
            SYNTAX  PortID
            ACCESS  read-only
            STATUS  mandatory
            DESCRIPTION
                "Port 1 to 4, total 4 ports."
            ::= { qt1LineTotalPerfEntry 2 }

        qt1LineTotalPerfES  OBJECT-TYPE
            SYNTAX  INTEGER
            ACCESS  read-only
            STATUS  mandatory
            DESCRIPTION
                " ES Error Counter "
            ::= { qt1LineTotalPerfEntry 3 }

        qt1LineTotalPerfSES  OBJECT-TYPE
            SYNTAX  INTEGER
            ACCESS  read-only
            STATUS  mandatory
            DESCRIPTION
                " SES Error Counter "
            ::= { qt1LineTotalPerfEntry 4 }

        qt1LineTotalPerfBES  OBJECT-TYPE
            SYNTAX  INTEGER
            ACCESS  read-only
            STATUS  mandatory
            DESCRIPTION
                " BES Error Counter "
            ::= { qt1LineTotalPerfEntry 5 }

        qt1LineTotalPerfUAS  OBJECT-TYPE
            SYNTAX  INTEGER
            ACCESS  read-only
            STATUS  mandatory
            DESCRIPTION
                " UAS Error Counter "
            ::= { qt1LineTotalPerfEntry 6 }

        qt1LineTotalPerfCSS  OBJECT-TYPE
            SYNTAX  INTEGER
            ACCESS  read-only
            STATUS  mandatory
            DESCRIPTION
                " CSS Error Counter "
            ::= { qt1LineTotalPerfEntry 7 }

        qt1LineTotalPerfBPV  OBJECT-TYPE
            SYNTAX  INTEGER
            ACCESS  read-only
            STATUS  mandatory
            DESCRIPTION
                " BPV Error Counter "
            ::= { qt1LineTotalPerfEntry 8 }

        qt1LineTotalPerfLOFC  OBJECT-TYPE
            SYNTAX  INTEGER
            ACCESS  read-only
            STATUS  mandatory
            DESCRIPTION
                " LOFC Error Counter "
            ::= { qt1LineTotalPerfEntry 9 }


--
--  Line Seven Days Performance Table
--
        qt1Line7DaysPerfTable  OBJECT-TYPE
            SYNTAX  SEQUENCE OF QT1Line7DaysPerfEntry
            ACCESS  not-accessible
            STATUS  mandatory
            DESCRIPTION
                "Line 7 Days Performance Table"
            ::= { qt1-card 21 }

        qt1Line7DaysPerfEntry  OBJECT-TYPE
            SYNTAX  QT1Line7DaysPerfEntry
            ACCESS  not-accessible
            STATUS  mandatory
            DESCRIPTION
                "Line 7 days performance entry"
            INDEX { qt1L7DPSlotIndex , qt1L7DPPortIndex ,
                    qt1LineDaysIndex }
            ::= { qt1Line7DaysPerfTable 1 }

        QT1Line7DaysPerfEntry ::= SEQUENCE  {
            qt1L7DPSlotIndex        LSSlotID,
            qt1L7DPPortIndex        PortID,
            qt1LineDaysIndex        INTEGER (1..7),
            qt1LineDateStrIndex     DisplayString (SIZE (0..255) ),
            qt1Line7DaysPerfES      INTEGER,
            qt1Line7DaysPerfSES     INTEGER,
            qt1Line7DaysPerfBES     INTEGER,
            qt1Line7DaysPerfUAS     INTEGER,
            qt1Line7DaysPerfCSS     INTEGER
--            qt1Line7DaysPerfLOFC    INTEGER


    }

        qt1L7DPSlotIndex  OBJECT-TYPE
            SYNTAX  LSSlotID
            ACCESS  read-only
            STATUS  mandatory
            DESCRIPTION
                "Qt1 slot"
            ::= { qt1Line7DaysPerfEntry 1 }

        qt1L7DPPortIndex  OBJECT-TYPE
            SYNTAX  PortID
            ACCESS  read-only
            STATUS  mandatory
            DESCRIPTION
                "Port 1 to 4, total 4 ports."
            ::= { qt1Line7DaysPerfEntry 2 }

        qt1LineDaysIndex  OBJECT-TYPE
            SYNTAX  INTEGER (1..7)
            ACCESS  read-only
            STATUS  mandatory
            DESCRIPTION
                "Seven Days index "
            ::= { qt1Line7DaysPerfEntry 3 }

        qt1LineDateStrIndex  OBJECT-TYPE
            SYNTAX  DisplayString (SIZE (0..255) )
            ACCESS  read-only
            STATUS  mandatory
            DESCRIPTION
                "Seven Days String "
            ::= { qt1Line7DaysPerfEntry 4 }

        qt1Line7DaysPerfES  OBJECT-TYPE
            SYNTAX  INTEGER
            ACCESS  read-only
            STATUS  mandatory
            DESCRIPTION
                " ES Error Counter "
            ::= { qt1Line7DaysPerfEntry 5 }

        qt1Line7DaysPerfSES  OBJECT-TYPE
            SYNTAX  INTEGER
            ACCESS  read-only
            STATUS  mandatory
            DESCRIPTION
                " SES Error Counter "
            ::= { qt1Line7DaysPerfEntry 6 }

        qt1Line7DaysPerfBES  OBJECT-TYPE
            SYNTAX  INTEGER
            ACCESS  read-only
            STATUS  mandatory
            DESCRIPTION
                " BES Error Counter "
            ::= { qt1Line7DaysPerfEntry 7 }

        qt1Line7DaysPerfUAS  OBJECT-TYPE
            SYNTAX  INTEGER
            ACCESS  read-only
            STATUS  mandatory
            DESCRIPTION
                " UAS Error Counter "
            ::= { qt1Line7DaysPerfEntry 8 }

        qt1Line7DaysPerfCSS  OBJECT-TYPE
            SYNTAX  INTEGER
            ACCESS  read-only
            STATUS  mandatory
            DESCRIPTION
                " CSS Error Counter "
            ::= { qt1Line7DaysPerfEntry 9 }

--        qt1Line7DaysPerfLOFC  OBJECT-TYPE
--            SYNTAX  INTEGER
--            ACCESS  read-only
--            STATUS  mandatory
--            DESCRIPTION
--                " LOFC Counter "
--            ::= { qt1Line7DaysPerfEntry 10 }


--
--  Alarm Queue Table
--

--          QE1AlarmQueueEntry         qt1AlarmQueueTable  OBJECT-TYPE
--             SYNTAX  SEQUENCE OF QT1AlarmQueueEntry
--             ACCESS  not-accessible
--             STATUS  mandatory
--             DESCRIPTION
--                "Alarm Queue Table"
--             ::= { qt1-card 11 }
--
--         qt1AlarmQueueEntry  OBJECT-TYPE
--             SYNTAX  QT1AlarmQueueEntry
--             ACCESS  not-accessible
--             STATUS  mandatory
--             DESCRIPTION
--                "Alarm queue entry"
--             INDEX  { qt1AQSlotIndex, qt1AQPortIndex,
--                      qt1AlarmQueueIndex }
--             ::= { qt1AlarmQueueTable 1 }
--
--         QT1AlarmQueueEntry ::=
--             SEQUENCE {
--               qt1AlarmQueueIndex
--                 INTEGER (1..40),
--               qt1AlarmQueueString
--                 DisplayString (SIZE(0..255))
--             }
--
--         qt1AlarmQueueIndex  OBJECT-TYPE
--             SYNTAX  INTEGER (1..40)
--             ACCESS  read-only
--             STATUS  mandatory
--             DESCRIPTION
--                "Select Alarm Queue Index(1-40)"
--             ::= { qt1AlarmQueueEntry 2 }
--
--         qt1AlarmQueueString  OBJECT-TYPE
--             SYNTAX  DisplayString (SIZE (0..255))
--             ACCESS  read-only
--             STATUS  mandatory
--             DESCRIPTION
--                "Alarm Queue String"
--             ::= { qt1AlarmQueueEntry 3 }

--
--  Alarm History Table
--

        qt1AlarmHistoryTable  OBJECT-TYPE
            SYNTAX  SEQUENCE OF QT1AlarmHistoryEntry
            ACCESS  not-accessible
            STATUS  mandatory
            DESCRIPTION
                "Alarm History Table"
            ::= { qt1-card 12 }

        qt1AlarmHistoryEntry  OBJECT-TYPE
            SYNTAX  QT1AlarmHistoryEntry
            ACCESS  not-accessible
            STATUS  mandatory
            DESCRIPTION
                "Alarm history entry"
            INDEX { qt1AHSlotIndex , qt1AHPortIndex ,
                    qt1AlarmHistoryIndex }
            ::= { qt1AlarmHistoryTable 1 }

        QT1AlarmHistoryEntry ::= SEQUENCE {
            qt1AHSlotIndex              LSSlotID,
            qt1AHPortIndex              PortID,
            qt1AlarmHistoryIndex        INTEGER,
            qt1Threshold                INTEGER,
            qt1CurrentState             INTEGER,
            qt1CurrentCount             INTEGER,
            qt1Alarm                    LsAlarmSeverity
        }

        qt1AHSlotIndex  OBJECT-TYPE
            SYNTAX  LSSlotID
            ACCESS  read-only
            STATUS  mandatory
            DESCRIPTION
                "Qt1 slot"
            ::= { qt1AlarmHistoryEntry 1 }

        qt1AHPortIndex  OBJECT-TYPE
            SYNTAX  PortID
            ACCESS  read-only
            STATUS  mandatory
            DESCRIPTION
                "Port 1 to 4, total 4 ports."
            ::= { qt1AlarmHistoryEntry 2 }

        qt1AlarmHistoryIndex  OBJECT-TYPE
            SYNTAX  INTEGER {
                    yel-line(1),
                    ais-line(2),
                    los-line(3),
                    lof-line(4),
                    bpv-line(5),
                    ess-line(6),
                    uas-line(7),
                    css-line(8)
                }
            ACCESS  read-only
            STATUS  mandatory
            DESCRIPTION
                " Alarm History Index "
            ::= { qt1AlarmHistoryEntry 3 }

        qt1Threshold  OBJECT-TYPE
            SYNTAX  INTEGER
            ACCESS  read-only
            STATUS  mandatory
            DESCRIPTION
                " Alarm History Threshold Value "
            ::= { qt1AlarmHistoryEntry 4 }

        qt1CurrentState  OBJECT-TYPE
            SYNTAX  INTEGER {
                    ok(1),
                    alarm(2),
                    disable(3)
                }
            ACCESS  read-only
            STATUS  mandatory
            DESCRIPTION
                " Alarm History Current State"
            ::= { qt1AlarmHistoryEntry 5 }

        qt1CurrentCount  OBJECT-TYPE
            SYNTAX  INTEGER
            ACCESS  read-only
            STATUS  mandatory
            DESCRIPTION
                " Alarm History Current Count "
            ::= { qt1AlarmHistoryEntry 6 }

        qt1Alarm  OBJECT-TYPE
            SYNTAX  LsAlarmSeverity
            ACCESS  read-only
            STATUS  mandatory
            DESCRIPTION
                "Alarm History Alarm State"
            ::= { qt1AlarmHistoryEntry 7 }


--
--  Line Availability Table
--

        qt1LineAvailabilityTable  OBJECT-TYPE
            SYNTAX  SEQUENCE OF QT1LineAvailabilityEntry
            ACCESS  not-accessible
            STATUS  mandatory
            DESCRIPTION
                "The DS1 line control table."
            ::= { qt1-card 13 }

        qt1LineAvailabilityEntry  OBJECT-TYPE
            SYNTAX  QT1LineAvailabilityEntry
            ACCESS  not-accessible
            STATUS  mandatory
            DESCRIPTION
                "An entry in the DS1 line control table."
            INDEX { qt1LASlotIndex , qt1LAPortIndex }
            ::= { qt1LineAvailabilityTable 1 }

        QT1LineAvailabilityEntry ::= SEQUENCE {
            qt1LASlotIndex              LSSlotID,
            qt1LAPortIndex              PortID,
            qt1AvailableSeconds         DisplayString,
            qt1UnavailableSeconds       DisplayString,
            qt1LineAvailability         DisplayString
        }

        qt1LASlotIndex  OBJECT-TYPE
            SYNTAX  LSSlotID
            ACCESS  read-only
            STATUS  mandatory
            DESCRIPTION
                "Qt1 slot"
            ::= { qt1LineAvailabilityEntry 1 }

        qt1LAPortIndex  OBJECT-TYPE
            SYNTAX  PortID
            ACCESS  read-only
            STATUS  mandatory
            DESCRIPTION
                "Port 1 to 4, total 4 ports."
            ::= { qt1LineAvailabilityEntry 2 }

        qt1AvailableSeconds  OBJECT-TYPE
            SYNTAX  DisplayString (SIZE(0..255))
            ACCESS  read-only
            STATUS  mandatory
            DESCRIPTION
                "Line Available Seconds"
            ::= { qt1LineAvailabilityEntry 3 }

        qt1UnavailableSeconds  OBJECT-TYPE
            SYNTAX  DisplayString (SIZE(0..255))
            ACCESS  read-only
            STATUS  mandatory
            DESCRIPTION
                "Line Unavailable Seconds"
            ::= { qt1LineAvailabilityEntry 4 }

        qt1LineAvailability  OBJECT-TYPE
            SYNTAX  DisplayString (SIZE(0..255))
            ACCESS  read-only
            STATUS  mandatory
            DESCRIPTION
                "Line Available Percentage"
            ::= { qt1LineAvailabilityEntry 5 }


--
--  Alarm Control Table
--

        qt1AlarmControlTable  OBJECT-TYPE
            SYNTAX  SEQUENCE OF QT1AlarmControlEntry
            ACCESS  not-accessible
            STATUS  mandatory
            DESCRIPTION
                "The alarm control table."
            ::= { qt1-card 14 }

        qt1AlarmControlEntry  OBJECT-TYPE
            SYNTAX  QT1AlarmControlEntry
            ACCESS  not-accessible
            STATUS  mandatory
            DESCRIPTION
                "An entry in the DS1 alarm control table."
            INDEX { qt1ACSlotIndex , qt1ACPortIndex }
            ::= { qt1AlarmControlTable 1 }

        QT1AlarmControlEntry ::= SEQUENCE {
            qt1ACSlotIndex              LSSlotID,
            qt1ACPortIndex              PortID,
            qt1YEL-Line                 LsAlarmSeverity,
            qt1AIS-Line                 LsAlarmSeverity,
            qt1LOS-Line                 LsAlarmSeverity,
            qt1LOF-Line                 LsAlarmSeverity,
            qt1BPV-Line                 LsAlarmSeverity,
            qt1ESS-Line                 LsAlarmSeverity,
            qt1UAS-Line                 LsAlarmSeverity,
            qt1CSS-Line                 LsAlarmSeverity
        }

        qt1ACSlotIndex  OBJECT-TYPE
            SYNTAX  LSSlotID
            ACCESS  read-only
            STATUS  mandatory
            DESCRIPTION
                "Qt1 slot"
            ::= { qt1AlarmControlEntry 1 }

        qt1ACPortIndex  OBJECT-TYPE
            SYNTAX  PortID
            ACCESS  read-only
            STATUS  mandatory
            DESCRIPTION
                "Port 1 to 4, total 4 ports."
            ::= { qt1AlarmControlEntry 2 }

        qt1YEL-Line  OBJECT-TYPE
            SYNTAX  LsAlarmSeverity
            ACCESS  read-write
            STATUS  mandatory
            DESCRIPTION
                "YEL-Line State"
            ::= { qt1AlarmControlEntry 3 }

        qt1AIS-Line  OBJECT-TYPE
            SYNTAX  LsAlarmSeverity
            ACCESS  read-write
            STATUS  mandatory
            DESCRIPTION
                "AIS-Line State"
            ::= { qt1AlarmControlEntry 4 }

        qt1LOS-Line  OBJECT-TYPE
            SYNTAX  LsAlarmSeverity
            ACCESS  read-write
            STATUS  mandatory
            DESCRIPTION
                "LOS-line State"
            ::= { qt1AlarmControlEntry 5 }

        qt1LOF-Line  OBJECT-TYPE
            SYNTAX  LsAlarmSeverity
            ACCESS  read-write
            STATUS  mandatory
            DESCRIPTION
                "LOF-Line State"
            ::= { qt1AlarmControlEntry 6 }

        qt1BPV-Line  OBJECT-TYPE
            SYNTAX  LsAlarmSeverity
            ACCESS  read-write
            STATUS  mandatory
            DESCRIPTION
                "BPV-Line State"
            ::= { qt1AlarmControlEntry 7 }

        qt1ESS-Line  OBJECT-TYPE
            SYNTAX  LsAlarmSeverity
            ACCESS  read-write
            STATUS  mandatory
            DESCRIPTION
                "ESS-Line State"
            ::= { qt1AlarmControlEntry 8 }

        qt1UAS-Line  OBJECT-TYPE
            SYNTAX  LsAlarmSeverity
            ACCESS  read-write
            STATUS  mandatory
            DESCRIPTION
                "UAS-Line State"
            ::= { qt1AlarmControlEntry 9 }

        qt1CSS-Line  OBJECT-TYPE
            SYNTAX  LsAlarmSeverity
            ACCESS  read-write
            STATUS  mandatory
            DESCRIPTION
                "CS-Line State"
            ::= { qt1AlarmControlEntry 10 }


--
--  Threshold Control Table
--

        qt1ThresholdControlTable  OBJECT-TYPE
            SYNTAX  SEQUENCE OF QT1ThresholdControlEntry
            ACCESS  not-accessible
            STATUS  mandatory
            DESCRIPTION
                "The alarm control table."
            ::= { qt1-card 15 }

        qt1ThresholdControlEntry  OBJECT-TYPE
            SYNTAX  QT1ThresholdControlEntry
            ACCESS  not-accessible
            STATUS  mandatory
            DESCRIPTION
                "An entry in the DS1 threshold control table."
            INDEX { qt1TCSlotIndex , qt1TCPortIndex }
            ::= { qt1ThresholdControlTable 1 }

        QT1ThresholdControlEntry ::= SEQUENCE {
            qt1TCSlotIndex              LSSlotID,
            qt1TCPortIndex              PortID,
            qt1ThresholdBPV-Line        INTEGER,
            qt1ThresholdESS-Line        INTEGER,
            qt1ThresholdUAS-Line        INTEGER,
            qt1ThresholdCSS-Line        INTEGER
        }

        qt1TCSlotIndex  OBJECT-TYPE
            SYNTAX  LSSlotID
            ACCESS  read-only
            STATUS  mandatory
            DESCRIPTION
                "Qt1 slot"
            ::= { qt1ThresholdControlEntry 1 }

        qt1TCPortIndex  OBJECT-TYPE
            SYNTAX  PortID
            ACCESS  read-only
            STATUS  mandatory
            DESCRIPTION
                "Port 1 to 4, total 4 ports."
            ::= { qt1ThresholdControlEntry 2 }

        qt1ThresholdBPV-Line  OBJECT-TYPE
            SYNTAX  INTEGER
            ACCESS  read-write
            STATUS  mandatory
            DESCRIPTION
                " Threshold of BPV-Line "
            ::= { qt1ThresholdControlEntry 3 }

        qt1ThresholdESS-Line  OBJECT-TYPE
            SYNTAX  INTEGER
            ACCESS  read-write
            STATUS  mandatory
            DESCRIPTION
                " Threshold of ESS-Line "
            ::= { qt1ThresholdControlEntry 4 }

        qt1ThresholdUAS-Line  OBJECT-TYPE
            SYNTAX  INTEGER
            ACCESS  read-write
            STATUS  mandatory
            DESCRIPTION
                " Threshold of UAS-Line "
            ::= { qt1ThresholdControlEntry 5 }

        qt1ThresholdCSS-Line  OBJECT-TYPE
            SYNTAX  INTEGER
            ACCESS  read-write
            STATUS  mandatory
            DESCRIPTION
                " Threshold of CS-Line "
            ::= { qt1ThresholdControlEntry 6 }


--
-- Line Diagnostic Control Table
--

        qt1LineDiagControlTable  OBJECT-TYPE
            SYNTAX  SEQUENCE OF QT1LineDiagControlEntry
            ACCESS  not-accessible
            STATUS  mandatory
            DESCRIPTION
                "The alarm control table."
            ::= { qt1-card 16 }

        qt1LineDiagControlEntry  OBJECT-TYPE
            SYNTAX  QT1LineDiagControlEntry
            ACCESS  not-accessible
            STATUS  mandatory
            DESCRIPTION
                "An entry in the DS1 threshold control table."
            INDEX { qt1DCSlotIndex , qt1DCPortIndex }
            ::= { qt1LineDiagControlTable 1 }

        QT1LineDiagControlEntry ::= SEQUENCE {
            qt1DCSlotIndex              LSSlotID,
            qt1DCPortIndex              INTEGER,
            qt1LoopbackType             INTEGER,
            qt1LoopbackStatus           INTEGER,
            qt1QRSSControl              INTEGER,
            qt1QRSSStatus               INTEGER,
            qt1QRSSElapseSeconds        INTEGER,
            qt1QRSSErrorSeconds         INTEGER,
            qt1QRSSErrorCounts          INTEGER,
            qt1InbandLoopbackPeriod     INTEGER
        }

        qt1DCSlotIndex  OBJECT-TYPE
            SYNTAX  LSSlotID
            ACCESS  read-only
            STATUS  mandatory
            DESCRIPTION
                "Qt1 slot"
            ::= { qt1LineDiagControlEntry 1 }

        qt1DCPortIndex  OBJECT-TYPE
            SYNTAX  INTEGER {
                    port-1(1),
                    port-2(2),
                    port-3(3),
                    port-4(4)
                }
            ACCESS  read-only
            STATUS  mandatory
            DESCRIPTION
                "Port 1 to 4, total 4 ports."
            ::= { qt1LineDiagControlEntry 2 }

        qt1LoopbackType  OBJECT-TYPE
            SYNTAX  INTEGER {
                    no-loopback(1),
                    local-loopback(2),
                    payload-loopback(3),
                    line-loopback(4),
                    remote-LLB-Inband-Active(5),
                    remote-PLB-ATT-Active(6),
                    remote-PLB-ANSI-Active(7),
                    remote-LLB-ANSI-Active(8),
                    remote-LLB-Inband-Deactive(9),
                    remote-PLB-ATT-Deactive(10),
                    remote-PLB-ANSI-Deactive(11),
                    remote-LLB-ANSI-Deactive(12)
                }
            ACCESS  read-write
            STATUS  mandatory
            DESCRIPTION
                "qt1 Loopback Type"
            ::= { qt1LineDiagControlEntry 3 }

        qt1LoopbackStatus  OBJECT-TYPE
            SYNTAX  INTEGER {
                    success(1),
                    fail(2),
                    loopback-not-active(3)
                }
            ACCESS  read-only
            STATUS  mandatory
            DESCRIPTION
                "qt1 Loopback Status"
            ::= { qt1LineDiagControlEntry 4 }

        qt1QRSSControl  OBJECT-TYPE
            SYNTAX  INTEGER {
                    qrss-deactive(1),
                    qrss-active-full(2),
                    qrss-reset-error-count(3),
                    qrss-inject-error(4)
                }
            ACCESS  read-write
            STATUS  mandatory
            DESCRIPTION
                "qt1 QRSS Control"
            ::= { qt1LineDiagControlEntry 5 }

        qt1QRSSStatus  OBJECT-TYPE
            SYNTAX  INTEGER {
                    qrss-sync(1),
                    qrss-unsync(2),
                    qrss-not-active(3)
                }
            ACCESS  read-only
            STATUS  mandatory
            DESCRIPTION
                "qt1 QRSS Status"
            ::= { qt1LineDiagControlEntry 6 }

        qt1QRSSElapseSeconds  OBJECT-TYPE
            SYNTAX  INTEGER
            ACCESS  read-only
            STATUS  mandatory
            DESCRIPTION
                "qt1 QRSS Elapse Seconds"
            ::= { qt1LineDiagControlEntry 7 }

        qt1QRSSErrorSeconds  OBJECT-TYPE
            SYNTAX  INTEGER
            ACCESS  read-only
            STATUS  mandatory
            DESCRIPTION
                "qt1 QRSS Error Seconds"
            ::= { qt1LineDiagControlEntry 8 }

        qt1QRSSErrorCounts  OBJECT-TYPE
            SYNTAX  INTEGER
            ACCESS  read-only
            STATUS  mandatory
            DESCRIPTION
                "qt1 QRSS Error Counts"
            ::= { qt1LineDiagControlEntry 9 }

        qt1InbandLoopbackPeriod  OBJECT-TYPE
            SYNTAX  INTEGER
            ACCESS  read-write
            STATUS  mandatory
            DESCRIPTION
                "period(in seconds) of QT1 inband local, payload, or line loopback"
            ::= { qt1LineDiagControlEntry 10 }


--
--  Command Control Table
--

        qt1CommandControlTable  OBJECT-TYPE
            SYNTAX  SEQUENCE OF QT1CommandControlEntry
            ACCESS  not-accessible
            STATUS  mandatory
            DESCRIPTION
                "The command control table."
            ::= { qt1-card 17 }

        qt1CommandControlEntry  OBJECT-TYPE
            SYNTAX  QT1CommandControlEntry
            ACCESS  not-accessible
            STATUS  mandatory
            DESCRIPTION
                "An entry in the command control table."
            INDEX { qt1CCSlotIndex , qt1CCPortIndex }
            ::= { qt1CommandControlTable 1 }

        QT1CommandControlEntry ::= SEQUENCE {
            qt1CCSlotIndex              LSSlotID,
            qt1CCPortIndex              PortID,
            qt1UserPerfReset            INTEGER,
--               qt1AlarmHistoryReset
--                 INTEGER,
            qt1PortReset                INTEGER,
            qt1PortLoadDefault          INTEGER
        }

        qt1CCSlotIndex  OBJECT-TYPE
            SYNTAX  LSSlotID
            ACCESS  read-only
            STATUS  mandatory
            DESCRIPTION
                "Qt1 slot"
            ::= { qt1CommandControlEntry 1 }

        qt1CCPortIndex  OBJECT-TYPE
            SYNTAX  PortID
            ACCESS  read-only
            STATUS  mandatory
            DESCRIPTION
                "Port 1 to 4, total 4 ports."
            ::= { qt1CommandControlEntry 2 }

        qt1UserPerfReset    OBJECT-TYPE
            SYNTAX  INTEGER {
                    reset(1)
                }
            ACCESS  read-write
            STATUS  mandatory
            DESCRIPTION
                "Command: Reset User Performance"
            ::= { qt1CommandControlEntry 4 }

--         qt1AlarmHistoryReset    OBJECT-TYPE
--             SYNTAX  INTEGER {
--                         reset(1)
--                     }
--             ACCESS  read-write
--             STATUS  mandatory
--             DESCRIPTION
--                "Command: Reset Alarm History"
--             ::= { qt1CommandControlEntry 5 }

        qt1PortReset    OBJECT-TYPE
            SYNTAX  INTEGER {
                    reset(1)
                }
            ACCESS  read-write
            STATUS  mandatory
            DESCRIPTION
                "Command: Reset QT1 Port"
            ::= { qt1CommandControlEntry 6 }

        qt1PortLoadDefault    OBJECT-TYPE
            SYNTAX  INTEGER {
                    load-default(1)
                }
            ACCESS  read-write
            STATUS  mandatory
            DESCRIPTION
                "Command: Load Default QT1 Port"
            ::= { qt1CommandControlEntry 7 }


--
--  SYSTEM Information Table
--

        qt1SystemInfoTable  OBJECT-TYPE
            SYNTAX  SEQUENCE OF QT1SystemInformationEntry
            ACCESS  not-accessible
            STATUS  mandatory
            DESCRIPTION
                "The system information table."
            ::= { qt1-card 18 }

        qt1SystemInformationEntry  OBJECT-TYPE
            SYNTAX  QT1SystemInformationEntry
            ACCESS  not-accessible
            STATUS  mandatory
            DESCRIPTION
                "An entry in the system information table."
            INDEX { qt1SISlotIndex }
            ::= { qt1SystemInfoTable 1 }

        QT1SystemInformationEntry ::= SEQUENCE {
            qt1SISlotIndex              LSSlotID,
            qt1PROMVersion              DisplayString,
            qt1HardwareVersion          DisplayString
        }

        qt1SISlotIndex  OBJECT-TYPE
            SYNTAX  LSSlotID
            ACCESS  read-only
            STATUS  mandatory
            DESCRIPTION
                "Qt1 slot"
            ::= { qt1SystemInformationEntry 1 }

        qt1PROMVersion  OBJECT-TYPE
            SYNTAX  DisplayString (SIZE (0..255) )
            ACCESS  read-only
            STATUS  mandatory
            DESCRIPTION
                " qt1 PROM Version"
            ::= { qt1SystemInformationEntry 2 }

        qt1HardwareVersion  OBJECT-TYPE
            SYNTAX  DisplayString (SIZE (0..255) )
            ACCESS  read-only
            STATUS  mandatory
            DESCRIPTION
                " qt1 Hardware Version"
            ::= { qt1SystemInformationEntry 3 }


--
--  QT1 Customer Information Table
--

        qt1CustomerInfoTable  OBJECT-TYPE
            SYNTAX  SEQUENCE OF QT1CustomerInfoEntry
            ACCESS  not-accessible
            STATUS  mandatory
            DESCRIPTION
                "The Customer Information table."
            ::= { qt1-card 99 }

        qt1CustomerInfoEntry  OBJECT-TYPE
            SYNTAX  QT1CustomerInfoEntry
            ACCESS  not-accessible
            STATUS  mandatory
            DESCRIPTION
                "An entry in the Customer Information table."
            INDEX { qt1CISlotIndex , qt1CIPortIndex }
            ::= { qt1CustomerInfoTable 1 }

        QT1CustomerInfoEntry ::= SEQUENCE {
            qt1CISlotIndex              LSSlotID,
            qt1CIPortIndex              PortID,
            qt1CICustomerInfo           DisplayString (SIZE(0..64))
        }

        qt1CISlotIndex    OBJECT-TYPE
            SYNTAX  LSSlotID
            ACCESS  read-only
            STATUS  mandatory
            DESCRIPTION
                "QT1 slot index"
            ::= { qt1CustomerInfoEntry 1 }

        qt1CIPortIndex    OBJECT-TYPE
            SYNTAX  PortID
            ACCESS  read-only
            STATUS  mandatory
            DESCRIPTION
                "Port number"
            ::= { qt1CustomerInfoEntry 2 }

        qt1CICustomerInfo  OBJECT-TYPE
            SYNTAX  DisplayString (SIZE (0..64) )
            ACCESS  read-write
            STATUS  mandatory
            DESCRIPTION
                "Customer information"
            ::= { qt1CustomerInfoEntry 3 }

        qt1TotalCard   OBJECT-TYPE
            SYNTAX  INTEGER
            ACCESS  read-only
            STATUS  mandatory
            DESCRIPTION
                "Total cards of QT1"
            ::= { qt1-card 100 }

--======================================================================--
--======================================================================--
--  g703 Card MIB
--======================================================================--
--======================================================================--


--
--  Alarm History Table
--

        g703AlmHistoryTable  OBJECT-TYPE
            SYNTAX  SEQUENCE OF G703AlmHistoryEntry
            ACCESS  not-accessible
            STATUS  mandatory
            DESCRIPTION
                " G.703 Alarm History Table"
            ::= { g703-card 1 }

        g703AlmHistoryEntry  OBJECT-TYPE
            SYNTAX  G703AlmHistoryEntry
            ACCESS  not-accessible
            STATUS  mandatory
            DESCRIPTION
                " "
            INDEX { g703AlmHistorySlotIndex , g703AlmHistoryPortIndex }
            ::= { g703AlmHistoryTable 1 }

        G703AlmHistoryEntry ::= SEQUENCE {
            g703AlmHistorySlotIndex     LSSlotID,
            g703AlmHistoryPortIndex     PortID,
            g703AlmHistoryState         INTEGER,
            g703AlmHistoryCount         INTEGER,
            g703AlmHistoryEnable        INTEGER
        }

        g703AlmHistorySlotIndex  OBJECT-TYPE
            SYNTAX  LSSlotID
            ACCESS  read-only
            STATUS  mandatory
            DESCRIPTION
                "G703 slot"
            ::= { g703AlmHistoryEntry 1 }

        g703AlmHistoryPortIndex  OBJECT-TYPE
            SYNTAX  PortID
            ACCESS  read-only
            STATUS  mandatory
            DESCRIPTION
                "G.703 port 1-8"
            ::= { g703AlmHistoryEntry 2 }

        g703AlmHistoryState  OBJECT-TYPE
            SYNTAX  INTEGER {
                    ok(1),
                    alarm(2),
                    disable(3),
                    na(4)
                }
            ACCESS  read-only
            STATUS  mandatory
            DESCRIPTION
                " Alarm Current State"
            ::= { g703AlmHistoryEntry 3 }

        g703AlmHistoryCount  OBJECT-TYPE
            SYNTAX  INTEGER
            ACCESS  read-only
            STATUS  mandatory
            DESCRIPTION
                " Alarm Count which happened "
            ::= { g703AlmHistoryEntry 4 }

        g703AlmHistoryEnable  OBJECT-TYPE
            SYNTAX  INTEGER {
                    disable(1),
                    major(2),
                    critical(3),
                    minor(4),
                    na(5)
                }
            ACCESS  read-only
            STATUS  mandatory
            DESCRIPTION
                "Alarm is enabled or not"
            ::= { g703AlmHistoryEntry 5 }

--
--  Alarm Control Table
--

        g703AlarmControlTable  OBJECT-TYPE
            SYNTAX  SEQUENCE OF G703AlarmControlEntry
            ACCESS  not-accessible
            STATUS  mandatory
            DESCRIPTION
                "G.703 Alarm Control Table."
            ::= { g703-card 2 }

        g703AlarmControlEntry  OBJECT-TYPE
            SYNTAX  G703AlarmControlEntry
            ACCESS  not-accessible
            STATUS  mandatory
            DESCRIPTION
                "An entry in the G.703 Alarm Control Table."
            INDEX { g703AlarmSlotIndex , g703AlarmPortIndex }
            ::= { g703AlarmControlTable 1 }

        G703AlarmControlEntry ::= SEQUENCE {
            g703AlarmSlotIndex          LSSlotID,
            g703AlarmPortIndex          PortID,
            g703AlarmType               INTEGER,
            g703AlarmSetup              LsAlarmSeverity
        }

        g703AlarmSlotIndex  OBJECT-TYPE
            SYNTAX  LSSlotID
            ACCESS  read-only
            STATUS  mandatory
            DESCRIPTION
                "G.703 slot index"
            ::= { g703AlarmControlEntry 1 }

        g703AlarmPortIndex  OBJECT-TYPE
            SYNTAX  PortID
            ACCESS  read-only
            STATUS  mandatory
            DESCRIPTION
                "G.703 port 1-8"
            ::= { g703AlarmControlEntry 2 }

        g703AlarmType  OBJECT-TYPE
            SYNTAX  INTEGER {
                    los(1)
                }
            ACCESS  read-only
            STATUS  mandatory
            DESCRIPTION
                "Alarm Type"
            ::= { g703AlarmControlEntry 3 }

        g703AlarmSetup  OBJECT-TYPE
            SYNTAX  LsAlarmSeverity
            ACCESS  read-write
            STATUS  mandatory
            DESCRIPTION
                "Alarm is enabled or not"
            ::= { g703AlarmControlEntry 4 }

--
-- Line Diagnostic Control Table
--

        g703LineDiagControlTable  OBJECT-TYPE
            SYNTAX  SEQUENCE OF G703LineDiagControlEntry
            ACCESS  not-accessible
            STATUS  mandatory
            DESCRIPTION
                "G.703 Diagnostic Control Table."
            ::= { g703-card 3 }

        g703LineDiagControlEntry  OBJECT-TYPE
            SYNTAX  G703LineDiagControlEntry
            ACCESS  not-accessible
            STATUS  mandatory
            DESCRIPTION
                "An entry of G.703 diagnostic control table."
            INDEX { g703DCSlotIndex , g703DCPortIndex }
            ::= { g703LineDiagControlTable 1 }

        G703LineDiagControlEntry ::= SEQUENCE {
            g703DCSlotIndex             LSSlotID,
            g703DCPortIndex             PortID,
            g703LoopbackType            INTEGER
--               g703BertControl
--                 INTEGER,
--               g703BertStatus
--                 INTEGER,
--               g703ElapseSeconds
--                 INTEGER,
--               g703ErrorSeconds
--                 INTEGER,
--               g703ErrorBits
--                 INTEGER




    }

        g703DCSlotIndex  OBJECT-TYPE
            SYNTAX  LSSlotID
            ACCESS  read-only
            STATUS  mandatory
            DESCRIPTION
                "G703 slot"
            ::= { g703LineDiagControlEntry 1 }

        g703DCPortIndex  OBJECT-TYPE
            SYNTAX  PortID
            ACCESS  read-only
            STATUS  mandatory
            DESCRIPTION
                " Port index, Total 8 ports"
            ::= { g703LineDiagControlEntry 2 }

        g703LoopbackType  OBJECT-TYPE
            SYNTAX  INTEGER {
                    no-loopback(1),
                    local-Loopback(2),
                    payLoad-Loopback(3)
                }
            ACCESS  read-write
            STATUS  mandatory
            DESCRIPTION
                "G703 Loopback Type"
            ::= { g703LineDiagControlEntry 3 }

--         g703BertControl  OBJECT-TYPE
--             SYNTAX  INTEGER {
--                        bert-OFF(1),
--                        bert-ON(2),
--                        reset(3),
--                        inject-Error(4)
--                     }
--             ACCESS  read-write
--             STATUS  mandatory
--             DESCRIPTION
--                "BERT control"
--             ::= { g703LineDiagControlEntry 4 }
--
--        g703BertStatus  OBJECT-TYPE
--             SYNTAX  INTEGER {
--                        bert-Sync(1),
--                        bert-Unsync(2),
--                        bert-Not-Active(3)
--                     }
--             ACCESS  read-only
--             STATUS  mandatory
--             DESCRIPTION
--                "BERT status"
--             ::= { g703LineDiagControlEntry 5 }
--
--        g703ElapseSeconds  OBJECT-TYPE
--             SYNTAX  INTEGER
--             ACCESS  read-only
--             STATUS  mandatory
--             DESCRIPTION
--                "Elapse seconds"
--             ::= { g703LineDiagControlEntry 6 }
--
--         g703ErrorSeconds OBJECT-TYPE
--             SYNTAX  INTEGER
--             ACCESS  read-only
--             STATUS  mandatory
--             DESCRIPTION
--                "Error seconds"
--             ::= { g703LineDiagControlEntry 7 }
--
--         g703ErrorBits  OBJECT-TYPE
--             SYNTAX  INTEGER
--             ACCESS  read-only
--             STATUS  mandatory
--             DESCRIPTION
--                "Error bits"
--             ::= { g703LineDiagControlEntry 8 }


--
--  G703 Status Table
--

        g703StatusTable  OBJECT-TYPE
            SYNTAX  SEQUENCE OF G703Status
            ACCESS  not-accessible
            STATUS  mandatory
            DESCRIPTION
                "The G.703 status table."
            ::= { g703-card 4 }

        g703StatusEntry  OBJECT-TYPE
            SYNTAX  G703Status
            ACCESS  not-accessible
            STATUS  mandatory
            DESCRIPTION
                "An entry in the G.703 status table."
            INDEX { g703StSlotIndex , g703StPortIndex
                }
            ::= { g703StatusTable 1 }

        G703Status ::= SEQUENCE {
            g703StSlotIndex             LSSlotID,
            g703StPortIndex             PortID,
            g703StatusLOS               INTEGER
        }

        g703StSlotIndex  OBJECT-TYPE
            SYNTAX  LSSlotID
            ACCESS  read-only
            STATUS  mandatory
            DESCRIPTION
                "G703 slot"
            ::= { g703StatusEntry 1 }

        g703StPortIndex  OBJECT-TYPE
            SYNTAX  PortID
            ACCESS  read-only
            STATUS  mandatory
            DESCRIPTION
                " Port index"
            ::= { g703StatusEntry 2 }

        g703StatusLOS  OBJECT-TYPE
            SYNTAX  INTEGER {
                    no(1),
                    yes(2)
                }
            ACCESS  read-only
            STATUS  mandatory
            DESCRIPTION
                " G.703 LOS status "
            ::= { g703StatusEntry 3 }

--
--  SYSTEM Information Table
--

        g703SystemInfoTable  OBJECT-TYPE
            SYNTAX  SEQUENCE OF G703SystemInformation
            ACCESS  not-accessible
            STATUS  mandatory
            DESCRIPTION
                "The system information table."
            ::= { g703-card 5 }

        g703SystemInfoEntry  OBJECT-TYPE
            SYNTAX  G703SystemInformation
            ACCESS  not-accessible
            STATUS  mandatory
            DESCRIPTION
                "An entry in the system information table."
            INDEX { g703SISlotIndex }
            ::= { g703SystemInfoTable 1 }

        G703SystemInformation ::= SEQUENCE {
            g703SISlotIndex             LSSlotID,
            g703FpgaVersion             DisplayString
        }

        g703SISlotIndex  OBJECT-TYPE
            SYNTAX  LSSlotID
            ACCESS  read-only
            STATUS  mandatory
            DESCRIPTION
                "G703 slot"
            ::= { g703SystemInfoEntry 1 }

        g703FpgaVersion  OBJECT-TYPE
            SYNTAX  DisplayString (SIZE (0..255) )
            ACCESS  read-only
            STATUS  mandatory
            DESCRIPTION
                " G.703 FPGA Version"
            ::= { g703SystemInfoEntry 2 }

--
--  Command Control Table
--

        g703CommandControlTable  OBJECT-TYPE
            SYNTAX  SEQUENCE OF G703CommandControlEntry
            ACCESS  not-accessible
            STATUS  mandatory
            DESCRIPTION
                "The command control table."
            ::= { g703-card 6 }

        g703CommandControlEntry  OBJECT-TYPE
            SYNTAX  G703CommandControlEntry
            ACCESS  not-accessible
            STATUS  mandatory
            DESCRIPTION
                "An entry in the command control table."
            INDEX { g703CCSlotIndex }
            ::= { g703CommandControlTable 1 }

        G703CommandControlEntry ::= SEQUENCE {
            g703CCSlotIndex             LSSlotID,
            g703AlarmCountClear         INTEGER
        }

        g703CCSlotIndex  OBJECT-TYPE
            SYNTAX  LSSlotID
            ACCESS  read-only
            STATUS  mandatory
            DESCRIPTION
                "G703 slot"
            ::= { g703CommandControlEntry 1 }

        g703AlarmCountClear    OBJECT-TYPE
            SYNTAX  INTEGER {
                    reset(1)
                }
            ACCESS  read-write
            STATUS  mandatory
            DESCRIPTION
                "Command: Clear alarm count"
            ::= { g703CommandControlEntry 2 }

        g703TotalCard   OBJECT-TYPE
            SYNTAX  INTEGER
            ACCESS  read-only
            STATUS  mandatory
            DESCRIPTION
                "Total cards of G703"
            ::= { g703-card 100 }

--======================================================================--
--======================================================================--
--  G.SHDSL-2 MIB
--======================================================================--
--======================================================================--


--
--  GDSL2 SYSTEM Table
--

        gdsl2SystemTable  OBJECT-TYPE
            SYNTAX  SEQUENCE OF Gdsl2SystemEntry
            ACCESS  not-accessible
            STATUS  mandatory
            DESCRIPTION
                "The system control table."
            ::= { gdsl2-card 1 }

        gdsl2SystemEntry  OBJECT-TYPE
            SYNTAX  Gdsl2SystemEntry
            ACCESS  not-accessible
            STATUS  mandatory
            DESCRIPTION
                "An entry in the system table."
            INDEX { gdsl2SysSlotIndex ,
                    gdsl2SysPortIndex ,
                    gdsl2SysHTUIndex }
            ::= { gdsl2SystemTable 1 }

        Gdsl2SystemEntry ::= SEQUENCE {
            gdsl2SysSlotIndex           LSSlotID,
            gdsl2SysPortIndex           G2PortID,
            gdsl2SysHTUIndex            INTEGER,
            gdsl2Mode                   INTEGER,
            gdsl2ServiceType            INTEGER,
            gdsl2ClockSource            INTEGER,
            gdsl2Model                  INTEGER

    }

        gdsl2SysSlotIndex  OBJECT-TYPE
            SYNTAX  LSSlotID
            ACCESS  read-only
            STATUS  mandatory
            DESCRIPTION
                "Gshdsl2 slot"
            ::= { gdsl2SystemEntry 1 }

        gdsl2SysPortIndex  OBJECT-TYPE
            SYNTAX  G2PortID
            ACCESS  read-only
            STATUS  mandatory
            DESCRIPTION
                " Port 1/3."
            ::= { gdsl2SystemEntry 2 }

        gdsl2SysHTUIndex  OBJECT-TYPE
            SYNTAX  INTEGER {
                    local(1),
                    remote(2)
                }
            ACCESS  read-only
            STATUS  mandatory
            DESCRIPTION
                "Local or Remote"
            ::= { gdsl2SystemEntry 3 }

        gdsl2Mode  OBJECT-TYPE
            SYNTAX  INTEGER {
                    master(1),
                    slave(2)
                }
            ACCESS  read-write
            STATUS  mandatory
            DESCRIPTION
                "G.SHDSL mode (Master or Slave)"
            ::= { gdsl2SystemEntry 4 }

        gdsl2ServiceType  OBJECT-TYPE
            SYNTAX  INTEGER {
                    one-pair(1),
                    two-pairs(2)
                }
            ACCESS  read-only
            STATUS  mandatory
            DESCRIPTION
                " Service Configuration"
            ::= { gdsl2SystemEntry 5 }

        gdsl2ClockSource  OBJECT-TYPE
            SYNTAX  INTEGER {
                    line(1),
                    system(2),
                    dte(3),
                    e1t1(4)
                }
            ACCESS  read-write
            STATUS  mandatory
            DESCRIPTION
                " System Master Clock Source"
            ::= { gdsl2SystemEntry 6 }

        gdsl2Model  OBJECT-TYPE
            SYNTAX  INTEGER {
                    rack(1),
                    h3300-3s(2),
                    h3300(3),
                    h3310(4),
                    h3304(5),
                    other(99)
                }
            ACCESS  read-only
            STATUS  mandatory
            DESCRIPTION
                "G.shdsl model"
            ::= { gdsl2SystemEntry 7 }


--
--  GDSL2 Line Configuartion for Loop-1, Loop-2
--

        gdsl2LineConfigTable  OBJECT-TYPE
            SYNTAX  SEQUENCE OF Gdsl2LineConfigEntry
            ACCESS  not-accessible
            STATUS  mandatory
            DESCRIPTION
                "The G.SHDSL Line Configuration table."
            ::= { gdsl2-card 2 }

        gdsl2LineConfigEntry  OBJECT-TYPE
            SYNTAX  Gdsl2LineConfigEntry
            ACCESS  not-accessible
            STATUS  mandatory
            DESCRIPTION
                "An entry in the G.SHDSL Line Configuration table."
            INDEX { gdsl2LCSlotIndex ,
                    gdsl2LCPortIndex ,
                    gdsl2LineLoopIndex }
            ::= { gdsl2LineConfigTable 1 }

        Gdsl2LineConfigEntry ::= SEQUENCE {
            gdsl2LCSlotIndex            LSSlotID,
            gdsl2LCPortIndex            G2PortID,
            gdsl2LineLoopIndex          INTEGER,
            gdsl2LineRate               INTEGER,
            gdsl2LineCode               INTEGER,
            gdsl2LineLoopNum            INTEGER,
            gdsl2LineNx64               INTEGER,
            gdsl2CAS                    INTEGER,
            gdsl2OOS                    INTEGER
        }

        gdsl2LCSlotIndex  OBJECT-TYPE
            SYNTAX  LSSlotID
            ACCESS  read-only
            STATUS  mandatory
            DESCRIPTION
                "Gshdsl2 slot"
            ::= { gdsl2LineConfigEntry 1 }

        gdsl2LCPortIndex  OBJECT-TYPE
            SYNTAX  G2PortID
            ACCESS  read-only
            STATUS  mandatory
            DESCRIPTION
                " Port 1/3."
            ::= { gdsl2LineConfigEntry 2 }

        gdsl2LineLoopIndex  OBJECT-TYPE
            SYNTAX  INTEGER (1..2)
            ACCESS  read-only
            STATUS  mandatory
            DESCRIPTION
                "Unit Loop Number"
            ::= { gdsl2LineConfigEntry 3 }

        gdsl2LineRate  OBJECT-TYPE
            SYNTAX  INTEGER {
                    r0Kbps(0),
                    r72Kbps(1),
                    r136Kbps(2),
                    r200Kbps(3),
                    r264Kbps(4),
                    r328Kbps(5),
                    r392Kbps(6),
                    r456Kbps(7),
                    r520Kbps(8),
                    r584Kbps(9),
                    r648Kbps(10),
                    r712Kbps(11),
                    r776Kbps(12),
                    r840Kbps(13),
                    r904Kbps(14),
                    r968Kbps(15),
                    r1032Kbps(16),
                    r1096Kbps(17),
                    r1160Kbps(18),
                    r1224Kbps(19),
                    r1288Kbps(20),
                    r1352Kbps(21),
                    r1416Kbps(22),
                    r1480Kbps(23),
                    r1544Kbps(24),
                    r1608Kbps(25),
                    r1672Kbps(26),
                    r1736Kbps(27),
                    r1800Kbps(28),
                    r1864Kbps(29),
                    r1928Kbps(30),
                    r1992Kbps(31),
                    r2056Kbps(32)
                }
            ACCESS  read-only
            STATUS  mandatory
            DESCRIPTION
                "To describe G.SHDSL Line Rate of specified loop,
                for an example: 776Kbps"
            ::= { gdsl2LineConfigEntry 4 }

        gdsl2LineCode  OBJECT-TYPE
            SYNTAX  INTEGER {
                    code-2b1q(1),
                    code-cap(2)
                }
            ACCESS  read-only
            STATUS  mandatory
            DESCRIPTION
                " G.SHDSL Line Coding"
            ::= { gdsl2LineConfigEntry 5 }

        gdsl2LineLoopNum OBJECT-TYPE
            SYNTAX INTEGER {
                    loop-one(1),
                    loop-two(2),
                    two-loops(3),
                    one-one(4)
                }
            ACCESS  read-write
            STATUS  mandatory
            DESCRIPTION
                " gdsl Loop number"
            ::= { gdsl2LineConfigEntry 6 }

        gdsl2LineNx64  OBJECT-TYPE
            SYNTAX  INTEGER (3..32)
            ACCESS  read-write
            STATUS  mandatory
            DESCRIPTION
                "Number of N*64 Kbps"
            ::= { gdsl2LineConfigEntry 7 }

        gdsl2CAS  OBJECT-TYPE
            SYNTAX  INTEGER {
                    on(1),
                    off(2)
                }
            ACCESS  read-write
            STATUS  mandatory
            DESCRIPTION
                "G.SHDSL CAS"
            ::= { gdsl2LineConfigEntry 8 }

        gdsl2OOS  OBJECT-TYPE
            SYNTAX  INTEGER   {
                    b0001(1),
                    b0010(2),
                    b0011(3),
                    b0100(4),
                    b0101(5),
                    b0110(6),
                    b0111(7),
                    b1000(8),
                    b1001(9),
                    b1010(10),
                    b1011(11),
                    b1100(12),
                    b1101(13),
                    b1110(14),
                    b1111(15)
                }
            ACCESS  read-write
            STATUS  mandatory
            DESCRIPTION
                "OOS"
            ::= { gdsl2LineConfigEntry 9 }


--
--  GDSL2 AI Configuartion
--

        gdsl2AIConfigTable  OBJECT-TYPE
            SYNTAX  SEQUENCE OF Gdsl2AIConfigEntry
            ACCESS  not-accessible
            STATUS  mandatory
            DESCRIPTION
                "The G.SHDSL Application Interface Configuration table."
            ::= { gdsl2-card 3 }

        gdsl2AIConfigEntry  OBJECT-TYPE
            SYNTAX  Gdsl2AIConfigEntry
            ACCESS  not-accessible
            STATUS  mandatory
            DESCRIPTION
                "An entry in the G.SHDSL AI Configuration table."
            INDEX { gdsl2AICSlotIndex ,
                    gdsl2AICPortIndex ,
                    gdsl2AiNumber }
            ::= { gdsl2AIConfigTable 1 }

        Gdsl2AIConfigEntry ::= SEQUENCE {
            gdsl2AICSlotIndex           LSSlotID,
            gdsl2AICPortIndex           G2PortID,
            gdsl2AiNumber               INTEGER,
            gdsl2DteReady               INTEGER,
            gdsl2DteRate                INTEGER,
            gdsl2DteClockPolarity       INTEGER,
            gdsl2DteDataPolarity        INTEGER,
            gdsl2DteRTS                 INTEGER,
            gdsl2DteTTM                 INTEGER,
            gdsl2DteV54                 INTEGER,
            gdsl2DteInterface           INTEGER,
            gdsl2DS1Ready               INTEGER,
            gdsl2DS1Framing             INTEGER,
            gdsl2DS1Code                INTEGER,
            gdsl2DS1CAS                 INTEGER,
            gdsl2DS1Idle                INTEGER,
            gdsl2T1Interf               INTEGER,
            gdsl2T1EquLbo               INTEGER,
            gdsl2DS1Map                 DisplayString (SIZE(32)),
            gdsl2E1T1Mode               INTEGER,
            gdsl2AISetResponse          INTEGER
        }

        gdsl2AICSlotIndex  OBJECT-TYPE
            SYNTAX  LSSlotID
            ACCESS  read-only
            STATUS  mandatory
            DESCRIPTION
                "Gshdsl2 slot"
            ::= { gdsl2AIConfigEntry 1 }

        gdsl2AICPortIndex  OBJECT-TYPE
            SYNTAX  G2PortID
            ACCESS  read-only
            STATUS  mandatory
            DESCRIPTION
                " Port 1/3."
            ::= { gdsl2AIConfigEntry 2 }

        gdsl2AiNumber  OBJECT-TYPE
            SYNTAX  INTEGER  {
--                      local(1),
                    remote(2)
                }
            ACCESS  read-only
            STATUS  mandatory
            DESCRIPTION
                "Local or Remote unit"
            ::= { gdsl2AIConfigEntry 3 }

        gdsl2DteReady   OBJECT-TYPE
            SYNTAX  INTEGER  {
                    dte-ready(1),
                    dte-not-ready(2)
                }
            ACCESS  read-only
            STATUS  mandatory
            DESCRIPTION
                "DTE port is present or not"
            ::= { gdsl2AIConfigEntry 4 }

        gdsl2DteRate  OBJECT-TYPE
            SYNTAX  INTEGER {
                    dte64K(1),
                    dte128K(2),
                    dte192K(3),
                    dte256K(4),
                    dte320K(5),
                    dte384K(6),
                    dte448K(7),
                    dte512K(8),
                    dte576K(9),
                    dte640K(10),
                    dte704K(11),
                    dte768K(12),
                    dte832K(13),
                    dte896K(14),
                    dte960K(15),
                    dte1024K(16),
                    dte1088K(17),
                    dte1152K(18),
                    dte1216K(19),
                    dte1280K(20),
                    dte1344K(21),
                    dte1408K(22),
                    dte1472K(23),
                    dte1536K(24),
                    dte1600K(25),
                    dte1664K(26),
                    dte1728K(27),
                    dte1792K(28),
                    dte1856K(29),
                    dte1920K(30),
                    dte1984K(31),
                    dte2048K(32),
                    none(33)
                }
            ACCESS  read-write
            STATUS  mandatory
            DESCRIPTION
                " G.SHDSL DTE Base Rate"
            ::= { gdsl2AIConfigEntry 5 }

        gdsl2DteClockPolarity  OBJECT-TYPE
            SYNTAX  INTEGER {
                    clock-normal(1),
                    clock-inverted(2),
                    none(3)
                }
            ACCESS  read-write
            STATUS  mandatory
            DESCRIPTION
                " G.SHDSL DTE Clock Polarity"
            ::= { gdsl2AIConfigEntry 6 }

        gdsl2DteDataPolarity  OBJECT-TYPE
            SYNTAX  INTEGER {
                    data-normal(1),
                    data-inverted(2),
                    none(3)
                }
            ACCESS  read-write
            STATUS  mandatory
            DESCRIPTION
                " G.SHDSL DTE Data Polarity"
            ::= { gdsl2AIConfigEntry 7 }

        gdsl2DteRTS  OBJECT-TYPE
            SYNTAX  INTEGER {
                    rts-active(1),
                    rts-permanent(2),
                    none(3)
                }
            ACCESS  read-write
            STATUS  mandatory
            DESCRIPTION
                " G.SHDSL DTE RTS Mode"
            ::= { gdsl2AIConfigEntry 8 }

        gdsl2DteTTM  OBJECT-TYPE
            SYNTAX  INTEGER {
                    ttm-off(1),
                    ttm-on(2),
                    none(3)
                }
            ACCESS  read-write
            STATUS  mandatory
            DESCRIPTION
                " G.SHDSL DTE TTM Mode"
            ::= { gdsl2AIConfigEntry 9 }

        gdsl2DteV54  OBJECT-TYPE
            SYNTAX  INTEGER {
                    v54-off(1),
                    v54-on(2),
                    none(3)
                }
            ACCESS  read-write
            STATUS  mandatory
            DESCRIPTION
                " G.SHDSL DTE V.54 Loopback Mode"
            ::= { gdsl2AIConfigEntry 10 }

        gdsl2DteInterface  OBJECT-TYPE
            SYNTAX  INTEGER {
                    v35(1),
                    eia530-rs449(2),
                    x21(3),
                    rs232(4),
                    router(7),
                    subrate(8),
                    dte-e1(9),
                    dte-t1(10),
                    bridge(12),
                    n64-v35(17),
                    n64-eia530(18),
                    n64-x21(19),
                    n64-e1(25),
                    none(5)
                }
            ACCESS  read-only
            STATUS  mandatory
            DESCRIPTION
                " G.SHDSL DTE Interface Type"
            ::= { gdsl2AIConfigEntry 11 }

        gdsl2DS1Ready  OBJECT-TYPE
            SYNTAX  INTEGER {
                    ds1-ready(1),
                    ds1-not-ready(2)
                }
            ACCESS  read-only
            STATUS  mandatory
            DESCRIPTION
                "G.SHDSL DS1 unit is present or not"
            ::= { gdsl2AIConfigEntry 12 }

        gdsl2DS1Framing  OBJECT-TYPE
            SYNTAX  INTEGER {
                    unframe(1),
                    d4(2),
                    esf(3),
                    esf-t1-403(9),
                    crc-off(4),
                    crc-on(5),
                    cas-crc-off(6),
                    cas-crc-on(7),
                    none(8)
                }
            ACCESS  read-write
            STATUS  mandatory
            DESCRIPTION
                " G.SHDSL DS1 Framing"
            ::= { gdsl2AIConfigEntry 13 }

        gdsl2DS1Code  OBJECT-TYPE
            SYNTAX  INTEGER {
                    b8zs(1),
                    ami(2),
                    hdb3(3),
                    none(4)
                }
            ACCESS  read-write
            STATUS  mandatory
            DESCRIPTION
                " G.SHDSL DS1 Coding"
            ::= { gdsl2AIConfigEntry 14 }

        gdsl2DS1CAS  OBJECT-TYPE
            SYNTAX  INTEGER {
                    on(1),
                    off(2),
                    none(3)
                }
            ACCESS  read-only
            STATUS  mandatory
            DESCRIPTION
                " G.SHDSL DS1 CAS"
            ::= { gdsl2AIConfigEntry 15 }

        gdsl2DS1Idle  OBJECT-TYPE
            SYNTAX  INTEGER
            ACCESS  read-write
            STATUS  mandatory
            DESCRIPTION
                " G.SHDSL DS1 Idle code"
            ::= { gdsl2AIConfigEntry 16 }

        gdsl2T1Interf  OBJECT-TYPE
            SYNTAX  INTEGER {
                    short-haul(1),
                    long-haul(2),
                    none(3)
                }
            ACCESS  read-write
            STATUS  mandatory
            DESCRIPTION
                " G.SHDSL T1 Interface"
            ::= { gdsl2AIConfigEntry 17 }

        gdsl2T1EquLbo  OBJECT-TYPE
            SYNTAX  INTEGER {
                    equ-0-133-feet(1),
                    equ-133-266-feet(2),
                    equ-266-399-feet(3),
                    equ-399-533-feet(4),
                    equ-533-655-feet(5),
                    none(6),
                    lbo-0db(11),
                    lbo-75db(12),
                    lbo-15db(13),
                    lbo-225db(14)
                }
            ACCESS  read-write
            STATUS  mandatory
            DESCRIPTION
                " G.SHDSL T1 EQU/LBO"
            ::= { gdsl2AIConfigEntry 18 }

        gdsl2DS1Map  OBJECT-TYPE
            SYNTAX  DisplayString (SIZE(32))
            ACCESS  read-write
            STATUS  mandatory
            DESCRIPTION
                " G.SHDSL DS1 Map"
            ::= { gdsl2AIConfigEntry 20 }

        gdsl2E1T1Mode  OBJECT-TYPE
            SYNTAX  INTEGER {
                    e1(1),
                    t1(2),
                    na(3)
                }
            ACCESS  read-write
            STATUS  mandatory
            DESCRIPTION
                " G.SHDSL E1/T1 Mode"
            ::= { gdsl2AIConfigEntry 21 }

        gdsl2AISetResponse  OBJECT-TYPE
            SYNTAX  INTEGER {
                    na(1),
                    ok(2),
                    fail(3)
                }
            ACCESS  read-write
            STATUS  mandatory
            DESCRIPTION
                " G.SHDSL Config Set response"
            ::= { gdsl2AIConfigEntry 99 }


--
--  GDSL2 Current Performance Table
--

        gdsl2CurrPerfTable  OBJECT-TYPE
            SYNTAX  SEQUENCE OF Gdsl2CurrPerfEntry
            ACCESS  not-accessible
            STATUS  mandatory
            DESCRIPTION
                ""
            ::= { gdsl2-card 4 }

        gdsl2CurrPerfEntry  OBJECT-TYPE
            SYNTAX  Gdsl2CurrPerfEntry
            ACCESS  not-accessible
            STATUS  mandatory
            DESCRIPTION
                " "
            INDEX { gdsl2CPSlotIndex ,
                    gdsl2CPPortIndex ,
                    gdsl2CurrPerfTypeIndex }
            ::= { gdsl2CurrPerfTable 1 }

        Gdsl2CurrPerfEntry ::= SEQUENCE  {
            gdsl2CPSlotIndex            LSSlotID,
            gdsl2CPPortIndex            G2PortID,
            gdsl2CurrPerfTypeIndex      INTEGER,
            gdsl2CurrES                 INTEGER,
            gdsl2CurrSES                INTEGER,
            gdsl2CurrUAS                INTEGER,
            gdsl2Curr15MinTimeElapsed   INTEGER,
            gdsl2Valid15MinInterval     INTEGER
        }

        gdsl2CPSlotIndex  OBJECT-TYPE
            SYNTAX  LSSlotID
            ACCESS  read-only
            STATUS  mandatory
            DESCRIPTION
                "Gshdsl2 slot"
            ::= { gdsl2CurrPerfEntry 1 }

        gdsl2CPPortIndex  OBJECT-TYPE
            SYNTAX  G2PortID
            ACCESS  read-only
            STATUS  mandatory
            DESCRIPTION
                " Port 1/3."
            ::= { gdsl2CurrPerfEntry 2 }

        gdsl2CurrPerfTypeIndex  OBJECT-TYPE
            SYNTAX  INTEGER {
                    master-loop-1(1),
                    master-loop-2(2),
                    master-ds1(3),
                    slave-loop-1(4),
                    slave-loop-2(5),
                    slave-ds1(6)
                }
            ACCESS  read-only
            STATUS  mandatory
            DESCRIPTION
                "Performance Type"
            ::= { gdsl2CurrPerfEntry 3 }

        gdsl2CurrES  OBJECT-TYPE
            SYNTAX  INTEGER
            ACCESS  read-only
            STATUS  mandatory
            DESCRIPTION
                " ES Error Counter "
            ::= { gdsl2CurrPerfEntry 4 }

        gdsl2CurrSES  OBJECT-TYPE
            SYNTAX  INTEGER
            ACCESS  read-only
            STATUS  mandatory
            DESCRIPTION
                " SES Error Counter "
            ::= { gdsl2CurrPerfEntry 5 }

        gdsl2CurrUAS  OBJECT-TYPE
            SYNTAX  INTEGER
            ACCESS  read-only
            STATUS  mandatory
            DESCRIPTION
                " UAS Error Counter "
            ::= { gdsl2CurrPerfEntry 6 }

        gdsl2Curr15MinTimeElapsed  OBJECT-TYPE
            SYNTAX  INTEGER
            ACCESS  read-only
            STATUS  mandatory
            DESCRIPTION
                " Current 15-minute time elapsed"
            ::= { gdsl2CurrPerfEntry 7 }

        gdsl2Valid15MinInterval  OBJECT-TYPE
            SYNTAX  INTEGER
            ACCESS  read-only
            STATUS  mandatory
            DESCRIPTION
                " Current 1-day Valid 15-min interval"
            ::= { gdsl2CurrPerfEntry 8 }


--
--  GDSL2 Total Performance Table
--

        gdsl2TotalPerfTable  OBJECT-TYPE
            SYNTAX  SEQUENCE OF Gdsl2TotalPerfEntry
            ACCESS  not-accessible
            STATUS  mandatory
            DESCRIPTION
                ""
            ::= { gdsl2-card 5 }

        gdsl2TotalPerfEntry  OBJECT-TYPE
            SYNTAX  Gdsl2TotalPerfEntry
            ACCESS  not-accessible
            STATUS  mandatory
            DESCRIPTION
                " "
            INDEX { gdsl2TPSlotIndex ,
                    gdsl2TPPortIndex ,
                    gdsl2TotalPerfTypeIndex }
            ::= { gdsl2TotalPerfTable 1 }

        Gdsl2TotalPerfEntry ::= SEQUENCE  {
            gdsl2TPSlotIndex            LSSlotID,
            gdsl2TPPortIndex            G2PortID,
            gdsl2TotalPerfTypeIndex     INTEGER,
            gdsl2TotalES                INTEGER,
            gdsl2TotalSES               INTEGER,
            gdsl2TotalUAS               INTEGER
        }

        gdsl2TPSlotIndex  OBJECT-TYPE
            SYNTAX  LSSlotID
            ACCESS  read-only
            STATUS  mandatory
            DESCRIPTION
                "Gshdsl2 slot"
            ::= { gdsl2TotalPerfEntry 1 }

        gdsl2TPPortIndex  OBJECT-TYPE
            SYNTAX  G2PortID
            ACCESS  read-only
            STATUS  mandatory
            DESCRIPTION
                " Port 1/3."
            ::= { gdsl2TotalPerfEntry 2 }

        gdsl2TotalPerfTypeIndex  OBJECT-TYPE
            SYNTAX  INTEGER {
                    master-loop-1(1),
                    master-loop-2(2),
                    master-ds1(3),
                    slave-loop-1(4),
                    slave-loop-2(5),
                    slave-ds1(6)
                }
            ACCESS  read-only
            STATUS  mandatory
            DESCRIPTION
                "Performance Type"
            ::= { gdsl2TotalPerfEntry 3 }

        gdsl2TotalES  OBJECT-TYPE
            SYNTAX  INTEGER
            ACCESS  read-only
            STATUS  mandatory
            DESCRIPTION
                " ES Error Counter "
            ::= { gdsl2TotalPerfEntry 4 }

        gdsl2TotalSES  OBJECT-TYPE
            SYNTAX  INTEGER
            ACCESS  read-only
            STATUS  mandatory
            DESCRIPTION
                " SES Error Counter "
            ::= { gdsl2TotalPerfEntry 5 }

        gdsl2TotalUAS  OBJECT-TYPE
            SYNTAX  INTEGER
            ACCESS  read-only
            STATUS  mandatory
            DESCRIPTION
                " UAS Error Counter "
            ::= { gdsl2TotalPerfEntry 6 }

--
--  Interval Performance Table
--

        gdsl2IntvPerfTable  OBJECT-TYPE
            SYNTAX  SEQUENCE OF Gdsl2IntvPerfEntry
            ACCESS  not-accessible
            STATUS  mandatory
            DESCRIPTION
                ""
            ::= { gdsl2-card 6 }

        gdsl2IntvPerfEntry  OBJECT-TYPE
            SYNTAX  Gdsl2IntvPerfEntry
            ACCESS  not-accessible
            STATUS  mandatory
            DESCRIPTION
                " "
            INDEX { gdsl2IPSlotIndex ,
                    gdsl2IPPortIndex ,
                    gdsl2IntvPerfTypeIndex ,
                    gdsl2IntvPerfPeriod }
            ::= { gdsl2IntvPerfTable 1 }

        Gdsl2IntvPerfEntry ::= SEQUENCE  {
            gdsl2IPSlotIndex            LSSlotID,
            gdsl2IPPortIndex            G2PortID,
            gdsl2IntvPerfTypeIndex      INTEGER,
            gdsl2IntvPerfPeriod         INTEGER,
            gdsl2IntvES                 INTEGER,
            gdsl2IntvSES                INTEGER,
            gdsl2IntvUAS                INTEGER,
            gdsl2IntvAvailable          INTEGER
        }

        gdsl2IPSlotIndex  OBJECT-TYPE
            SYNTAX  LSSlotID
            ACCESS  read-only
            STATUS  mandatory
            DESCRIPTION
                "Gshdsl2 slot"
            ::= { gdsl2IntvPerfEntry 1 }

        gdsl2IPPortIndex  OBJECT-TYPE
            SYNTAX  G2PortID
            ACCESS  read-only
            STATUS  mandatory
            DESCRIPTION
                " Port 1/3."
            ::= { gdsl2IntvPerfEntry 2 }

        gdsl2IntvPerfTypeIndex  OBJECT-TYPE
            SYNTAX  INTEGER {
                    master-loop-1(1),
                    master-loop-2(2),
                    master-ds1(3),
                    slave-loop-1(4),
                    slave-loop-2(5),
                    slave-ds1(6)
                }
            ACCESS  read-only
            STATUS  mandatory
            DESCRIPTION
                "Performance Type"
            ::= { gdsl2IntvPerfEntry 3 }

        gdsl2IntvPerfPeriod  OBJECT-TYPE
            SYNTAX  INTEGER (1..32)
            ACCESS  read-only
            STATUS  mandatory
            DESCRIPTION
                "Performance Interval Period Number"
            ::= { gdsl2IntvPerfEntry 4 }

        gdsl2IntvES  OBJECT-TYPE
            SYNTAX  INTEGER
            ACCESS  read-only
            STATUS  mandatory
            DESCRIPTION
                " ES Error Counter "
            ::= { gdsl2IntvPerfEntry 5 }

        gdsl2IntvSES  OBJECT-TYPE
            SYNTAX  INTEGER
            ACCESS  read-only
            STATUS  mandatory
            DESCRIPTION
                " SES Error Counter "
            ::= { gdsl2IntvPerfEntry 6 }

        gdsl2IntvUAS  OBJECT-TYPE
            SYNTAX  INTEGER
            ACCESS  read-only
            STATUS  mandatory
            DESCRIPTION
                " UAS Error Counter "
            ::= { gdsl2IntvPerfEntry 7 }

        gdsl2IntvAvailable  OBJECT-TYPE
            SYNTAX  INTEGER   {
                    available(1),
                    na(2)
                }
            ACCESS  read-only
            STATUS  mandatory
            DESCRIPTION
                " Interval Available "
            ::= { gdsl2IntvPerfEntry 8 }


--
-- GDSL2 FRACTIONAL TABLE
--

        gdsl2FracTable   OBJECT-TYPE
            SYNTAX  SEQUENCE OF Gdsl2FracEntry
            ACCESS  not-accessible
            STATUS  mandatory
            DESCRIPTION
                " Key: gdsl2FracUnitIndex.gdsl2FracNumber"
            ::= { gdsl2-card 7 }

        gdsl2FracEntry   OBJECT-TYPE
            SYNTAX  Gdsl2FracEntry
            ACCESS  not-accessible
            STATUS  mandatory
            DESCRIPTION
                " "
            INDEX { gdsl2FracSlotIndex ,
                    gdsl2FracPortIndex ,
                    gdsl2FracNumber }
            ::= { gdsl2FracTable 1 }

        Gdsl2FracEntry ::= SEQUENCE {
            gdsl2FracSlotIndex          LSSlotID,
            gdsl2FracPortIndex          G2PortID,
            gdsl2FracNumber             INTEGER  (1..32),
            gdsl2FracIfIndex            INTEGER
        }

        gdsl2FracSlotIndex  OBJECT-TYPE
            SYNTAX  LSSlotID
            ACCESS  read-only
            STATUS  mandatory
            DESCRIPTION
                "Gshdsl2 slot"
            ::= { gdsl2FracEntry 1 }

        gdsl2FracPortIndex  OBJECT-TYPE
            SYNTAX  G2PortID
            ACCESS  read-only
            STATUS  mandatory
            DESCRIPTION
                " Port 1/3."
            ::= { gdsl2FracEntry 2 }

        gdsl2FracNumber   OBJECT-TYPE
            SYNTAX  INTEGER (1..32)
            ACCESS  read-only
            STATUS  mandatory
            DESCRIPTION
                "gdsl2FracNumber "
            ::= { gdsl2FracEntry 3 }

        gdsl2FracIfIndex  OBJECT-TYPE
            SYNTAX  INTEGER {
                    chan-idle(1),
                    chan-ds1(2),
                    chan-dte(3),
                    chan-x(4)
                }
            ACCESS  read-only
            STATUS  mandatory
            DESCRIPTION
                "gdsl2FracIfIndex "
            ::= { gdsl2FracEntry 4 }

--
-- Diagnostic Control Table
--

        gdsl2DiagTable  OBJECT-TYPE
            SYNTAX  SEQUENCE OF Gdsl2DiagEntry
            ACCESS  not-accessible
            STATUS  mandatory
            DESCRIPTION
                ""
            ::= { gdsl2-card 8 }

        gdsl2DiagEntry  OBJECT-TYPE
            SYNTAX  Gdsl2DiagEntry
            ACCESS  not-accessible
            STATUS  mandatory
            DESCRIPTION
                ""
            INDEX { gdsl2DiagSlotIndex ,
                    gdsl2DiagPortIndex }
            ::= { gdsl2DiagTable 1 }

        Gdsl2DiagEntry ::= SEQUENCE {
            gdsl2DiagSlotIndex          LSSlotID,
            gdsl2DiagPortIndex          G2PortID,
            gdsl2LocalGshdslLoopback    INTEGER,
            gdsl2RemoteGshdslLoopback   INTEGER,
            gdsl2RemoteDteLoopback      INTEGER,
            gdsl2BERTControl            INTEGER,
            gdsl2BERTReset              INTEGER,
            gdsl2BERTStatus             INTEGER,
            gdsl2BERTCounter            INTEGER,
            gdsl2BERTElapsed            INTEGER,
            gdsl2InbandLoopbackPeriod   INTEGER
        }

        gdsl2DiagSlotIndex  OBJECT-TYPE
            SYNTAX  LSSlotID
            ACCESS  read-only
            STATUS  mandatory
            DESCRIPTION
                "Gshdsl2 slot"
            ::= { gdsl2DiagEntry 1 }

        gdsl2DiagPortIndex  OBJECT-TYPE
            SYNTAX  G2PortID
            ACCESS  read-only
            STATUS  mandatory
            DESCRIPTION
                " Port 1/3."
            ::= { gdsl2DiagEntry 2 }

        gdsl2LocalGshdslLoopback  OBJECT-TYPE
            SYNTAX  INTEGER {
                    no-loopback(1),
                    gshdsl-to-line(2),
                    gshdsl-to-local(3)
                }
            ACCESS  read-write
            STATUS  mandatory
            DESCRIPTION
                "CSU Loopback Type"
            ::= { gdsl2DiagEntry 3 }

        gdsl2RemoteGshdslLoopback  OBJECT-TYPE
            SYNTAX  INTEGER {
                    slave-no-loopback(1),
                    slave-gshdsl-to-line(2),
                    slave-gshdsl-to-local(3),
                    slave-gshdsl-to-bridge(4),

                    slave-gshdsl-to-dte1(82),
                    slave-gshdsl-to-dte2(83),
                    slave-gshdsl-to-dte3(84)
                }
            ACCESS  read-write
            STATUS  mandatory
            DESCRIPTION
                "CSU Loopback Type"
            ::= { gdsl2DiagEntry 4 }

        gdsl2RemoteDteLoopback  OBJECT-TYPE
            SYNTAX  INTEGER {
                    slave-no-loopback(1),
                    slave-t1-to-line(2),
                    slave-t1-to-local(3),
                    slave-e1-to-line(4),
                    slave-e1-to-local(5),
                    slave-dte-to-line(6),
                    slave-dte-to-local(7),
                    slave-router-to-line(8)
                }
            ACCESS  read-write
            STATUS  mandatory
            DESCRIPTION
                "DTE/T1/E1 Loopback Type"
            ::= { gdsl2DiagEntry 5 }

        gdsl2BERTControl    OBJECT-TYPE
            SYNTAX  INTEGER {
                    bert-off(1),
--                      bert-2-15-1(2),
                    bert-on(3)
                }
            ACCESS  read-write
            STATUS  mandatory
            DESCRIPTION
                "Bert Control"
            ::= { gdsl2DiagEntry 6 }

        gdsl2BERTReset    OBJECT-TYPE
            SYNTAX  INTEGER {
                    bert-no-action(1),
                    bert-restart(2)
                }
            ACCESS  read-write
            STATUS  mandatory
            DESCRIPTION
                "Bert Restart"
            ::= { gdsl2DiagEntry 7 }

        gdsl2BERTStatus  OBJECT-TYPE
            SYNTAX  INTEGER {
                    bert-sync(1),
                    bert-unsync(2),
                    bert-not-active(3)
                }
            ACCESS  read-only
            STATUS  mandatory
            DESCRIPTION
                "BERT Status"
            ::= { gdsl2DiagEntry 8 }

        gdsl2BERTCounter  OBJECT-TYPE
            SYNTAX  INTEGER
            ACCESS  read-only
            STATUS  mandatory
            DESCRIPTION
                "BERT Counter"
            ::= { gdsl2DiagEntry 9 }

        gdsl2BERTElapsed  OBJECT-TYPE
            SYNTAX  INTEGER
            ACCESS  read-only
            STATUS  mandatory
            DESCRIPTION
                "BERT Elapsed Time"
            ::= { gdsl2DiagEntry 10 }

        gdsl2InbandLoopbackPeriod  OBJECT-TYPE
            SYNTAX  INTEGER
            ACCESS  read-write
            STATUS  mandatory
            DESCRIPTION
                "period(in seconds) of loopback"
            ::= { gdsl2DiagEntry 11 }


--
--  Alarm Queue Table
--

--         gdsl2AlmQueueTable  OBJECT-TYPE
--             SYNTAX  SEQUENCE OF Gdsl2AlmQueueEntry
--             ACCESS  not-accessible
--             STATUS  mandatory
--             DESCRIPTION
--                " Key: gdsl2AlmQueueUnitIndex "
--             ::= { gdsl2-card 9 }
--
--         gdsl2AlmQueueEntry  OBJECT-TYPE
--             SYNTAX  Gdsl2AlmQueueEntry
--             ACCESS  not-accessible
--             STATUS  mandatory
--             DESCRIPTION
--                " "
--             INDEX  { gdsl2Index,
--                      gdsl2PortIndex,
--                      gdsl2AlmQueueNumber }
--             ::= { gdsl2AlmQueueTable 1 }
--
--         Gdsl2AlmQueueEntry ::=
--             SEQUENCE {
--               gdsl2AlmQueueNumber
--                 INTEGER (1..40),
--               gdsl2AlmQueueString
--                 DisplayString (SIZE(0..80))
--             }
--
--         gdsl2AlmQueueNumber  OBJECT-TYPE
--             SYNTAX  INTEGER (1..40)
--             ACCESS  read-only
--             STATUS  mandatory
--             DESCRIPTION
--                "Select Latest Alarm Queue number (1-40)"
--             ::= { gdsl2AlmQueueEntry 2 }
--
--         gdsl2AlmQueueString  OBJECT-TYPE
--             SYNTAX  DisplayString (SIZE (0..80))
--             ACCESS  read-only
--             STATUS  mandatory
--             DESCRIPTION
--                "Alarm Queue String"
--             ::= { gdsl2AlmQueueEntry 3 }

--
--  Alarm Status Table
--

        gdsl2AlmStatusTable  OBJECT-TYPE
            SYNTAX  SEQUENCE OF Gdsl2AlmStatusEntry
            ACCESS  not-accessible
            STATUS  mandatory
            DESCRIPTION
                " Key: xdslAlmStatusUnitIndex "
            ::= { gdsl2-card 10 }

        gdsl2AlmStatusEntry  OBJECT-TYPE
            SYNTAX  Gdsl2AlmStatusEntry
            ACCESS  not-accessible
            STATUS  mandatory
            DESCRIPTION
                " "
            INDEX { gdsl2AlmSlotIndex ,
                    gdsl2AlmPortIndex ,
                    gdsl2AlmStatusNumber }
            ::= { gdsl2AlmStatusTable 1 }

        Gdsl2AlmStatusEntry ::= SEQUENCE {
            gdsl2AlmSlotIndex           LSSlotID,
            gdsl2AlmPortIndex           G2PortID,
            gdsl2AlmStatusNumber        INTEGER (1..40),
            gdsl2AlmStatusString        DisplayString,
            gdsl2AlmStatusThreshold     INTEGER,
            gdsl2AlmStatusState         INTEGER,
            gdsl2AlmStatusCount         INTEGER,
            gdsl2AlmStatusEnable        LsAlarmSeverity
        }

        gdsl2AlmSlotIndex  OBJECT-TYPE
            SYNTAX  LSSlotID
            ACCESS  read-only
            STATUS  mandatory
            DESCRIPTION
                "Gshdsl2 slot"
            ::= { gdsl2AlmStatusEntry 1 }

        gdsl2AlmPortIndex  OBJECT-TYPE
            SYNTAX  G2PortID
            ACCESS  read-only
            STATUS  mandatory
            DESCRIPTION
                " Port 1/3."
            ::= { gdsl2AlmStatusEntry 2 }

        gdsl2AlmStatusNumber  OBJECT-TYPE
            SYNTAX  INTEGER (1..40)
            ACCESS  read-only
            STATUS  mandatory
            DESCRIPTION
                " Alarm Status Index "
            ::= { gdsl2AlmStatusEntry 3 }

        gdsl2AlmStatusString  OBJECT-TYPE
            SYNTAX  DisplayString (SIZE (0..80))
            ACCESS  read-only
            STATUS  mandatory
            DESCRIPTION
                "Alarm Type String"
            ::= { gdsl2AlmStatusEntry 4 }

        gdsl2AlmStatusThreshold  OBJECT-TYPE
            SYNTAX  INTEGER
            ACCESS  read-write
            STATUS  mandatory
            DESCRIPTION
                " Alarm Threshold Value "
            ::= { gdsl2AlmStatusEntry 5 }

        gdsl2AlmStatusState  OBJECT-TYPE
            SYNTAX  INTEGER {
                    ok(1),
                    alarm(2),
                    disable(3),
                    none(4)
                }
            ACCESS  read-only
            STATUS  mandatory
            DESCRIPTION
                " Alarm Current State"
            ::= { gdsl2AlmStatusEntry 6 }

        gdsl2AlmStatusCount  OBJECT-TYPE
            SYNTAX  INTEGER
            ACCESS  read-only
            STATUS  mandatory
            DESCRIPTION
                " Alarm Count which happened "
            ::= { gdsl2AlmStatusEntry 7 }

        gdsl2AlmStatusEnable  OBJECT-TYPE
            SYNTAX  LsAlarmSeverity
            ACCESS  read-write
            STATUS  mandatory
            DESCRIPTION
                "Alarm is enabled or not"
            ::= { gdsl2AlmStatusEntry 8 }

--
--  Gdsl2 Status Config Table
--

        gdsl2StatusConfigTable  OBJECT-TYPE
            SYNTAX  SEQUENCE OF Gdsl2StatusConfigTableEntry
            ACCESS  not-accessible
            STATUS  mandatory
            DESCRIPTION
                " Gdsl Status Config Configuration "
            ::= { gdsl2-card 11 }

        gdsl2StatusConfigEntry  OBJECT-TYPE
            SYNTAX  Gdsl2StatusConfigTableEntry
            ACCESS  not-accessible
            STATUS  mandatory
            DESCRIPTION
                " "
            INDEX { gdsl2SCSlotIndex ,
                    gdsl2SCPortIndex }
            ::= { gdsl2StatusConfigTable 1 }

        Gdsl2StatusConfigTableEntry ::= SEQUENCE {
            gdsl2SCSlotIndex            LSSlotID,
            gdsl2SCPortIndex            G2PortID,
            gdsl2DS1SYNC                INTEGER,
            gdsl2DS1TxAIS               INTEGER,
            gdsl2DS1TxRAI               INTEGER,
            gdsl2DS1RxAIS               INTEGER,
            gdsl2DS1RxRAI               INTEGER,
            gdsl2DS1LOS                 INTEGER,
            gdsl2DS1LOF                 INTEGER,
            gdsl2dteDSR                 INTEGER,
            gdsl2dteCTS                 INTEGER,
            gdsl2dteDCD                 INTEGER,
            gdsl2dteDTR                 INTEGER,
            gdsl2dteRTS                 INTEGER,
            gdsl2PortCAS                INTEGER,
            gdsl2LAN1Status             INTEGER,
            gdsl2WAN1Status             INTEGER

    }

        gdsl2SCSlotIndex  OBJECT-TYPE
            SYNTAX  LSSlotID
            ACCESS  read-only
            STATUS  mandatory
            DESCRIPTION
                "Gshdsl2 slot"
            ::= { gdsl2StatusConfigEntry 1 }

        gdsl2SCPortIndex  OBJECT-TYPE
            SYNTAX  G2PortID
            ACCESS  read-only
            STATUS  mandatory
            DESCRIPTION
                " Port 1/3."
            ::= { gdsl2StatusConfigEntry 2 }

        gdsl2DS1SYNC  OBJECT-TYPE
            SYNTAX  INTEGER {
                    yes(1),
                    no(2),
                    xx(3)
                }
            ACCESS  read-only
            STATUS  mandatory
            DESCRIPTION
                " Gshdsl DS1 line status."
            ::= { gdsl2StatusConfigEntry 3 }

        gdsl2DS1TxAIS  OBJECT-TYPE
            SYNTAX  INTEGER {
                    yes(1),
                    no(2),
                    xx(3)
                }
            ACCESS  read-only
            STATUS  mandatory
            DESCRIPTION
                "Gshdsl DS1 line Tx Alarm Indication Signal."
            ::= { gdsl2StatusConfigEntry 4 }

        gdsl2DS1TxRAI  OBJECT-TYPE
            SYNTAX  INTEGER {
                    yes(1),
                    no(2),
                    xx(3)
                }
            ACCESS  read-only
            STATUS  mandatory
            DESCRIPTION
                " Gshdsl DS1 line Tx Remote Alarm Indication."
            ::= { gdsl2StatusConfigEntry 5 }

        gdsl2DS1RxAIS  OBJECT-TYPE
            SYNTAX  INTEGER {
                    yes(1),
                    no(2),
                    xx(3)
                }
            ACCESS  read-only
            STATUS  mandatory
            DESCRIPTION
                " Gshdsl DS1 line Rx Alarm Indication Signal."
            ::= { gdsl2StatusConfigEntry 6 }

        gdsl2DS1RxRAI  OBJECT-TYPE
            SYNTAX  INTEGER {
                    yes(1),
                    no(2),
                    xx(3)
                }
            ACCESS  read-only
            STATUS  mandatory
            DESCRIPTION
                " Gshdsl DS1 line Rx Remote Alarm Indication."
            ::= { gdsl2StatusConfigEntry 7 }

        gdsl2DS1LOS  OBJECT-TYPE
            SYNTAX  INTEGER {
                    yes(1),
                    no(2),
                    xx(3)
                }
            ACCESS  read-only
            STATUS  mandatory
            DESCRIPTION
                " Gshdsl DS1 line LOS Status."
            ::= { gdsl2StatusConfigEntry 8 }

        gdsl2DS1LOF  OBJECT-TYPE
            SYNTAX  INTEGER {
                    yes(1),
                    no(2),
                    xx(3)
                }
            ACCESS  read-only
            STATUS  mandatory
            DESCRIPTION
                " Gshdsl DS1 line LOF Status."
            ::= { gdsl2StatusConfigEntry 9 }

        gdsl2dteDSR  OBJECT-TYPE
            SYNTAX  INTEGER {
                    yes(1),
                    no(2),
                    xx(3)
                }
            ACCESS  read-only
            STATUS  mandatory
            DESCRIPTION
                " Gshdsl dte line DSR Status."
            ::= { gdsl2StatusConfigEntry 10 }

        gdsl2dteCTS  OBJECT-TYPE
            SYNTAX  INTEGER {
                    yes(1),
                    no(2),
                    xx(3)
                }
            ACCESS  read-only
            STATUS  mandatory
            DESCRIPTION
                " Gshdsl dte line CTS Status."
            ::= { gdsl2StatusConfigEntry 11 }

        gdsl2dteDCD  OBJECT-TYPE
            SYNTAX  INTEGER {
                    yes(1),
                    no(2),
                    xx(3)
                }
            ACCESS  read-only
            STATUS  mandatory
            DESCRIPTION
                " Gshdsl dte line DCD Status."
            ::= { gdsl2StatusConfigEntry 12 }

        gdsl2dteDTR  OBJECT-TYPE
            SYNTAX  INTEGER {
                    yes(1),
                    no(2),
                    xx(3)
                }
            ACCESS  read-only
            STATUS  mandatory
            DESCRIPTION
                " Gshdsl dte line DTR Status."
            ::= { gdsl2StatusConfigEntry 13 }

        gdsl2dteRTS  OBJECT-TYPE
            SYNTAX  INTEGER {
                    yes(1),
                    no(2),
                    xx(3)
                }
            ACCESS  read-only
            STATUS  mandatory
            DESCRIPTION
                " Gshdsl dte line RTS Status."
            ::= { gdsl2StatusConfigEntry 14 }

        gdsl2PortCAS  OBJECT-TYPE
            SYNTAX  INTEGER {
                    loss(1),
                    sync(2),
                    disable(3)
                }
            ACCESS  read-only
            STATUS  mandatory
            DESCRIPTION
                " Gshdsl CAS Status."
            ::= { gdsl2StatusConfigEntry 15 }

        gdsl2LAN1Status  OBJECT-TYPE
            SYNTAX  INTEGER {
                    down(1),
                    up(2),
                    na(3)
                }
            ACCESS  read-only
            STATUS  mandatory
            DESCRIPTION
                " LAN1 Status."
            ::= { gdsl2StatusConfigEntry 16 }

        gdsl2WAN1Status  OBJECT-TYPE
            SYNTAX  INTEGER {
                    down(1),
                    up(2),
                    na(3)
                }
            ACCESS  read-only
            STATUS  mandatory
            DESCRIPTION
                " WAN1 Status."
            ::= { gdsl2StatusConfigEntry 17 }

--
--  GDSL2 Info Table
--

        gdsl2InfoTable  OBJECT-TYPE
            SYNTAX  SEQUENCE OF Gdsl2InfoEntry
            ACCESS  not-accessible
            STATUS  mandatory
            DESCRIPTION
                " Key: gdsl2InfoUnitIndex "
            ::= { gdsl2-card 12 }

        gdsl2InfoEntry  OBJECT-TYPE
            SYNTAX  Gdsl2InfoEntry
            ACCESS  not-accessible
            STATUS  mandatory
            DESCRIPTION
                " "
            INDEX { gdsl2InfoSlotIndex ,
                    gdsl2InfoPortIndex ,
                    gdsl2LoopNum }
            ::= { gdsl2InfoTable 1  }

        Gdsl2InfoEntry ::= SEQUENCE {
            gdsl2InfoSlotIndex          LSSlotID,
            gdsl2InfoPortIndex          G2PortID,
            gdsl2LoopNum                INTEGER,
            gdsl2MasterNoiseMarginString    DisplayString (SIZE(0..80)),
            gdsl2MasterMaxNMRString         DisplayString (SIZE(0..80)),
            gdsl2MasterMinNMRString         DisplayString (SIZE(0..80)),
            gdsl2SlaveNoiseMarginString     DisplayString (SIZE(0..80)),
            gdsl2SlaveMaxNMRString          DisplayString (SIZE(0..80)),
            gdsl2SlaveMinNMRString          DisplayString (SIZE(0..80))
        }

        gdsl2InfoSlotIndex  OBJECT-TYPE
            SYNTAX  LSSlotID
            ACCESS  read-only
            STATUS  mandatory
            DESCRIPTION
                "Gshdsl2 slot"
            ::= { gdsl2InfoEntry 1 }

        gdsl2InfoPortIndex  OBJECT-TYPE
            SYNTAX  G2PortID
            ACCESS  read-only
            STATUS  mandatory
            DESCRIPTION
                " Port 1/3."
            ::= { gdsl2InfoEntry 2 }

        gdsl2LoopNum  OBJECT-TYPE
            SYNTAX  INTEGER {
                    loop-1(1),
                    loop-2(2)
                }
            ACCESS  read-only
            STATUS  mandatory
            DESCRIPTION
                "Loop-1 or Loop-2"
            ::= { gdsl2InfoEntry 3 }

        gdsl2MasterNoiseMarginString  OBJECT-TYPE
            SYNTAX  DisplayString (SIZE (0..80))
            ACCESS  read-only
            STATUS  mandatory
            DESCRIPTION
                "Noise Margin String"
            ::= { gdsl2InfoEntry 4 }

        gdsl2MasterMaxNMRString  OBJECT-TYPE
            SYNTAX  DisplayString (SIZE (0..80))
            ACCESS  read-only
            STATUS  mandatory
            DESCRIPTION
                "Max Noise Margin String"
            ::= { gdsl2InfoEntry 5 }

        gdsl2MasterMinNMRString  OBJECT-TYPE
            SYNTAX  DisplayString (SIZE (0..80))
            ACCESS  read-only
            STATUS  mandatory
            DESCRIPTION
                "Min Margin String"
            ::= { gdsl2InfoEntry 6 }

        gdsl2SlaveNoiseMarginString  OBJECT-TYPE
            SYNTAX  DisplayString (SIZE (0..80))
            ACCESS  read-only
            STATUS  mandatory
            DESCRIPTION
                "Noise Margin String"
            ::= { gdsl2InfoEntry 7 }

        gdsl2SlaveMaxNMRString  OBJECT-TYPE
            SYNTAX  DisplayString (SIZE (0..80))
            ACCESS  read-only
            STATUS  mandatory
            DESCRIPTION
                "Max Noise Margin String"
            ::= { gdsl2InfoEntry 8 }

        gdsl2SlaveMinNMRString  OBJECT-TYPE
            SYNTAX  DisplayString (SIZE (0..80))
            ACCESS  read-only
            STATUS  mandatory
            DESCRIPTION
                "Min Margin String"
            ::= { gdsl2InfoEntry 9 }

--
--  Command Control Table
--

        gdsl2CommandControlTable  OBJECT-TYPE
            SYNTAX  SEQUENCE OF Gdsl2CommandControlEntry
            ACCESS  not-accessible
            STATUS  mandatory
            DESCRIPTION
                "The command control table."
            ::= { gdsl2-card 13 }

        gdsl2CommandControlEntry  OBJECT-TYPE
            SYNTAX  Gdsl2CommandControlEntry
            ACCESS  not-accessible
            STATUS  mandatory
            DESCRIPTION
                "An entry in the command control table."
            INDEX { gdsl2CCSlotIndex ,
                    gdsl2CCPortIndex }
            ::= { gdsl2CommandControlTable 1 }

        Gdsl2CommandControlEntry ::= SEQUENCE {
            gdsl2CCSlotIndex            LSSlotID,
            gdsl2CCPortIndex            G2PortID,
            gdsl2ClearPerformance       INTEGER,
--               gdsl2ClearAlarmHistory
--                 INTEGER,
            gdsl2UnitReset              INTEGER,
            gdsl2UnitLoadDefault        INTEGER,
            gdsl2FarEndReset            INTEGER
        }

        gdsl2CCSlotIndex  OBJECT-TYPE
            SYNTAX  LSSlotID
            ACCESS  read-only
            STATUS  mandatory
            DESCRIPTION
                "Gshdsl2 slot"
            ::= { gdsl2CommandControlEntry 1 }

        gdsl2CCPortIndex  OBJECT-TYPE
            SYNTAX  G2PortID
            ACCESS  read-only
            STATUS  mandatory
            DESCRIPTION
                " Port 1/3."
            ::= { gdsl2CommandControlEntry 2 }

        gdsl2ClearPerformance    OBJECT-TYPE
            SYNTAX  INTEGER {
                    clear(1)
                }
            ACCESS  read-write
            STATUS  mandatory
            DESCRIPTION
                "Command: Clear User Performance"
            ::= { gdsl2CommandControlEntry 4 }

--         gdsl2ClearAlarmHistory    OBJECT-TYPE
--             SYNTAX  INTEGER {
--                         clear(1)
--                     }
--             ACCESS  read-write
--             STATUS  mandatory
--             DESCRIPTION
--                "Command: Clear Alarm History"
--             ::= { gdsl2CommandControlEntry 5 }

        gdsl2UnitReset    OBJECT-TYPE
            SYNTAX  INTEGER {
                    reset(1)
                }
            ACCESS  read-write
            STATUS  mandatory
            DESCRIPTION
                "Command: Reset G.SHDSL-2"
            ::= { gdsl2CommandControlEntry 6 }

        gdsl2UnitLoadDefault    OBJECT-TYPE
            SYNTAX  INTEGER {
                    load-default(1)
                }
            ACCESS  read-write
            STATUS  mandatory
            DESCRIPTION
                "Command: Load Default G.SHDSL-2"
            ::= { gdsl2CommandControlEntry 7 }

        gdsl2FarEndReset    OBJECT-TYPE
            SYNTAX  INTEGER {
                    reset(1)
                }
            ACCESS  read-write
            STATUS  mandatory
            DESCRIPTION
                "Command: Reset Far End System"
            ::= { gdsl2CommandControlEntry 8 }

--
--  SYSTEM Information Table
--

        gdsl2SystemInfoTable  OBJECT-TYPE
            SYNTAX  SEQUENCE OF Gdsl2SystemInformationEntry
            ACCESS  not-accessible
            STATUS  mandatory
            DESCRIPTION
                "The system information table."
            ::= { gdsl2-card 14 }

        gdsl2SystemInformationEntry  OBJECT-TYPE
            SYNTAX  Gdsl2SystemInformationEntry
            ACCESS  not-accessible
            STATUS  mandatory
            DESCRIPTION
                "An entry in the system information table."
            INDEX { gdsl2SISlotIndex }
            ::= { gdsl2SystemInfoTable 1 }

        Gdsl2SystemInformationEntry ::= SEQUENCE {
            gdsl2SISlotIndex            LSSlotID,
            gdsl2SoftwareVersion        DisplayString,
            gdsl2HardwareVersion        DisplayString
        }

        gdsl2SISlotIndex  OBJECT-TYPE
            SYNTAX  LSSlotID
            ACCESS  read-only
            STATUS  mandatory
            DESCRIPTION
                "Gshdsl2 slot"
            ::= { gdsl2SystemInformationEntry 1 }

        gdsl2SoftwareVersion  OBJECT-TYPE
            SYNTAX  DisplayString (SIZE (0..255) )
            ACCESS  read-only
            STATUS  mandatory
            DESCRIPTION
                " G.SHDSL-2 Software Version"
            ::= { gdsl2SystemInformationEntry 2 }

        gdsl2HardwareVersion  OBJECT-TYPE
            SYNTAX  DisplayString (SIZE (0..255) )
            ACCESS  read-only
            STATUS  mandatory
            DESCRIPTION
                " G.SHDSL-2 Hardware Version"
            ::= { gdsl2SystemInformationEntry 3 }


--
--  G.SHDSL-2 Customer Information Table
--

        gdsl2CustomerInfoTable  OBJECT-TYPE
            SYNTAX  SEQUENCE OF Gdsl2CustomerInfoEntry
            ACCESS  not-accessible
            STATUS  mandatory
            DESCRIPTION
                "The Customer Information table."
            ::= { gdsl2-card 99 }

        gdsl2CustomerInfoEntry  OBJECT-TYPE
            SYNTAX  Gdsl2CustomerInfoEntry
            ACCESS  not-accessible
            STATUS  mandatory
            DESCRIPTION
                "An entry in the Customer Information table."
            INDEX { gdsl2CISlotIndex , gdsl2CIPortIndex }
            ::= { gdsl2CustomerInfoTable 1 }

        Gdsl2CustomerInfoEntry ::= SEQUENCE {
            gdsl2CISlotIndex            LSSlotID,
            gdsl2CIPortIndex            G2PortID,
            gdsl2CICustomerInfo         DisplayString (SIZE(0..64))
        }

        gdsl2CISlotIndex    OBJECT-TYPE
            SYNTAX  LSSlotID
            ACCESS  read-only
            STATUS  mandatory
            DESCRIPTION
                "LS slot index"
            ::= { gdsl2CustomerInfoEntry 1 }

        gdsl2CIPortIndex    OBJECT-TYPE
            SYNTAX  G2PortID
            ACCESS  read-only
            STATUS  mandatory
            DESCRIPTION
                " Port 1/3."
            ::= { gdsl2CustomerInfoEntry 2 }

        gdsl2CICustomerInfo  OBJECT-TYPE
            SYNTAX  DisplayString (SIZE (0..64) )
            ACCESS  read-write
            STATUS  mandatory
            DESCRIPTION
                "Customer information"
            ::= { gdsl2CustomerInfoEntry 3 }


--
--  Daughter Card Information Table
--

        gdsl2DCardInfoTable  OBJECT-TYPE
            SYNTAX  SEQUENCE OF Gdsl2DCardInfoEntry
            ACCESS  not-accessible
            STATUS  mandatory
            DESCRIPTION
                "The Daughter Card Information table."
            ::= { gdsl2-card 15 }

        gdsl2DCardInfoEntry  OBJECT-TYPE
            SYNTAX  Gdsl2DCardInfoEntry
            ACCESS  not-accessible
            STATUS  mandatory
            DESCRIPTION
                "An entry in the daughter card information table."
            INDEX { gdsl2DCISlotIndex ,
                    gdsl2DCIPortIndex }
            ::= { gdsl2DCardInfoTable 1 }

        Gdsl2DCardInfoEntry ::= SEQUENCE {
            gdsl2DCISlotIndex           LSSlotID,
            gdsl2DCIPortIndex           G2PortID,
            gdsl2DaughterCard           INTEGER
        }

        gdsl2DCISlotIndex  OBJECT-TYPE
            SYNTAX  LSSlotID
            ACCESS  read-only
            STATUS  mandatory
            DESCRIPTION
                "Gshdsl2 slot"
            ::= { gdsl2DCardInfoEntry 1 }

        gdsl2DCIPortIndex  OBJECT-TYPE
            SYNTAX  G2PortID
            ACCESS  read-only
            STATUS  mandatory
            DESCRIPTION
                " Port 1/3."
            ::= { gdsl2DCardInfoEntry 2 }

        gdsl2DaughterCard  OBJECT-TYPE
            SYNTAX  INTEGER {
                    no-daughter-card(1),
                    sealing-current-single(2),
                    sealing-current-daul(3),
                    line-power-single(4),
                    line-power-daul(5)
                }
            ACCESS  read-only
            STATUS  mandatory
            DESCRIPTION
                " G.SHDSL-2 Daughter Card "
            ::= { gdsl2DCardInfoEntry 3 }

--
--  GDSL2 ADVANCE SYSTEM Table
--

        gdsl2AdvanceSystemTable  OBJECT-TYPE
            SYNTAX  SEQUENCE OF Gdsl2AdvanceSystemEntry
            ACCESS  not-accessible
            STATUS  mandatory
            DESCRIPTION
                "The system control table."
            ::= { gdsl2-card 16 }

        gdsl2AdvanceSystemEntry  OBJECT-TYPE
            SYNTAX  Gdsl2AdvanceSystemEntry
            ACCESS  not-accessible
            STATUS  mandatory
            DESCRIPTION
                "An entry in the Advance system table."
            INDEX { gdsl2AdvSlotIndex ,
                    gdsl2AdvPortIndex ,
                    gdsl2AdvHTUIndex }
            ::= { gdsl2AdvanceSystemTable 1 }

        Gdsl2AdvanceSystemEntry ::= SEQUENCE {
            gdsl2AdvSlotIndex           LSSlotID,
            gdsl2AdvPortIndex           G2PortID,
            gdsl2AdvHTUIndex            INTEGER,
            gdsl2AnnexType              INTEGER,
            gdsl2ClockMode              INTEGER,
            gdsl2PSDMask                INTEGER,
            gdsl2PBOMode                INTEGER
        }

        gdsl2AdvSlotIndex  OBJECT-TYPE
            SYNTAX  LSSlotID
            ACCESS  read-only
            STATUS  mandatory
            DESCRIPTION
                "Gshdsl2 slot"
            ::= { gdsl2AdvanceSystemEntry 1 }

        gdsl2AdvPortIndex  OBJECT-TYPE
            SYNTAX  G2PortID
            ACCESS  read-only
            STATUS  mandatory
            DESCRIPTION
                " Port 1/3."
            ::= { gdsl2AdvanceSystemEntry 2 }

        gdsl2AdvHTUIndex  OBJECT-TYPE
            SYNTAX  INTEGER {
                    local(1),
                    remote(2)
                }
            ACCESS  read-only
            STATUS  mandatory
            DESCRIPTION
                "Local or Remote"
            ::= { gdsl2AdvanceSystemEntry 3 }

        gdsl2AnnexType  OBJECT-TYPE
            SYNTAX  INTEGER {
                    type-A(1),
                    type-B(2),
                    not-support(3)
                }
            ACCESS  read-write
            STATUS  mandatory
            DESCRIPTION
                "G.SHDSL Annex Type"
            ::= { gdsl2AdvanceSystemEntry 4 }

        gdsl2ClockMode  OBJECT-TYPE
            SYNTAX  INTEGER {
                    plesiosynchronous(1),
                    synchronous(2),
                    hybrid(3),
                    not-support(4)
                }
            ACCESS  read-write
            STATUS  mandatory
            DESCRIPTION
                " G.SHDSL Clock Mode"
            ::= { gdsl2AdvanceSystemEntry 5 }

        gdsl2PSDMask  OBJECT-TYPE
            SYNTAX  INTEGER {
                    symmetric(1),
                    asymmetric(2),
                    not-support(3)
                }
            ACCESS  read-write
            STATUS  mandatory
            DESCRIPTION
                " G.SHDSL PSD Mask"
            ::= { gdsl2AdvanceSystemEntry 6 }

        gdsl2PBOMode  OBJECT-TYPE
            SYNTAX  INTEGER {
                    automatic(1),
                    pbo-0-db(2),
                    pbo-1-db(3),
                    pbo-2-db(4),
                    pbo-3-db(5),
                    pbo-4-db(6),
                    pbo-5-db(7),
                    pbo-6-db(8),
                    pbo-7-db(9),
                    pbo-8-db(10),
                    pbo-9-db(11),
                    pbo-10-db(12),
                    pbo-11-db(13),
                    pbo-12-db(14),
                    pbo-13-db(15),
                    pbo-14-db(16),
                    pbo-15-db(17),
                    pbo-16-db(18),
                    pbo-17-db(19),
                    pbo-18-db(20),
                    pbo-19-db(21),
                    pbo-20-db(22),
                    pbo-21-db(23),
                    pbo-22-db(24),
                    pbo-23-db(25),
                    pbo-24-db(26),
                    pbo-25-db(27),
                    pbo-26-db(28),
                    pbo-27-db(29),
                    pbo-28-db(30),
                    pbo-29-db(31),
                    pbo-30-db(32),
                    pbo-31-db(33),
                    not-support(34)
                }
            ACCESS  read-write
            STATUS  mandatory
            DESCRIPTION
                " G.SHDSL PBO Mode"
            ::= { gdsl2AdvanceSystemEntry 7 }

--
--  GDSL2 Remote Link Identification Table
--

        gdsl2RemoteLinkIDTable  OBJECT-TYPE
            SYNTAX  SEQUENCE OF Gdsl2RemoteLinkIDEntry
            ACCESS  not-accessible
            STATUS  mandatory
            DESCRIPTION
                "The G.SHDSL Remote Link Identification Table."
            ::= { gdsl2-card 17 }

        gdsl2RemoteLinkIDEntry  OBJECT-TYPE
            SYNTAX  Gdsl2RemoteLinkIDEntry
            ACCESS  not-accessible
            STATUS  mandatory
            DESCRIPTION
                "An entry in the G.SHDSL Remote Link Identification table."
            INDEX { gdsl2RLSlotIndex ,
                    gdsl2RLPortIndex }
            ::= { gdsl2RemoteLinkIDTable 1 }

        Gdsl2RemoteLinkIDEntry ::= SEQUENCE {
            gdsl2RLSlotIndex            LSSlotID,
            gdsl2RLPortIndex            G2PortID,
            gdsl2RemoteLinkIDType       INTEGER,
            gdsl2RemoteLinkIDRack       INTEGER,
            gdsl2RemoteLinkIDSlotNumber INTEGER,
            gdsl2RemoteLinkIDPort       INTEGER,
            gdsl2RemoteLinkIDSerialNumber   INTEGER
        }

        gdsl2RLSlotIndex  OBJECT-TYPE
            SYNTAX  LSSlotID
            ACCESS  read-only
            STATUS  mandatory
            DESCRIPTION
                "Gshdsl2 slot"
            ::= { gdsl2RemoteLinkIDEntry 1 }

        gdsl2RLPortIndex  OBJECT-TYPE
            SYNTAX  G2PortID
            ACCESS  read-only
            STATUS  mandatory
            DESCRIPTION
                " Port 1/3."
            ::= { gdsl2RemoteLinkIDEntry 2 }

        gdsl2RemoteLinkIDType  OBJECT-TYPE
            SYNTAX  INTEGER {
                    notAvailable(0),
                    cpe(1),
                    an(2)
                }
            ACCESS  read-only
            STATUS  mandatory
            DESCRIPTION
                "Type of remote site."
            ::= { gdsl2RemoteLinkIDEntry 3 }

        gdsl2RemoteLinkIDRack  OBJECT-TYPE
            SYNTAX  INTEGER {
                    notAvailable(0)
                }
            ACCESS  read-only
            STATUS  mandatory
            DESCRIPTION
                "Remote Link Identification Rack"
            ::= { gdsl2RemoteLinkIDEntry 4 }

        gdsl2RemoteLinkIDSlotNumber  OBJECT-TYPE
            SYNTAX  INTEGER {
                    notAvailable(0)
                }
            ACCESS  read-only
            STATUS  mandatory
            DESCRIPTION
                "Remote Link Identification SlotNumber"
            ::= { gdsl2RemoteLinkIDEntry 5 }

        gdsl2RemoteLinkIDPort  OBJECT-TYPE
            SYNTAX  INTEGER {
                    notAvailable(0)
                }
            ACCESS  read-only
            STATUS  mandatory
            DESCRIPTION
                "Remote Link Identification Port"
            ::= { gdsl2RemoteLinkIDEntry 6 }

        gdsl2RemoteLinkIDSerialNumber  OBJECT-TYPE
            SYNTAX  INTEGER {
                    notAvailable(0)
                }
            ACCESS  read-only
            STATUS  mandatory
            DESCRIPTION
                "Remote Link Identification Serial Number"
            ::= { gdsl2RemoteLinkIDEntry 7 }

--
--  Seven Days Performance Table
--
        gdsl2SevenDaysPerfTable  OBJECT-TYPE
            SYNTAX  SEQUENCE OF Gdsl2SevenDaysPerfEntry
            ACCESS  not-accessible
            STATUS  mandatory
            DESCRIPTION
                "7 Days Performance Table"
            ::= { gdsl2-card 18 }

        gdsl2SevenDaysPerfEntry  OBJECT-TYPE
            SYNTAX  Gdsl2SevenDaysPerfEntry
            ACCESS  not-accessible
            STATUS  mandatory
            DESCRIPTION
                "7 days performance entry"
            INDEX { gdsl2DPSlotIndex ,
                    gdsl2DPPortIndex ,
                    gdsl2DaysPerfTypeIndex ,
                    gdsl2DaysIndex }
            ::= { gdsl2SevenDaysPerfTable 1 }

        Gdsl2SevenDaysPerfEntry ::= SEQUENCE  {
            gdsl2DPSlotIndex            LSSlotID,
            gdsl2DPPortIndex            G2PortID,
            gdsl2DaysPerfTypeIndex      INTEGER,
            gdsl2DaysIndex              INTEGER (1..7),
            gdsl2DateStrIndex           DisplayString (SIZE (0..255) ),
            gdsl2SevenDaysPerfES        INTEGER,
            gdsl2SevenDaysPerfSES       INTEGER,
            gdsl2SevenDaysPerfUAS       INTEGER
        }

        gdsl2DPSlotIndex  OBJECT-TYPE
            SYNTAX  LSSlotID
            ACCESS  read-only
            STATUS  mandatory
            DESCRIPTION
                "Gshdsl2 slot"
            ::= { gdsl2SevenDaysPerfEntry 1 }

        gdsl2DPPortIndex  OBJECT-TYPE
            SYNTAX  G2PortID
            ACCESS  read-only
            STATUS  mandatory
            DESCRIPTION
                " Port 1/3."
            ::= { gdsl2SevenDaysPerfEntry 2 }

        gdsl2DaysPerfTypeIndex  OBJECT-TYPE
            SYNTAX  INTEGER {
                    master-loop-1(1),
                    master-loop-2(2),
                    master-ds1(3),
                    slave-loop-1(4),
                    slave-loop-2(5),
                    slave-ds1(6)
                }
            ACCESS  read-only
            STATUS  mandatory
            DESCRIPTION
                "Performance Type"
            ::= { gdsl2SevenDaysPerfEntry 3 }

        gdsl2DaysIndex  OBJECT-TYPE
            SYNTAX  INTEGER (1..7)
            ACCESS  read-only
            STATUS  mandatory
            DESCRIPTION
                "Seven Days index "
            ::= { gdsl2SevenDaysPerfEntry 4 }

        gdsl2DateStrIndex  OBJECT-TYPE
            SYNTAX  DisplayString (SIZE (0..255) )
            ACCESS  read-only
            STATUS  mandatory
            DESCRIPTION
                "Seven Days String "
            ::= { gdsl2SevenDaysPerfEntry 5 }

        gdsl2SevenDaysPerfES  OBJECT-TYPE
            SYNTAX  INTEGER
            ACCESS  read-only
            STATUS  mandatory
            DESCRIPTION
                " ES Error Counter "
            ::= { gdsl2SevenDaysPerfEntry 6 }

        gdsl2SevenDaysPerfSES  OBJECT-TYPE
            SYNTAX  INTEGER
            ACCESS  read-only
            STATUS  mandatory
            DESCRIPTION
                " SES Error Counter "
            ::= { gdsl2SevenDaysPerfEntry 7 }

        gdsl2SevenDaysPerfUAS  OBJECT-TYPE
            SYNTAX  INTEGER
            ACCESS  read-only
            STATUS  mandatory
            DESCRIPTION
                " UAS Error Counter "
            ::= { gdsl2SevenDaysPerfEntry 8 }

--
-- GDSL2 Remote Fractional TABLE
--

    gdsl2RemoteFracTable                OBJECT IDENTIFIER ::= { gdsl2-card 19 }

--
-- GDSL2 Remote Fractional Config TABLE
--

        gdsl2RemFracConfigTable   OBJECT-TYPE
            SYNTAX  SEQUENCE OF Gdsl2RemFracConfigEntry
            ACCESS  not-accessible
            STATUS  mandatory
            DESCRIPTION
                "Remote Fractional Config Table"
            ::= { gdsl2RemoteFracTable 1 }

        gdsl2RemFracConfigEntry   OBJECT-TYPE
            SYNTAX  Gdsl2RemFracConfigEntry
            ACCESS  not-accessible
            STATUS  mandatory
            DESCRIPTION
                "Remote Fractional Config Entry "
            INDEX { gdsl2RFCSlotIndex ,
                    gdsl2RFCPortIndex ,
                    gdsl2RemoteFracNumber }
            ::= { gdsl2RemFracConfigTable 1 }

        Gdsl2RemFracConfigEntry ::= SEQUENCE {
            gdsl2RFCSlotIndex           LSSlotID,
            gdsl2RFCPortIndex           G2PortID,
            gdsl2RemoteFracNumber       INTEGER,
            gdsl2RemoteFracIfIndex      INTEGER
        }

        gdsl2RFCSlotIndex  OBJECT-TYPE
            SYNTAX  LSSlotID
            ACCESS  read-only
            STATUS  mandatory
            DESCRIPTION
                "Gshdsl2 slot"
            ::= { gdsl2RemFracConfigEntry 1 }

        gdsl2RFCPortIndex  OBJECT-TYPE
            SYNTAX  G2PortID
            ACCESS  read-only
            STATUS  mandatory
            DESCRIPTION
                " Port 1/3."
            ::= { gdsl2RemFracConfigEntry 2 }

        gdsl2RemoteFracNumber   OBJECT-TYPE
            SYNTAX  INTEGER (1..32)
            ACCESS  read-only
            STATUS  mandatory
            DESCRIPTION
                "Remote Fractional Number "
            ::= { gdsl2RemFracConfigEntry 3 }

        gdsl2RemoteFracIfIndex  OBJECT-TYPE
            SYNTAX  INTEGER {
                    chan-idle(1),
                    chan-ds1(2),
                    chan-x(3),
                    chan-dte(4),
                    chan-ethernet(5)
                }
            ACCESS  read-only
            STATUS  mandatory
            DESCRIPTION
                "Remote Fractional IfIndex"
            ::= { gdsl2RemFracConfigEntry 4 }

--
-- GDSL2 Set Remote Fractional TABLE
--

        gdsl2SetRemoteFracTable   OBJECT-TYPE
            SYNTAX  SEQUENCE OF Gdsl2SetRemoteFracEntry
            ACCESS  not-accessible
            STATUS  mandatory
            DESCRIPTION
                "Set Remote Fractional Table"
            ::= { gdsl2RemoteFracTable 2 }

        gdsl2SetRemoteFracEntry   OBJECT-TYPE
            SYNTAX  Gdsl2SetRemoteFracEntry
            ACCESS  not-accessible
            STATUS  mandatory
            DESCRIPTION
                "Set Remote Fractional Entry "
            INDEX { gdsl2SRFSlotIndex ,
                    gdsl2SRFPortIndex }
            ::= { gdsl2SetRemoteFracTable 1 }

        Gdsl2SetRemoteFracEntry ::= SEQUENCE {
            gdsl2SRFSlotIndex           LSSlotID,
            gdsl2SRFPortIndex           G2PortID,
            gdsl2StartFracNumber        INTEGER,
            gdsl2FracNumbers            INTEGER,
            gdsl2E1T1ClearStartFracNumber   INTEGER,
            gdsl2SetFracIfIndex             INTEGER
        }

        gdsl2SRFSlotIndex  OBJECT-TYPE
            SYNTAX  LSSlotID
            ACCESS  read-only
            STATUS  mandatory
            DESCRIPTION
                "Gshdsl2 slot"
            ::= { gdsl2SetRemoteFracEntry 1 }

        gdsl2SRFPortIndex  OBJECT-TYPE
            SYNTAX  G2PortID
            ACCESS  read-only
            STATUS  mandatory
            DESCRIPTION
                " Port 1/3."
            ::= { gdsl2SetRemoteFracEntry 2 }

        gdsl2StartFracNumber   OBJECT-TYPE
            SYNTAX  INTEGER (1..32)
            ACCESS  read-write
            STATUS  mandatory
            DESCRIPTION
                "Start Fractional Number "
            ::= { gdsl2SetRemoteFracEntry 3 }

        gdsl2FracNumbers   OBJECT-TYPE
            SYNTAX  INTEGER (1..32)
            ACCESS  read-write
            STATUS  mandatory
            DESCRIPTION
                "Number of Fractional"
            ::= { gdsl2SetRemoteFracEntry 4 }

        gdsl2E1T1ClearStartFracNumber   OBJECT-TYPE
            SYNTAX  INTEGER (1..32)
            ACCESS  read-write
            STATUS  mandatory
            DESCRIPTION
                "Remote E1/T1 Clear Start Fractional Number"
            ::= { gdsl2SetRemoteFracEntry 5 }

        gdsl2SetFracIfIndex  OBJECT-TYPE
            SYNTAX  INTEGER {
                    chan-idle(1),
                    chan-ds1(2),
                    chan-x(3),
                    chan-dte(4),
                    chan-ethernet(5)
                }
            ACCESS  read-write
            STATUS  mandatory
            DESCRIPTION
                "Set Fractional IfIndex"
            ::= { gdsl2SetRemoteFracEntry 6 }

--
-- Remote Bert Control Table
--

        gdsl2RemoteBertTable  OBJECT-TYPE
            SYNTAX  SEQUENCE OF Gdsl2RemoteBertEntry
            ACCESS  not-accessible
            STATUS  mandatory
            DESCRIPTION
                ""
            ::= { gdsl2-card 20 }

        gdsl2RemoteBertEntry  OBJECT-TYPE
            SYNTAX  Gdsl2RemoteBertEntry
            ACCESS  not-accessible
            STATUS  mandatory
            DESCRIPTION
                ""
            INDEX { gdsl2RBSlotIndex ,
                    gdsl2RBPortIndex }
            ::= { gdsl2RemoteBertTable 1 }

        Gdsl2RemoteBertEntry ::= SEQUENCE {
            gdsl2RBSlotIndex            LSSlotID,
            gdsl2RBPortIndex            G2PortID,
            gdsl2RemBertPatternType     INTEGER,
            gdsl2RemBertTestChannel     INTEGER,
            gdsl2RemBertTestControl     INTEGER,
            gdsl2RemBertStatus          INTEGER,
            gdsl2RemBertErrSecond       INTEGER,
            gdsl2RemBertErrCounter      INTEGER,
            gdsl2RemBertElapsedSecond   INTEGER,
            gdsl2RemBertUnsyncSecond    INTEGER
        }

        gdsl2RBSlotIndex  OBJECT-TYPE
            SYNTAX  LSSlotID
            ACCESS  read-only
            STATUS  mandatory
            DESCRIPTION
                "Gshdsl2 slot"
            ::= { gdsl2RemoteBertEntry 1 }

        gdsl2RBPortIndex  OBJECT-TYPE
            SYNTAX  G2PortID
            ACCESS  read-only
            STATUS  mandatory
            DESCRIPTION
                " Port 1/3."
            ::= { gdsl2RemoteBertEntry 2 }

        gdsl2RemBertPatternType  OBJECT-TYPE
            SYNTAX  INTEGER {
                    un-support(0),
--                      off(1),
                    bert-2-15-1(2),
                    bert-qrss(3)
                }
            ACCESS  read-write
            STATUS  mandatory
            DESCRIPTION
                "BERT Pattern Type"
            ::= { gdsl2RemoteBertEntry 3 }

        gdsl2RemBertTestChannel  OBJECT-TYPE
            SYNTAX  INTEGER {
                    un-support(0),
                    full(1)
                }
            ACCESS  read-write
            STATUS  mandatory
            DESCRIPTION
                "BERT Test Channel Type"
            ::= { gdsl2RemoteBertEntry 4 }

        gdsl2RemBertTestControl  OBJECT-TYPE
            SYNTAX  INTEGER {
                    un-support(0),
                    disable(1),
                    enable(2),
                    reset(3),
                    insert-error(4)
                }
            ACCESS  read-write
            STATUS  mandatory
            DESCRIPTION
                "BERT Test Control"
            ::= { gdsl2RemoteBertEntry 5 }

        gdsl2RemBertStatus  OBJECT-TYPE
            SYNTAX  INTEGER {
                    bert-unsync(1),
                    bert-sync(2),
                    bert-not-active(3)
                }
            ACCESS  read-only
            STATUS  mandatory
            DESCRIPTION
                "Remote BERT Status"
            ::= { gdsl2RemoteBertEntry 6 }

        gdsl2RemBertErrSecond  OBJECT-TYPE
            SYNTAX  INTEGER
            ACCESS  read-only
            STATUS  mandatory
            DESCRIPTION
                "Remote BERT Error Seconds"
            ::= { gdsl2RemoteBertEntry 7 }

        gdsl2RemBertErrCounter  OBJECT-TYPE
            SYNTAX  INTEGER
            ACCESS  read-only
            STATUS  mandatory
            DESCRIPTION
                "Remote BERT Error Counter"
            ::= { gdsl2RemoteBertEntry 8 }

        gdsl2RemBertElapsedSecond  OBJECT-TYPE
            SYNTAX  INTEGER
            ACCESS  read-only
            STATUS  mandatory
            DESCRIPTION
                "Remote BERT Elapsed Time"
            ::= { gdsl2RemoteBertEntry 9 }

        gdsl2RemBertUnsyncSecond  OBJECT-TYPE
            SYNTAX  INTEGER
            ACCESS  read-only
            STATUS  mandatory
            DESCRIPTION
                "Remote BERT Unsync Time"
            ::= { gdsl2RemoteBertEntry 10 }


--
--  G.shdsl card Remote Router Table
--
    gdsl2RouterConfig     OBJECT IDENTIFIER ::= { gdsl2-card 21 }
--
--  G.shdsl card remote NI Control Table
--

        gdsl2RtrNiControlTable  OBJECT-TYPE
            SYNTAX  SEQUENCE OF Gdsl2RtrNiControlEntry
            ACCESS  not-accessible
            STATUS  mandatory
            DESCRIPTION
                "Router NI Configuration Control Table"
            ::= { gdsl2RouterConfig 1 }

        gdsl2RouterNiControlEntry  OBJECT-TYPE
            SYNTAX  Gdsl2RtrNiControlEntry
            ACCESS  not-accessible
            STATUS  mandatory
            DESCRIPTION
                "Router NI Configuration Control Entry"
            INDEX { gdsl2RtrNiUnitIndex ,
                    gdsl2RtrNiPortIndex ,
                    gdsl2RtrNiIndex }
            ::= { gdsl2RtrNiControlTable 1 }

        Gdsl2RtrNiControlEntry ::= SEQUENCE {
            gdsl2RtrNiUnitIndex         LSSlotID,
            gdsl2RtrNiPortIndex         G2PortID,
            gdsl2RtrNiIndex             INTEGER,
            gdsl2RtrIPAddr              IpAddress,
            gdsl2RtrSubnetMask          IpAddress,
            gdsl2RtrFrame               INTEGER,
            gdsl2RtrRIP1                INTEGER,
            gdsl2RtrRIP2                INTEGER,
            gdsl2RtrMode                INTEGER
        }

        gdsl2RtrNiUnitIndex  OBJECT-TYPE
            SYNTAX  LSSlotID
            ACCESS  read-only
            STATUS  mandatory
            DESCRIPTION
                "LS slot index"
            ::= { gdsl2RouterNiControlEntry 1 }

        gdsl2RtrNiPortIndex  OBJECT-TYPE
            SYNTAX  G2PortID
            ACCESS  read-only
            STATUS  mandatory
            DESCRIPTION
                " Port 1/3."
            ::= { gdsl2RouterNiControlEntry 2 }

        gdsl2RtrNiIndex  OBJECT-TYPE
            SYNTAX  INTEGER {
                    lan1(1),
                    wan1(2)
                }
            ACCESS  read-only
            STATUS  mandatory
            DESCRIPTION
                " Router Ni index"
            ::= { gdsl2RouterNiControlEntry 3 }

        gdsl2RtrIPAddr   OBJECT-TYPE
            SYNTAX  IpAddress
            ACCESS  read-write
            STATUS  mandatory
            DESCRIPTION
                " RTR IP Address"
            ::= { gdsl2RouterNiControlEntry 4 }

        gdsl2RtrSubnetMask OBJECT-TYPE
            SYNTAX  IpAddress
            ACCESS  read-write
            STATUS  mandatory
            DESCRIPTION
                " RTR net mask"
            ::= { gdsl2RouterNiControlEntry 5 }

        gdsl2RtrFrame  OBJECT-TYPE
            SYNTAX  INTEGER {
                    hdlc(1),
                    ppp(2),
--                      fr(3),
                    ethernet(4),
                    na(5)
                }
            ACCESS  read-write
            STATUS  mandatory
            DESCRIPTION
                " RTR Layer2 frame"
            ::= { gdsl2RouterNiControlEntry 6 }

        gdsl2RtrRIP1 OBJECT-TYPE
            SYNTAX  INTEGER {
                    disabled(1),
                    enabled(2),
                    na(3)
                }
            ACCESS  read-write
            STATUS  mandatory
            DESCRIPTION
                " RTR RIP1"
            ::= { gdsl2RouterNiControlEntry 7 }

        gdsl2RtrRIP2  OBJECT-TYPE
            SYNTAX  INTEGER {
                    disabled(1),
                    enabled(2),
                    na(3)
                }
            ACCESS  read-write
            STATUS  mandatory
            DESCRIPTION
                " RTR RIP2"
            ::= { gdsl2RouterNiControlEntry 8 }

        gdsl2RtrMode OBJECT-TYPE
            SYNTAX  INTEGER {
                    router(1),
                    bridge(2),
                    na(3)
                }
            ACCESS  read-write
            STATUS  mandatory
            DESCRIPTION
                " RTR mode"
            ::= { gdsl2RouterNiControlEntry 9 }

--
--  G.shdsl card remote Route Table
--

        gdsl2RtrRouteCtrlTable  OBJECT-TYPE
            SYNTAX  SEQUENCE OF Gdsl2RtrRouteCtrlEntry
            ACCESS  not-accessible
            STATUS  mandatory
            DESCRIPTION
                "Router Route Control Table"
            ::= { gdsl2RouterConfig 2 }

        gdsl2RouterRouteControlEntry  OBJECT-TYPE
            SYNTAX  Gdsl2RtrRouteCtrlEntry
            ACCESS  not-accessible
            STATUS  mandatory
            DESCRIPTION
                "Router Route Control Entry"
            INDEX { gdsl2RtrRUnitIndex ,
                    gdsl2RtrRPortIndex ,
                    gdsl2RtrEntry }
            ::= { gdsl2RtrRouteCtrlTable 1 }

        Gdsl2RtrRouteCtrlEntry ::= SEQUENCE {
            gdsl2RtrRUnitIndex          LSSlotID,
            gdsl2RtrRPortIndex          G2PortID,
            gdsl2RtrEntry               INTEGER (1..16),
            gdsl2RtrNetAddr             IpAddress,
            gdsl2RtrNetMask             IpAddress,
            gdsl2RtrGatewayAddr         IpAddress,
            gdsl2RtrNIAddr              IpAddress,
            gdsl2RtrMetric              INTEGER
        }

        gdsl2RtrRUnitIndex  OBJECT-TYPE
            SYNTAX  LSSlotID
            ACCESS  read-only
            STATUS  mandatory
            DESCRIPTION
                "LS slot index"
            ::= { gdsl2RouterRouteControlEntry 1 }

        gdsl2RtrRPortIndex  OBJECT-TYPE
            SYNTAX  G2PortID
            ACCESS  read-only
            STATUS  mandatory
            DESCRIPTION
                " Port 1/3."
            ::= { gdsl2RouterRouteControlEntry 2 }

        gdsl2RtrEntry  OBJECT-TYPE
            SYNTAX  INTEGER (1..16)
            ACCESS  read-only
            STATUS  mandatory
            DESCRIPTION
                " Router Route Entry"
            ::= { gdsl2RouterRouteControlEntry 3 }


        gdsl2RtrNetAddr   OBJECT-TYPE
            SYNTAX  IpAddress
            ACCESS  read-write
            STATUS  mandatory
            DESCRIPTION
                " RTR route net Address"
            ::= { gdsl2RouterRouteControlEntry 4 }

        gdsl2RtrNetMask OBJECT-TYPE
            SYNTAX  IpAddress
            ACCESS  read-write
            STATUS  mandatory
            DESCRIPTION
                " RTR route net mask"
            ::= { gdsl2RouterRouteControlEntry 5 }

        gdsl2RtrGatewayAddr  OBJECT-TYPE
            SYNTAX  IpAddress
            ACCESS  read-write
            STATUS  mandatory
            DESCRIPTION
                " RTR route gateway Address"
            ::= { gdsl2RouterRouteControlEntry 6 }

        gdsl2RtrNIAddr  OBJECT-TYPE
            SYNTAX  IpAddress
            ACCESS  read-write
            STATUS  mandatory
            DESCRIPTION
                " RTR route NI Address"
            ::= { gdsl2RouterRouteControlEntry 7 }


        gdsl2RtrMetric OBJECT-TYPE
            SYNTAX  INTEGER {
                    na(255)
                }
            ACCESS  read-write
            STATUS  mandatory
            DESCRIPTION
                " RTR Route metric"
            ::= { gdsl2RouterRouteControlEntry 8 }

--
--  G.shdsl card remote Router Command
--
        gdsl2RtrCommandTable  OBJECT-TYPE
            SYNTAX  SEQUENCE OF Gdsl2RtrCmdEntry
            ACCESS  not-accessible
            STATUS  mandatory
            DESCRIPTION
                "Router Command Table"
            ::= { gdsl2RouterConfig 3 }

        gdsl2RtrCommandEntry  OBJECT-TYPE
            SYNTAX  Gdsl2RtrCmdEntry
            ACCESS  not-accessible
            STATUS  mandatory
            DESCRIPTION
                "Router Command Entry"
            INDEX { gdsl2RtrCmdUnitIndex ,
                    gdsl2RtrCmdPortIndex }
            ::= { gdsl2RtrCommandTable 1 }

        Gdsl2RtrCmdEntry ::= SEQUENCE {
            gdsl2RtrCmdUnitIndex        LSSlotID,
            gdsl2RtrCmdPortIndex        G2PortID,
            gdsl2RtrCommand             INTEGER,
            gdsl2CRCtransparency        INTEGER
        }

        gdsl2RtrCmdUnitIndex  OBJECT-TYPE
            SYNTAX  LSSlotID
            ACCESS  read-only
            STATUS  mandatory
            DESCRIPTION
                "LS slot index"
            ::= { gdsl2RtrCommandEntry 1 }

        gdsl2RtrCmdPortIndex  OBJECT-TYPE
            SYNTAX  G2PortID
            ACCESS  read-only
            STATUS  mandatory
            DESCRIPTION
                " Port 1/3."
            ::= { gdsl2RtrCommandEntry 2 }

        gdsl2RtrCommand  OBJECT-TYPE
            SYNTAX  INTEGER {
                    reset(1),
                    load-default(2),
                    none(3),
                    re-get-map-cfg(11),
                    re-get-ni-cfg(12),
                    re-get-rtr-cfg(13),
                    re-get-crc-cfg(14),
                    re-get-all-cfg(15)
                }
            ACCESS  read-write
            STATUS  mandatory
            DESCRIPTION
                " Router Command(reset or load-default)"
            ::= { gdsl2RtrCommandEntry 3 }

        gdsl2CRCtransparency OBJECT-TYPE
            SYNTAX  INTEGER {
                    off(1),
                    on(2),
                    na(3)
                }
            ACCESS  read-write
            STATUS  mandatory
            DESCRIPTION
                " CRC transparency"
            ::= { gdsl2RtrCommandEntry 4 }


--
--  G.shdsl card remote Router Map
--
        gdsl2RtrMapTable  OBJECT-TYPE
            SYNTAX  SEQUENCE OF Gdsl2RtrMappingEntry
            ACCESS  not-accessible
            STATUS  mandatory
            DESCRIPTION
                "Router Map Table"
            ::= { gdsl2RouterConfig 4 }

        gdsl2RtrMapEntry  OBJECT-TYPE
            SYNTAX  Gdsl2RtrMappingEntry
            ACCESS  not-accessible
            STATUS  mandatory
            DESCRIPTION
                "Router Map Entry"
            INDEX { gdsl2RtrMapUnitIndex ,
                    gdsl2RtrMapPortIndex ,
                    gdsl2RtrMapTsIndex }
            ::= { gdsl2RtrMapTable 1 }

        Gdsl2RtrMappingEntry ::= SEQUENCE {
            gdsl2RtrMapUnitIndex        LSSlotID,
            gdsl2RtrMapPortIndex        G2PortID,
            gdsl2RtrMapTsIndex          TimeslotID,
            gdsl2RtrCh                  INTEGER
        }

        gdsl2RtrMapUnitIndex  OBJECT-TYPE
            SYNTAX  LSSlotID
            ACCESS  read-only
            STATUS  mandatory
            DESCRIPTION
                "LS slot index"
            ::= { gdsl2RtrMapEntry 1 }

        gdsl2RtrMapPortIndex  OBJECT-TYPE
            SYNTAX  G2PortID
            ACCESS  read-only
            STATUS  mandatory
            DESCRIPTION
                " Port 1/3."
            ::= { gdsl2RtrMapEntry 2 }

        gdsl2RtrMapTsIndex  OBJECT-TYPE
            SYNTAX  TimeslotID
            ACCESS  read-only
            STATUS  mandatory
            DESCRIPTION
                " Timeslot 1~32, total 32 timeslots."
            ::= { gdsl2RtrMapEntry 3 }

        gdsl2RtrCh  OBJECT-TYPE
            SYNTAX  INTEGER {
                    idle(1),
                    wan1(2),
                    na(3)
                }
            ACCESS  read-write
            STATUS  mandatory
            DESCRIPTION
                "channel map data"
            ::= { gdsl2RtrMapEntry 4 }


--
--  G.shdsl card remote Bridge Config
--

    gdsl2RemoteBridgeConfig OBJECT IDENTIFIER ::= { gdsl2-card 22 }

--  G.shdsl card remote Bridge: config table
        gdsl2RemBridgeTable  OBJECT-TYPE
            SYNTAX  SEQUENCE OF Gdsl2RemBridgeEntry
            ACCESS  not-accessible
            STATUS  mandatory
            DESCRIPTION
                "Remote Bridge Table"
            ::= { gdsl2RemoteBridgeConfig 1 }

        gdsl2RemBridgeEntry  OBJECT-TYPE
            SYNTAX  Gdsl2RemBridgeEntry
            ACCESS  not-accessible
            STATUS  mandatory
            DESCRIPTION
                "Remote Bridge Entry"
            INDEX { gdsl2RBgSlotIndex ,
                    gdsl2RBgPortIndex }
            ::= { gdsl2RemBridgeTable 1 }

        Gdsl2RemBridgeEntry ::= SEQUENCE {
            gdsl2RBgSlotIndex           LSSlotID,
            gdsl2RBgPortIndex           G2PortID,
            gdsl2RemBrgAgeTime          INTEGER (10..1000000),
            gdsl2RemBrgCRC              INTEGER,
            gdsl2RemBrgLanSpeed         INTEGER
        }

        gdsl2RBgSlotIndex  OBJECT-TYPE
            SYNTAX  LSSlotID
            ACCESS  read-only
            STATUS  mandatory
            DESCRIPTION
                "LS slot index"
            ::= { gdsl2RemBridgeEntry 1 }

        gdsl2RBgPortIndex  OBJECT-TYPE
            SYNTAX  G2PortID
            ACCESS  read-only
            STATUS  mandatory
            DESCRIPTION
                " Port 1/3."
            ::= { gdsl2RemBridgeEntry 2 }

        gdsl2RemBrgAgeTime  OBJECT-TYPE
            SYNTAX  INTEGER (10..1000000)
            ACCESS  read-write
            STATUS  mandatory
            DESCRIPTION
                "Remote Bridge: Age time 10~1000000 seconds."
            ::= { gdsl2RemBridgeEntry 3 }

        gdsl2RemBrgCRC  OBJECT-TYPE
            SYNTAX  INTEGER {
                    off(1),
                    on(2)
                }
            ACCESS  read-write
            STATUS  mandatory
            DESCRIPTION
                "Remote Bridge: CRC"
            ::= { gdsl2RemBridgeEntry 4 }

        gdsl2RemBrgLanSpeed  OBJECT-TYPE
            SYNTAX  INTEGER {
                    no(0),
                    half-duplex-10M(1),
                    full-duplex-10M(2),
                    half-duplex-100M(3),
                    full-duplex-100M(4),
                    auto-negotiation(5)
                }
            ACCESS  read-write
            STATUS  mandatory
            DESCRIPTION
                "Remote Bridge: LAN speed"
            ::= { gdsl2RemBridgeEntry 5 }


--  G.shdsl card remote VLAN: VLAN State Table
        gdsl2RemVlanStateTable  OBJECT-TYPE
            SYNTAX  SEQUENCE OF Gdsl2RemVlanStateEntry
            ACCESS  not-accessible
            STATUS  mandatory
            DESCRIPTION
                "Remote VLAN State Table"
            ::= { gdsl2RemoteBridgeConfig 2 }

        gdsl2RemVlanStateEntry  OBJECT-TYPE
            SYNTAX  Gdsl2RemVlanStateEntry
            ACCESS  not-accessible
            STATUS  mandatory
            DESCRIPTION
                "Remote VLAN State Entry"
            INDEX { gdsl2RVSSlotIndex ,
                    gdsl2RVSPortIndex }
            ::= { gdsl2RemVlanStateTable 1 }

        Gdsl2RemVlanStateEntry ::= SEQUENCE {
            gdsl2RVSSlotIndex           LSSlotID,
            gdsl2RVSPortIndex           G2PortID,
            gdsl2RemVlanEnable          INTEGER,
            gdsl2RemVlanMgmtVID         INTEGER (1..4095),
            gdsl2RemVlanRegenCRC        INTEGER
        }

        gdsl2RVSSlotIndex  OBJECT-TYPE
            SYNTAX  LSSlotID
            ACCESS  read-only
            STATUS  mandatory
            DESCRIPTION
                "LS slot index"
            ::= { gdsl2RemVlanStateEntry 1 }

        gdsl2RVSPortIndex  OBJECT-TYPE
            SYNTAX  G2PortID
            ACCESS  read-only
            STATUS  mandatory
            DESCRIPTION
                " Port 1/3."
            ::= { gdsl2RemVlanStateEntry 2 }

        gdsl2RemVlanEnable  OBJECT-TYPE
            SYNTAX  INTEGER {
                    disable(1),
                    enable(2)
                }
            ACCESS  read-write
            STATUS  mandatory
            DESCRIPTION
                "Remote VLAN: disable or enable"
            ::= { gdsl2RemVlanStateEntry 3 }

        gdsl2RemVlanMgmtVID  OBJECT-TYPE
            SYNTAX  INTEGER (1..4095)
            ACCESS  read-write
            STATUS  mandatory
            DESCRIPTION
                "Remote VLAN: Magement VID"
            ::= { gdsl2RemVlanStateEntry 4 }

        gdsl2RemVlanRegenCRC  OBJECT-TYPE
            SYNTAX  INTEGER {
                    disable(1),
                    enable(2)
                }
            ACCESS  read-write
            STATUS  mandatory
            DESCRIPTION
                "Remote VLAN: regenate CRC"
            ::= { gdsl2RemVlanStateEntry 5 }


--  G.shdsl card remote Bridge: VLAN Control Table
        gdsl2RemVlanControlTable  OBJECT-TYPE
            SYNTAX  SEQUENCE OF Gdsl2RemVlanControlEntry
            ACCESS  not-accessible
            STATUS  mandatory
            DESCRIPTION
                "Remote VLAN Control Table"
            ::= { gdsl2RemoteBridgeConfig 3 }

        gdsl2RemVlanControlEntry  OBJECT-TYPE
            SYNTAX  Gdsl2RemVlanControlEntry
            ACCESS  not-accessible
            STATUS  mandatory
            DESCRIPTION
                "Remote VLAN Control Entry"
            INDEX { gdsl2RVCSlotIndex ,
                    gdsl2RVCPortIndex }
            ::= { gdsl2RemVlanControlTable 1 }

        Gdsl2RemVlanControlEntry ::= SEQUENCE {
            gdsl2RVCSlotIndex           LSSlotID,
            gdsl2RVCPortIndex           G2PortID,
            gdsl2RemVlanVID             INTEGER (1..4095),
            gdsl2RemVlanTAG             INTEGER,
            gdsl2RemVlanMember          INTEGER,
            gdsl2RemVlanCommand         INTEGER,
            gdsl2RemVlanResponse        INTEGER
        }

        gdsl2RVCSlotIndex  OBJECT-TYPE
            SYNTAX  LSSlotID
            ACCESS  read-only
            STATUS  mandatory
            DESCRIPTION
                "LS slot index"
            ::= { gdsl2RemVlanControlEntry 1 }

        gdsl2RVCPortIndex  OBJECT-TYPE
            SYNTAX  G2PortID
            ACCESS  read-only
            STATUS  mandatory
            DESCRIPTION
                " Port 1/3."
            ::= { gdsl2RemVlanControlEntry 2 }

        gdsl2RemVlanVID  OBJECT-TYPE
            SYNTAX  INTEGER (1..4095)
            ACCESS  read-write
            STATUS  mandatory
            DESCRIPTION
                "Remote VLAN: VLAN ID"
            ::= { gdsl2RemVlanControlEntry 4 }

        gdsl2RemVlanTAG  OBJECT-TYPE
            SYNTAX  INTEGER {
                    untag(1),
                    tag(2)
                }
            ACCESS  read-write
            STATUS  mandatory
            DESCRIPTION
                "Remote VLAN: UNTAG or TAG"
            ::= { gdsl2RemVlanControlEntry 5 }

        gdsl2RemVlanMember  OBJECT-TYPE
            SYNTAX  INTEGER {
                    lan1(1),
                    wan1(2)
                }
            ACCESS  read-write
            STATUS  mandatory
            DESCRIPTION
                "Remote VLAN: Member is LAN1 or WAN1"
            ::= { gdsl2RemVlanControlEntry 6 }

        gdsl2RemVlanCommand  OBJECT-TYPE
            SYNTAX  INTEGER {
                    create-vid(1),
                    add-member(2),
                    deactive-vid(3),
                    remove-member(4)
                }
            ACCESS  read-write
            STATUS  mandatory
            DESCRIPTION
                "Remote VLAN: command"
            ::= { gdsl2RemVlanControlEntry 11 }

        gdsl2RemVlanResponse  OBJECT-TYPE
            SYNTAX  INTEGER {
                    ok(1),
                    vid-created-before(2),
                    vid-not-created-before(3),
                    not-empty(4),
                    no-response(11),
                    not-available(12)
                }
            ACCESS  read-only
            STATUS  mandatory
            DESCRIPTION
                "Remote VLAN: Set response"
            ::= { gdsl2RemVlanControlEntry 12 }


--  G.shdsl card remote Bridge: VLAN List Table
        gdsl2RemVlanListTable  OBJECT-TYPE
            SYNTAX  SEQUENCE OF Gdsl2RemVlanListEntry
            ACCESS  not-accessible
            STATUS  mandatory
            DESCRIPTION
                "Remote VLAN List Table"
            ::= { gdsl2RemoteBridgeConfig 4 }

        gdsl2RemVlanListEntry  OBJECT-TYPE
            SYNTAX  Gdsl2RemVlanListEntry
            ACCESS  not-accessible
            STATUS  mandatory
            DESCRIPTION
                "Remote VLAN List Entry"
            INDEX { gdsl2RVLSlotIndex ,
                    gdsl2RVLPortIndex ,
                    gdsl2RVLVLanIndex }
            ::= { gdsl2RemVlanListTable 1 }

        Gdsl2RemVlanListEntry ::= SEQUENCE {
            gdsl2RVLSlotIndex           LSSlotID,
            gdsl2RVLPortIndex           G2PortID,
            gdsl2RVLVLanIndex           INTEGER,
            gdsl2RVLVlanVID             INTEGER (1..4095),
            gdsl2RVLVlanTAGmember       DisplayString,
            gdsl2RVLVlanUNTAGmember     DisplayString
        }

        gdsl2RVLSlotIndex  OBJECT-TYPE
            SYNTAX  LSSlotID
            ACCESS  read-only
            STATUS  mandatory
            DESCRIPTION
                "LS slot index"
            ::= { gdsl2RemVlanListEntry 1 }

        gdsl2RVLPortIndex  OBJECT-TYPE
            SYNTAX  G2PortID
            ACCESS  read-only
            STATUS  mandatory
            DESCRIPTION
                " Port 1/3."
            ::= { gdsl2RemVlanListEntry 2 }

        gdsl2RVLVLanIndex  OBJECT-TYPE
            SYNTAX  INTEGER
            ACCESS  read-only
            STATUS  mandatory
            DESCRIPTION
                "VLAN list index"
            ::= { gdsl2RemVlanListEntry 3 }

        gdsl2RVLVlanVID  OBJECT-TYPE
            SYNTAX  INTEGER (1..4095)
            ACCESS  read-only
            STATUS  mandatory
            DESCRIPTION
                "Remote VLAN: VLAN ID"
            ::= { gdsl2RemVlanListEntry 4 }

        gdsl2RVLVlanTAGmember  OBJECT-TYPE
            SYNTAX  DisplayString
            ACCESS  read-only
            STATUS  mandatory
            DESCRIPTION
                "Remote VLAN: TAG member"
            ::= { gdsl2RemVlanListEntry 5 }

        gdsl2RVLVlanUNTAGmember  OBJECT-TYPE
            SYNTAX  DisplayString
            ACCESS  read-only
            STATUS  mandatory
            DESCRIPTION
                "Remote VLAN: UNTAG member"
            ::= { gdsl2RemVlanListEntry 6 }


--  G.shdsl card remote Bridge: VLAN Port Table
        gdsl2RemVlanPortTable  OBJECT-TYPE
            SYNTAX  SEQUENCE OF Gdsl2RemVlanPortEntry
            ACCESS  not-accessible
            STATUS  mandatory
            DESCRIPTION
                "Remote VLAN Port Table"
            ::= { gdsl2RemoteBridgeConfig 5 }

        gdsl2RemVlanPortEntry  OBJECT-TYPE
            SYNTAX  Gdsl2RemVlanPortEntry
            ACCESS  not-accessible
            STATUS  mandatory
            DESCRIPTION
                "Remote VLAN Port Entry"
            INDEX { gdsl2RVPSlotIndex ,
                    gdsl2RVPPortIndex ,
                    gdsl2RVPVPIndex }
            ::= { gdsl2RemVlanPortTable 1 }

        Gdsl2RemVlanPortEntry ::= SEQUENCE {
            gdsl2RVPSlotIndex           LSSlotID,
            gdsl2RVPPortIndex           G2PortID,
            gdsl2RVPVPIndex             INTEGER,
            gdsl2RVPVlanPVID            INTEGER (1..4095),
            gdsl2RVPVlanFrameType       INTEGER,
            gdsl2RVPVlanIngressFilter   INTEGER,
            gdsl2RVPSetResponse         INTEGER
        }

        gdsl2RVPSlotIndex  OBJECT-TYPE
            SYNTAX  LSSlotID
            ACCESS  read-only
            STATUS  mandatory
            DESCRIPTION
                "LS slot index"
            ::= { gdsl2RemVlanPortEntry 1 }

        gdsl2RVPPortIndex  OBJECT-TYPE
            SYNTAX  G2PortID
            ACCESS  read-only
            STATUS  mandatory
            DESCRIPTION
                " Port 1/3."
            ::= { gdsl2RemVlanPortEntry 2 }

        gdsl2RVPVPIndex  OBJECT-TYPE
            SYNTAX  INTEGER {
                    lan1(1),
                    wan1(2)
                }
            ACCESS  read-only
            STATUS  mandatory
            DESCRIPTION
                "VLAN Port index"
            ::= { gdsl2RemVlanPortEntry 3 }

        gdsl2RVPVlanPVID  OBJECT-TYPE
            SYNTAX  INTEGER (1..4095)
            ACCESS  read-write
            STATUS  mandatory
            DESCRIPTION
                "Remote VLAN: VLAN ID"
            ::= { gdsl2RemVlanPortEntry 4 }

        gdsl2RVPVlanFrameType  OBJECT-TYPE
            SYNTAX  INTEGER {
                    all(1),
                    tag-only(2)
                }
            ACCESS  read-write
            STATUS  mandatory
            DESCRIPTION
                "Remote VLAN: Frame Type"
            ::= { gdsl2RemVlanPortEntry 5 }

        gdsl2RVPVlanIngressFilter  OBJECT-TYPE
            SYNTAX  INTEGER {
                    disable(1),
                    enable(2)
                }
            ACCESS  read-write
            STATUS  mandatory
            DESCRIPTION
                "Remote VLAN: Ingress Filter"
            ::= { gdsl2RemVlanPortEntry 6 }

        gdsl2RVPSetResponse  OBJECT-TYPE
            SYNTAX  INTEGER {
                    ok(1),
                    vid-not-created-before(3),
                    no-response(11),
                    not-available(12)
                }
            ACCESS  read-only
            STATUS  mandatory
            DESCRIPTION
                "Remote VLAN: Set response"
            ::= { gdsl2RemVlanPortEntry 7 }

        gdsl2TotalCard   OBJECT-TYPE
            SYNTAX  INTEGER
            ACCESS  read-only
            STATUS  mandatory
            DESCRIPTION
                "Total cards of GDSL2"
            ::= { gdsl2-card 100 }

--======================================================================--
--======================================================================--
--  G.SHDSL-4 MIB
--======================================================================--
--======================================================================--


--
--  GDSL4 SYSTEM Table
--

        gdsl4SystemTable  OBJECT-TYPE
            SYNTAX  SEQUENCE OF Gdsl4SystemEntry
            ACCESS  not-accessible
            STATUS  mandatory
            DESCRIPTION
                "The system control table."
            ::= { gdsl4-card 1 }

        gdsl4SystemEntry  OBJECT-TYPE
            SYNTAX  Gdsl4SystemEntry
            ACCESS  not-accessible
            STATUS  mandatory
            DESCRIPTION
                "An entry in the system table."
            INDEX { gdsl4SysSlotIndex ,
                    gdsl4SysPortIndex ,
                    gdsl4SysHTUIndex }
            ::= { gdsl4SystemTable 1 }

        Gdsl4SystemEntry ::= SEQUENCE {
            gdsl4SysSlotIndex           LSSlotID,
            gdsl4SysPortIndex           PortID,
            gdsl4SysHTUIndex            INTEGER,
            gdsl4Mode                   INTEGER,
            gdsl4ServiceType            INTEGER,
            gdsl4ClockSource            INTEGER,
            gdsl4Model                  INTEGER

    }

        gdsl4SysSlotIndex  OBJECT-TYPE
            SYNTAX  LSSlotID
            ACCESS  read-only
            STATUS  mandatory
            DESCRIPTION
                "Gshdsl4 slot"
            ::= { gdsl4SystemEntry 1 }

        gdsl4SysPortIndex  OBJECT-TYPE
            SYNTAX  PortID
            ACCESS  read-only
            STATUS  mandatory
            DESCRIPTION
                " Port 1~4."
            ::= { gdsl4SystemEntry 2 }

        gdsl4SysHTUIndex  OBJECT-TYPE
            SYNTAX  INTEGER {
                    local(1),
                    remote(2)
                }
            ACCESS  read-only
            STATUS  mandatory
            DESCRIPTION
                "Local or Remote"
            ::= { gdsl4SystemEntry 3 }

        gdsl4Mode  OBJECT-TYPE
            SYNTAX  INTEGER {
                    master(1),
                    slave(2)
                }
            ACCESS  read-write
            STATUS  mandatory
            DESCRIPTION
                "G.SHDSL mode (Master or Slave)"
            ::= { gdsl4SystemEntry 4 }

        gdsl4ServiceType  OBJECT-TYPE
            SYNTAX  INTEGER {
                    one-pair(1),
                    two-pairs(2)
                }
            ACCESS  read-only
            STATUS  mandatory
            DESCRIPTION
                " Service Configuration"
            ::= { gdsl4SystemEntry 5 }

        gdsl4ClockSource  OBJECT-TYPE
            SYNTAX  INTEGER {
                    line(1),
                    system(2),
                    dte(3),
                    e1t1(4)
                }
            ACCESS  read-write
            STATUS  mandatory
            DESCRIPTION
                " System Master Clock Source"
            ::= { gdsl4SystemEntry 6 }

        gdsl4Model  OBJECT-TYPE
            SYNTAX  INTEGER {
                    rack(1),
                    h3300-3s(2),
                    h3300(3),
                    h3310(4),
                    h3304(5),
                    other(99)
                }
            ACCESS  read-only
            STATUS  mandatory
            DESCRIPTION
                "G.shdsl model"
            ::= { gdsl4SystemEntry 7 }


--
--  GDSL4 Line Configuartion for Loop-1, Loop-2
--

        gdsl4LineConfigTable  OBJECT-TYPE
            SYNTAX  SEQUENCE OF Gdsl4LineConfigEntry
            ACCESS  not-accessible
            STATUS  mandatory
            DESCRIPTION
                "The G.SHDSL Line Configuration table."
            ::= { gdsl4-card 2 }

        gdsl4LineConfigEntry  OBJECT-TYPE
            SYNTAX  Gdsl4LineConfigEntry
            ACCESS  not-accessible
            STATUS  mandatory
            DESCRIPTION
                "An entry in the G.SHDSL Line Configuration table."
            INDEX { gdsl4LCSlotIndex ,
                    gdsl4LCPortIndex ,
                    gdsl4LineLoopNumber }
            ::= { gdsl4LineConfigTable 1 }

        Gdsl4LineConfigEntry ::= SEQUENCE {
            gdsl4LCSlotIndex            LSSlotID,
            gdsl4LCPortIndex            PortID,
            gdsl4LineLoopNumber         INTEGER,
            gdsl4LineRate               INTEGER,
            gdsl4LineCode               INTEGER,
            gdsl4LineNx64               INTEGER,
            gdsl4CAS                    INTEGER,
            gdsl4OOS                    INTEGER
        }

        gdsl4LCSlotIndex  OBJECT-TYPE
            SYNTAX  LSSlotID
            ACCESS  read-only
            STATUS  mandatory
            DESCRIPTION
                "Gshdsl4 slot"
            ::= { gdsl4LineConfigEntry 1 }

        gdsl4LCPortIndex  OBJECT-TYPE
            SYNTAX  PortID
            ACCESS  read-only
            STATUS  mandatory
            DESCRIPTION
                " Port 1~4."
            ::= { gdsl4LineConfigEntry 2 }

        gdsl4LineLoopNumber  OBJECT-TYPE
            SYNTAX  INTEGER (1..2)
            ACCESS  read-only
            STATUS  mandatory
            DESCRIPTION
                "Unit Loop Number"
            ::= { gdsl4LineConfigEntry 3 }

        gdsl4LineRate  OBJECT-TYPE
            SYNTAX  INTEGER {
                    r0Kbps(0),
                    r72Kbps(1),
                    r136Kbps(2),
                    r200Kbps(3),
                    r264Kbps(4),
                    r328Kbps(5),
                    r392Kbps(6),
                    r456Kbps(7),
                    r520Kbps(8),
                    r584Kbps(9),
                    r648Kbps(10),
                    r712Kbps(11),
                    r776Kbps(12),
                    r840Kbps(13),
                    r904Kbps(14),
                    r968Kbps(15),
                    r1032Kbps(16),
                    r1096Kbps(17),
                    r1160Kbps(18),
                    r1224Kbps(19),
                    r1288Kbps(20),
                    r1352Kbps(21),
                    r1416Kbps(22),
                    r1480Kbps(23),
                    r1544Kbps(24),
                    r1608Kbps(25),
                    r1672Kbps(26),
                    r1736Kbps(27),
                    r1800Kbps(28),
                    r1864Kbps(29),
                    r1928Kbps(30),
                    r1992Kbps(31),
                    r2056Kbps(32)
                }
            ACCESS  read-only
            STATUS  mandatory
            DESCRIPTION
                "To describe G.SHDSL Line Rate of specified loop,
                for an example: 776Kbps"
            ::= { gdsl4LineConfigEntry 4 }

        gdsl4LineCode  OBJECT-TYPE
            SYNTAX  INTEGER {
                    code-2b1q(1),
                    code-cap(2)
                }
            ACCESS  read-only
            STATUS  mandatory
            DESCRIPTION
                " G.SHDSL Line Coding"
            ::= { gdsl4LineConfigEntry 5 }

        gdsl4LineNx64  OBJECT-TYPE
            SYNTAX  INTEGER (3..32)
            ACCESS  read-write
            STATUS  mandatory
            DESCRIPTION
                "Number of N*64 Kbps"
            ::= { gdsl4LineConfigEntry 6 }

        gdsl4CAS  OBJECT-TYPE
            SYNTAX  INTEGER {
                    on(1),
                    off(2)
                }
            ACCESS  read-write
            STATUS  mandatory
            DESCRIPTION
                "G.SHDSL CAS"
            ::= { gdsl4LineConfigEntry 7 }

        gdsl4OOS  OBJECT-TYPE
            SYNTAX  INTEGER   {
                    b0001(1),
                    b0010(2),
                    b0011(3),
                    b0100(4),
                    b0101(5),
                    b0110(6),
                    b0111(7),
                    b1000(8),
                    b1001(9),
                    b1010(10),
                    b1011(11),
                    b1100(12),
                    b1101(13),
                    b1110(14),
                    b1111(15)
                }
            ACCESS  read-write
            STATUS  mandatory
            DESCRIPTION
                "OOS"
            ::= { gdsl4LineConfigEntry 8 }


--
--  GDSL4 AI Configuartion
--

        gdsl4AIConfigTable  OBJECT-TYPE
            SYNTAX  SEQUENCE OF Gdsl4AIConfigEntry
            ACCESS  not-accessible
            STATUS  mandatory
            DESCRIPTION
                "The G.SHDSL Application Interface Configuration table."
            ::= { gdsl4-card 3 }

        gdsl4AIConfigEntry  OBJECT-TYPE
            SYNTAX  Gdsl4AIConfigEntry
            ACCESS  not-accessible
            STATUS  mandatory
            DESCRIPTION
                "An entry in the G.SHDSL AI Configuration table."
            INDEX { gdsl4AICSlotIndex ,
                    gdsl4AICPortIndex ,
                    gdsl4AiNumber }
            ::= { gdsl4AIConfigTable 1 }

        Gdsl4AIConfigEntry ::= SEQUENCE {
            gdsl4AICSlotIndex           LSSlotID,
            gdsl4AICPortIndex           PortID,
            gdsl4AiNumber               INTEGER,
            gdsl4DteReady               INTEGER,
            gdsl4DteRate                INTEGER,
            gdsl4DteClockPolarity       INTEGER,
            gdsl4DteDataPolarity        INTEGER,
            gdsl4DteRTS                 INTEGER,
            gdsl4DteTTM                 INTEGER,
            gdsl4DteV54                 INTEGER,
            gdsl4DteInterface           INTEGER,
            gdsl4DS1Ready               INTEGER,
            gdsl4DS1Framing             INTEGER,
            gdsl4DS1Code                INTEGER,
            gdsl4DS1CAS                 INTEGER,
            gdsl4DS1Idle                INTEGER,
            gdsl4T1Interf               INTEGER,
            gdsl4T1EquLbo               INTEGER,
            gdsl4DS1Map                 DisplayString (SIZE(32)),
            gdsl4E1T1Mode               INTEGER,
            gdsl4AISetResponse          INTEGER
        }

        gdsl4AICSlotIndex  OBJECT-TYPE
            SYNTAX  LSSlotID
            ACCESS  read-only
            STATUS  mandatory
            DESCRIPTION
                "Gshdsl4 slot"
            ::= { gdsl4AIConfigEntry 1 }

        gdsl4AICPortIndex  OBJECT-TYPE
            SYNTAX  PortID
            ACCESS  read-only
            STATUS  mandatory
            DESCRIPTION
                " Port 1~4."
            ::= { gdsl4AIConfigEntry 2 }

        gdsl4AiNumber  OBJECT-TYPE
            SYNTAX  INTEGER  {
--                      local(1),
                    remote(2)
                }
            ACCESS  read-only
            STATUS  mandatory
            DESCRIPTION
                "Local or Remote unit"
            ::= { gdsl4AIConfigEntry 3 }

        gdsl4DteReady   OBJECT-TYPE
            SYNTAX  INTEGER  {
                    dte-ready(1),
                    dte-not-ready(2)
                }
            ACCESS  read-only
            STATUS  mandatory
            DESCRIPTION
                "DTE port is present or not"
            ::= { gdsl4AIConfigEntry 4 }

        gdsl4DteRate  OBJECT-TYPE
            SYNTAX  INTEGER {
                    dte64K(1),
                    dte128K(2),
                    dte192K(3),
                    dte256K(4),
                    dte320K(5),
                    dte384K(6),
                    dte448K(7),
                    dte512K(8),
                    dte576K(9),
                    dte640K(10),
                    dte704K(11),
                    dte768K(12),
                    dte832K(13),
                    dte896K(14),
                    dte960K(15),
                    dte1024K(16),
                    dte1088K(17),
                    dte1152K(18),
                    dte1216K(19),
                    dte1280K(20),
                    dte1344K(21),
                    dte1408K(22),
                    dte1472K(23),
                    dte1536K(24),
                    dte1600K(25),
                    dte1664K(26),
                    dte1728K(27),
                    dte1792K(28),
                    dte1856K(29),
                    dte1920K(30),
                    dte1984K(31),
                    dte2048K(32),
                    none(33)
                }
            ACCESS  read-write
            STATUS  mandatory
            DESCRIPTION
                " G.SHDSL DTE Base Rate"
            ::= { gdsl4AIConfigEntry 5 }

        gdsl4DteClockPolarity  OBJECT-TYPE
            SYNTAX  INTEGER {
                    clock-normal(1),
                    clock-inverted(2),
                    none(3)
                }
            ACCESS  read-write
            STATUS  mandatory
            DESCRIPTION
                " G.SHDSL DTE Clock Polarity"
            ::= { gdsl4AIConfigEntry 6 }

        gdsl4DteDataPolarity  OBJECT-TYPE
            SYNTAX  INTEGER {
                    data-normal(1),
                    data-inverted(2),
                    none(3)
                }
            ACCESS  read-write
            STATUS  mandatory
            DESCRIPTION
                " G.SHDSL DTE Data Polarity"
            ::= { gdsl4AIConfigEntry 7 }

        gdsl4DteRTS  OBJECT-TYPE
            SYNTAX  INTEGER {
                    rts-active(1),
                    rts-permanent(2),
                    none(3)
                }
            ACCESS  read-write
            STATUS  mandatory
            DESCRIPTION
                " G.SHDSL DTE RTS Mode"
            ::= { gdsl4AIConfigEntry 8 }

        gdsl4DteTTM  OBJECT-TYPE
            SYNTAX  INTEGER {
                    ttm-off(1),
                    ttm-on(2),
                    none(3)
                }
            ACCESS  read-write
            STATUS  mandatory
            DESCRIPTION
                " G.SHDSL DTE TTM Mode"
            ::= { gdsl4AIConfigEntry 9 }

        gdsl4DteV54  OBJECT-TYPE
            SYNTAX  INTEGER {
                    v54-off(1),
                    v54-on(2),
                    none(3)
                }
            ACCESS  read-write
            STATUS  mandatory
            DESCRIPTION
                " G.SHDSL DTE V.54 Loopback Mode"
            ::= { gdsl4AIConfigEntry 10 }

        gdsl4DteInterface  OBJECT-TYPE
            SYNTAX  INTEGER {
                    v35(1),
                    eia530-rs449(2),
                    x21(3),
                    rs232(4),
                    router(7),
                    subrate(8),
                    dte-e1(9),
                    dte-t1(10),
                    bridge(12),
                    n64-v35(17),
                    n64-eia530(18),
                    n64-x21(19),
                    n64-e1(25),
                    none(5)
                }
            ACCESS  read-only
            STATUS  mandatory
            DESCRIPTION
                " G.SHDSL DTE Interface Type"
            ::= { gdsl4AIConfigEntry 11 }

        gdsl4DS1Ready  OBJECT-TYPE
            SYNTAX  INTEGER {
                    ds1-ready(1),
                    ds1-not-ready(2)
                }
            ACCESS  read-only
            STATUS  mandatory
            DESCRIPTION
                "G.SHDSL DS1 unit is present or not"
            ::= { gdsl4AIConfigEntry 12 }

        gdsl4DS1Framing  OBJECT-TYPE
            SYNTAX  INTEGER {
                    unframe(1),
                    d4(2),
                    esf(3),
                    esf-t1-403(9),
                    crc-off(4),
                    crc-on(5),
                    cas-crc-off(6),
                    cas-crc-on(7),
                    none(8)
                }
            ACCESS  read-write
            STATUS  mandatory
            DESCRIPTION
                " G.SHDSL DS1 Framing"
            ::= { gdsl4AIConfigEntry 13 }

        gdsl4DS1Code  OBJECT-TYPE
            SYNTAX  INTEGER {
                    b8zs(1),
                    ami(2),
                    hdb3(3),
                    none(4)
                }
            ACCESS  read-write
            STATUS  mandatory
            DESCRIPTION
                " G.SHDSL DS1 Coding"
            ::= { gdsl4AIConfigEntry 14 }

        gdsl4DS1CAS  OBJECT-TYPE
            SYNTAX  INTEGER {
                    on(1),
                    off(2),
                    none(3)
                }
            ACCESS  read-only
            STATUS  mandatory
            DESCRIPTION
                " G.SHDSL DS1 CAS"
            ::= { gdsl4AIConfigEntry 15 }

        gdsl4DS1Idle  OBJECT-TYPE
            SYNTAX  INTEGER
            ACCESS  read-write
            STATUS  mandatory
            DESCRIPTION
                " G.SHDSL DS1 Idle code"
            ::= { gdsl4AIConfigEntry 16 }

        gdsl4T1Interf  OBJECT-TYPE
            SYNTAX  INTEGER {
                    short-haul(1),
                    long-haul(2),
                    none(3)
                }
            ACCESS  read-write
            STATUS  mandatory
            DESCRIPTION
                " G.SHDSL T1 Interface"
            ::= { gdsl4AIConfigEntry 17 }

        gdsl4T1EquLbo  OBJECT-TYPE
            SYNTAX  INTEGER {
                    equ-0-133-feet(1),
                    equ-133-266-feet(2),
                    equ-266-399-feet(3),
                    equ-399-533-feet(4),
                    equ-533-655-feet(5),
                    none(6),
                    lbo-0db(11),
                    lbo-75db(12),
                    lbo-15db(13),
                    lbo-225db(14)
                }
            ACCESS  read-write
            STATUS  mandatory
            DESCRIPTION
                " G.SHDSL T1 EQU/LBO"
            ::= { gdsl4AIConfigEntry 18 }

        gdsl4DS1Map  OBJECT-TYPE
            SYNTAX  DisplayString (SIZE(32))
            ACCESS  read-write
            STATUS  mandatory
            DESCRIPTION
                " G.SHDSL DS1 Map"
            ::= { gdsl4AIConfigEntry 20 }

        gdsl4E1T1Mode  OBJECT-TYPE
            SYNTAX  INTEGER {
                    e1(1),
                    t1(2),
                    na(3)
                }
            ACCESS  read-write
            STATUS  mandatory
            DESCRIPTION
                " G.SHDSL E1/T1 Mode"
            ::= { gdsl4AIConfigEntry 21 }

        gdsl4AISetResponse  OBJECT-TYPE
            SYNTAX  INTEGER {
                    na(1),
                    ok(2),
                    fail(3)
                }
            ACCESS  read-write
            STATUS  mandatory
            DESCRIPTION
                " G.SHDSL Config Set response"
            ::= { gdsl4AIConfigEntry 99 }


--
--  GDSL4 Current Performance Table
--

        gdsl4CurrPerfTable  OBJECT-TYPE
            SYNTAX  SEQUENCE OF Gdsl4CurrPerfEntry
            ACCESS  not-accessible
            STATUS  mandatory
            DESCRIPTION
                ""
            ::= { gdsl4-card 4 }

        gdsl4CurrPerfEntry  OBJECT-TYPE
            SYNTAX  Gdsl4CurrPerfEntry
            ACCESS  not-accessible
            STATUS  mandatory
            DESCRIPTION
                " "
            INDEX { gdsl4CPSlotIndex ,
                    gdsl4CPPortIndex ,
                    gdsl4CurrPerfTypeIndex }
            ::= { gdsl4CurrPerfTable 1 }

        Gdsl4CurrPerfEntry ::= SEQUENCE  {
            gdsl4CPSlotIndex            LSSlotID,
            gdsl4CPPortIndex            PortID,
            gdsl4CurrPerfTypeIndex      INTEGER,
            gdsl4CurrES                 INTEGER,
            gdsl4CurrSES                INTEGER,
            gdsl4CurrUAS                INTEGER,
            gdsl4Curr15MinTimeElapsed   INTEGER,
            gdsl4Valid15MinInterval     INTEGER
        }

        gdsl4CPSlotIndex  OBJECT-TYPE
            SYNTAX  LSSlotID
            ACCESS  read-only
            STATUS  mandatory
            DESCRIPTION
                "Gshdsl4 slot"
            ::= { gdsl4CurrPerfEntry 1 }

        gdsl4CPPortIndex  OBJECT-TYPE
            SYNTAX  PortID
            ACCESS  read-only
            STATUS  mandatory
            DESCRIPTION
                " Port 1~4."
            ::= { gdsl4CurrPerfEntry 2 }

        gdsl4CurrPerfTypeIndex  OBJECT-TYPE
            SYNTAX  INTEGER {
                    master-loop-1(1),
                    master-loop-2(2),
                    master-ds1(3),
                    slave-loop-1(4),
                    slave-loop-2(5),
                    slave-ds1(6)
                }
            ACCESS  read-only
            STATUS  mandatory
            DESCRIPTION
                "Performance Type"
            ::= { gdsl4CurrPerfEntry 3 }

        gdsl4CurrES  OBJECT-TYPE
            SYNTAX  INTEGER
            ACCESS  read-only
            STATUS  mandatory
            DESCRIPTION
                " ES Error Counter "
            ::= { gdsl4CurrPerfEntry 4 }

        gdsl4CurrSES  OBJECT-TYPE
            SYNTAX  INTEGER
            ACCESS  read-only
            STATUS  mandatory
            DESCRIPTION
                " SES Error Counter "
            ::= { gdsl4CurrPerfEntry 5 }

        gdsl4CurrUAS  OBJECT-TYPE
            SYNTAX  INTEGER
            ACCESS  read-only
            STATUS  mandatory
            DESCRIPTION
                " UAS Error Counter "
            ::= { gdsl4CurrPerfEntry 6 }

        gdsl4Curr15MinTimeElapsed  OBJECT-TYPE
            SYNTAX  INTEGER
            ACCESS  read-only
            STATUS  mandatory
            DESCRIPTION
                " Current 15-minute time elapsed"
            ::= { gdsl4CurrPerfEntry 7 }

        gdsl4Valid15MinInterval  OBJECT-TYPE
            SYNTAX  INTEGER
            ACCESS  read-only
            STATUS  mandatory
            DESCRIPTION
                " Current 1-day Valid 15-min interval"
            ::= { gdsl4CurrPerfEntry 8 }


--
--  GDSL4 Total Performance Table
--

        gdsl4TotalPerfTable  OBJECT-TYPE
            SYNTAX  SEQUENCE OF Gdsl4TotalPerfEntry
            ACCESS  not-accessible
            STATUS  mandatory
            DESCRIPTION
                ""
            ::= { gdsl4-card 5 }

        gdsl4TotalPerfEntry  OBJECT-TYPE
            SYNTAX  Gdsl4TotalPerfEntry
            ACCESS  not-accessible
            STATUS  mandatory
            DESCRIPTION
                " "
            INDEX { gdsl4TPSlotIndex ,
                    gdsl4TPPortIndex ,
                    gdsl4TotalPerfTypeIndex }
            ::= { gdsl4TotalPerfTable 1 }

        Gdsl4TotalPerfEntry ::= SEQUENCE  {
            gdsl4TPSlotIndex            LSSlotID,
            gdsl4TPPortIndex            PortID,
            gdsl4TotalPerfTypeIndex     INTEGER,
            gdsl4TotalES                INTEGER,
            gdsl4TotalSES               INTEGER,
            gdsl4TotalUAS               INTEGER
        }

        gdsl4TPSlotIndex  OBJECT-TYPE
            SYNTAX  LSSlotID
            ACCESS  read-only
            STATUS  mandatory
            DESCRIPTION
                "Gshdsl4 slot"
            ::= { gdsl4TotalPerfEntry 1 }

        gdsl4TPPortIndex  OBJECT-TYPE
            SYNTAX  PortID
            ACCESS  read-only
            STATUS  mandatory
            DESCRIPTION
                " Port 1~4."
            ::= { gdsl4TotalPerfEntry 2 }

        gdsl4TotalPerfTypeIndex  OBJECT-TYPE
            SYNTAX  INTEGER {
                    master-loop-1(1),
                    master-loop-2(2),
                    master-ds1(3),
                    slave-loop-1(4),
                    slave-loop-2(5),
                    slave-ds1(6)
                }
            ACCESS  read-only
            STATUS  mandatory
            DESCRIPTION
                "Performance Type"
            ::= { gdsl4TotalPerfEntry 3 }

        gdsl4TotalES  OBJECT-TYPE
            SYNTAX  INTEGER
            ACCESS  read-only
            STATUS  mandatory
            DESCRIPTION
                " ES Error Counter "
            ::= { gdsl4TotalPerfEntry 4 }

        gdsl4TotalSES  OBJECT-TYPE
            SYNTAX  INTEGER
            ACCESS  read-only
            STATUS  mandatory
            DESCRIPTION
                " SES Error Counter "
            ::= { gdsl4TotalPerfEntry 5 }

        gdsl4TotalUAS  OBJECT-TYPE
            SYNTAX  INTEGER
            ACCESS  read-only
            STATUS  mandatory
            DESCRIPTION
                " UAS Error Counter "
            ::= { gdsl4TotalPerfEntry 6 }

--
--  Interval Performance Table
--

        gdsl4IntvPerfTable  OBJECT-TYPE
            SYNTAX  SEQUENCE OF Gdsl4IntvPerfEntry
            ACCESS  not-accessible
            STATUS  mandatory
            DESCRIPTION
                ""
            ::= { gdsl4-card 6 }

        gdsl4IntvPerfEntry  OBJECT-TYPE
            SYNTAX  Gdsl4IntvPerfEntry
            ACCESS  not-accessible
            STATUS  mandatory
            DESCRIPTION
                " "
            INDEX { gdsl4IPSlotIndex ,
                    gdsl4IPPortIndex ,
                    gdsl4IntvPerfTypeIndex ,
                    gdsl4IntvPerfPeriod }
            ::= { gdsl4IntvPerfTable 1 }

        Gdsl4IntvPerfEntry ::= SEQUENCE  {
            gdsl4IPSlotIndex            LSSlotID,
            gdsl4IPPortIndex            PortID,
            gdsl4IntvPerfTypeIndex      INTEGER,
            gdsl4IntvPerfPeriod         INTEGER,
            gdsl4IntvES                 INTEGER,
            gdsl4IntvSES                INTEGER,
            gdsl4IntvUAS                INTEGER,
            gdsl4IntvAvailable          INTEGER
        }

        gdsl4IPSlotIndex  OBJECT-TYPE
            SYNTAX  LSSlotID
            ACCESS  read-only
            STATUS  mandatory
            DESCRIPTION
                "Gshdsl4 slot"
            ::= { gdsl4IntvPerfEntry 1 }

        gdsl4IPPortIndex  OBJECT-TYPE
            SYNTAX  PortID
            ACCESS  read-only
            STATUS  mandatory
            DESCRIPTION
                " Port 1~4."
            ::= { gdsl4IntvPerfEntry 2 }

        gdsl4IntvPerfTypeIndex  OBJECT-TYPE
            SYNTAX  INTEGER {
                    master-loop-1(1),
                    master-loop-2(2),
                    master-ds1(3),
                    slave-loop-1(4),
                    slave-loop-2(5),
                    slave-ds1(6)
                }
            ACCESS  read-only
            STATUS  mandatory
            DESCRIPTION
                "Performance Type"
            ::= { gdsl4IntvPerfEntry 3 }

        gdsl4IntvPerfPeriod  OBJECT-TYPE
            SYNTAX  INTEGER (1..32)
            ACCESS  read-only
            STATUS  mandatory
            DESCRIPTION
                "Performance Interval Period Number"
            ::= { gdsl4IntvPerfEntry 4 }

        gdsl4IntvES  OBJECT-TYPE
            SYNTAX  INTEGER
            ACCESS  read-only
            STATUS  mandatory
            DESCRIPTION
                " ES Error Counter "
            ::= { gdsl4IntvPerfEntry 5 }

        gdsl4IntvSES  OBJECT-TYPE
            SYNTAX  INTEGER
            ACCESS  read-only
            STATUS  mandatory
            DESCRIPTION
                " SES Error Counter "
            ::= { gdsl4IntvPerfEntry 6 }

        gdsl4IntvUAS  OBJECT-TYPE
            SYNTAX  INTEGER
            ACCESS  read-only
            STATUS  mandatory
            DESCRIPTION
                " UAS Error Counter "
            ::= { gdsl4IntvPerfEntry 7 }

        gdsl4IntvAvailable  OBJECT-TYPE
            SYNTAX  INTEGER   {
                    available(1),
                    na(2)
                }
            ACCESS  read-only
            STATUS  mandatory
            DESCRIPTION
                " Interval Available "
            ::= { gdsl4IntvPerfEntry 8 }


--
-- GDSL4 FRACTIONAL TABLE
--

        gdsl4FracTable   OBJECT-TYPE
            SYNTAX  SEQUENCE OF Gdsl4FracEntry
            ACCESS  not-accessible
            STATUS  mandatory
            DESCRIPTION
                " Key: gdsl4FracUnitIndex.gdsl4FracNumber"
            ::= { gdsl4-card 7 }

        gdsl4FracEntry   OBJECT-TYPE
            SYNTAX  Gdsl4FracEntry
            ACCESS  not-accessible
            STATUS  mandatory
            DESCRIPTION
                " "
            INDEX { gdsl4FracSlotIndex ,
                    gdsl4FracPortIndex ,
                    gdsl4FracNumber }
            ::= { gdsl4FracTable 1 }

        Gdsl4FracEntry ::= SEQUENCE {
            gdsl4FracSlotIndex          LSSlotID,
            gdsl4FracPortIndex          PortID,
            gdsl4FracNumber             INTEGER  (1..32),
            gdsl4FracIfIndex            INTEGER
        }

        gdsl4FracSlotIndex  OBJECT-TYPE
            SYNTAX  LSSlotID
            ACCESS  read-only
            STATUS  mandatory
            DESCRIPTION
                "Gshdsl4 slot"
            ::= { gdsl4FracEntry 1 }

        gdsl4FracPortIndex  OBJECT-TYPE
            SYNTAX  PortID
            ACCESS  read-only
            STATUS  mandatory
            DESCRIPTION
                " Port 1~4."
            ::= { gdsl4FracEntry 2 }

        gdsl4FracNumber   OBJECT-TYPE
            SYNTAX  INTEGER (1..32)
            ACCESS  read-only
            STATUS  mandatory
            DESCRIPTION
                "gdsl4FracNumber "
            ::= { gdsl4FracEntry 3 }

        gdsl4FracIfIndex  OBJECT-TYPE
            SYNTAX  INTEGER {
                    chan-idle(1),
                    chan-ds1(2),
                    chan-dte(3),
                    chan-x(4)
                }
            ACCESS  read-only
            STATUS  mandatory
            DESCRIPTION
                "gdsl4FracIfIndex "
            ::= { gdsl4FracEntry 4 }

--
-- Diagnostic Control Table
--

        gdsl4DiagTable  OBJECT-TYPE
            SYNTAX  SEQUENCE OF Gdsl4DiagEntry
            ACCESS  not-accessible
            STATUS  mandatory
            DESCRIPTION
                ""
            ::= { gdsl4-card 8 }

        gdsl4DiagEntry  OBJECT-TYPE
            SYNTAX  Gdsl4DiagEntry
            ACCESS  not-accessible
            STATUS  mandatory
            DESCRIPTION
                ""
            INDEX { gdsl4DiagSlotIndex ,
                    gdsl4DiagPortIndex }
            ::= { gdsl4DiagTable 1 }

        Gdsl4DiagEntry ::= SEQUENCE {
            gdsl4DiagSlotIndex          LSSlotID,
            gdsl4DiagPortIndex          PortID,
            gdsl4LocalGshdslLoopback    INTEGER,
            gdsl4RemoteGshdslLoopback   INTEGER,
            gdsl4RemoteDteLoopback      INTEGER,
            gdsl4BERTControl            INTEGER,
            gdsl4BERTReset              INTEGER,
            gdsl4BERTStatus             INTEGER,
            gdsl4BERTCounter            INTEGER,
            gdsl4BERTElapsed            INTEGER,
            gdsl4InbandLoopbackPeriod   INTEGER
        }

        gdsl4DiagSlotIndex  OBJECT-TYPE
            SYNTAX  LSSlotID
            ACCESS  read-only
            STATUS  mandatory
            DESCRIPTION
                "Gshdsl4 slot"
            ::= { gdsl4DiagEntry 1 }

        gdsl4DiagPortIndex  OBJECT-TYPE
            SYNTAX  PortID
            ACCESS  read-only
            STATUS  mandatory
            DESCRIPTION
                " Port 1~4."
            ::= { gdsl4DiagEntry 2 }

        gdsl4LocalGshdslLoopback  OBJECT-TYPE
            SYNTAX  INTEGER {
                    no-loopback(1),
                    gshdsl-to-line(2),
                    gshdsl-to-local(3)
                }
            ACCESS  read-write
            STATUS  mandatory
            DESCRIPTION
                "CSU Loopback Type"
            ::= { gdsl4DiagEntry 3 }

        gdsl4RemoteGshdslLoopback  OBJECT-TYPE
            SYNTAX  INTEGER {
                    slave-no-loopback(1),
                    slave-gshdsl-to-line(2),
                    slave-gshdsl-to-local(3),
                    slave-gshdsl-to-bridge(4),

                    slave-gshdsl-to-dte1(82),
                    slave-gshdsl-to-dte2(83),
                    slave-gshdsl-to-dte3(84)
                }
            ACCESS  read-write
            STATUS  mandatory
            DESCRIPTION
                "CSU Loopback Type"
            ::= { gdsl4DiagEntry 4 }

        gdsl4RemoteDteLoopback  OBJECT-TYPE
            SYNTAX  INTEGER {
                    slave-no-loopback(1),
                    slave-t1-to-line(2),
                    slave-t1-to-local(3),
                    slave-e1-to-line(4),
                    slave-e1-to-local(5),
                    slave-dte-to-line(6),
                    slave-dte-to-local(7),
                    slave-router-to-line(8),
                    other(99)
                }
            ACCESS  read-write
            STATUS  mandatory
            DESCRIPTION
                "DTE/T1/E1 Loopback Type"
            ::= { gdsl4DiagEntry 5 }

        gdsl4BERTControl    OBJECT-TYPE
            SYNTAX  INTEGER {
                    bert-off(1),
--                      bert-2-15-1(2),
                    bert-on(3)
                }
            ACCESS  read-write
            STATUS  mandatory
            DESCRIPTION
                "Bert Control"
            ::= { gdsl4DiagEntry 6 }

        gdsl4BERTReset    OBJECT-TYPE
            SYNTAX  INTEGER {
                    bert-no-action(1),
                    bert-restart(2)
                }
            ACCESS  read-write
            STATUS  mandatory
            DESCRIPTION
                "Bert Restart"
            ::= { gdsl4DiagEntry 7 }

        gdsl4BERTStatus  OBJECT-TYPE
            SYNTAX  INTEGER {
                    bert-sync(1),
                    bert-unsync(2),
                    bert-not-active(3)
                }
            ACCESS  read-only
            STATUS  mandatory
            DESCRIPTION
                "BERT Status"
            ::= { gdsl4DiagEntry 8 }

        gdsl4BERTCounter  OBJECT-TYPE
            SYNTAX  INTEGER
            ACCESS  read-only
            STATUS  mandatory
            DESCRIPTION
                "BERT Counter"
            ::= { gdsl4DiagEntry 9 }

        gdsl4BERTElapsed  OBJECT-TYPE
            SYNTAX  INTEGER
            ACCESS  read-only
            STATUS  mandatory
            DESCRIPTION
                "BERT Elapsed Time"
            ::= { gdsl4DiagEntry 10 }

        gdsl4InbandLoopbackPeriod  OBJECT-TYPE
            SYNTAX  INTEGER
            ACCESS  read-write
            STATUS  mandatory
            DESCRIPTION
                "period(in seconds) of loopback"
            ::= { gdsl4DiagEntry 11 }



--
--  Alarm Queue Table
--

--         gdsl4AlmQueueTable  OBJECT-TYPE
--             SYNTAX  SEQUENCE OF Gdsl4AlmQueueEntry
--             ACCESS  not-accessible
--             STATUS  mandatory
--             DESCRIPTION
--                " Key: gdsl4AlmQueueUnitIndex "
--             ::= { gdsl4-card 9 }
--
--         gdsl4AlmQueueEntry  OBJECT-TYPE
--             SYNTAX  Gdsl4AlmQueueEntry
--             ACCESS  not-accessible
--             STATUS  mandatory
--             DESCRIPTION
--                " "
--             INDEX  { gdsl4Index,
--                      gdsl4PortIndex,
--                      gdsl4AlmQueueNumber }
--             ::= { gdsl4AlmQueueTable 1 }
--
--         Gdsl4AlmQueueEntry ::=
--             SEQUENCE {
--               gdsl4AlmQueueNumber
--                 INTEGER (1..40),
--               gdsl4AlmQueueString
--                 DisplayString (SIZE(0..80))
--             }
--
--         gdsl4AlmQueueNumber  OBJECT-TYPE
--             SYNTAX  INTEGER (1..40)
--             ACCESS  read-only
--             STATUS  mandatory
--             DESCRIPTION
--                "Select Latest Alarm Queue number (1-40)"
--             ::= { gdsl4AlmQueueEntry 2 }
--
--         gdsl4AlmQueueString  OBJECT-TYPE
--             SYNTAX  DisplayString (SIZE (0..80))
--             ACCESS  read-only
--             STATUS  mandatory
--             DESCRIPTION
--                "Alarm Queue String"
--             ::= { gdsl4AlmQueueEntry 3 }

--
--  Alarm Status Table
--

        gdsl4AlmStatusTable  OBJECT-TYPE
            SYNTAX  SEQUENCE OF Gdsl4AlmStatusEntry
            ACCESS  not-accessible
            STATUS  mandatory
            DESCRIPTION
                " Key: xdslAlmStatusUnitIndex "
            ::= { gdsl4-card 10 }

        gdsl4AlmStatusEntry  OBJECT-TYPE
            SYNTAX  Gdsl4AlmStatusEntry
            ACCESS  not-accessible
            STATUS  mandatory
            DESCRIPTION
                " "
            INDEX { gdsl4AlmSlotIndex ,
                    gdsl4AlmPortIndex ,
                    gdsl4AlmStatusNumber }
            ::= { gdsl4AlmStatusTable 1 }

        Gdsl4AlmStatusEntry ::= SEQUENCE {
            gdsl4AlmSlotIndex           LSSlotID,
            gdsl4AlmPortIndex           PortID,
            gdsl4AlmStatusNumber        INTEGER (1..40),
            gdsl4AlmStatusString        DisplayString,
            gdsl4AlmStatusThreshold     INTEGER,
            gdsl4AlmStatusState         INTEGER,
            gdsl4AlmStatusCount         INTEGER,
            gdsl4AlmStatusEnable        LsAlarmSeverity
        }

        gdsl4AlmSlotIndex  OBJECT-TYPE
            SYNTAX  LSSlotID
            ACCESS  read-only
            STATUS  mandatory
            DESCRIPTION
                "Gshdsl4 slot"
            ::= { gdsl4AlmStatusEntry 1 }

        gdsl4AlmPortIndex  OBJECT-TYPE
            SYNTAX  PortID
            ACCESS  read-only
            STATUS  mandatory
            DESCRIPTION
                " Port 1~4."
            ::= { gdsl4AlmStatusEntry 2 }

        gdsl4AlmStatusNumber  OBJECT-TYPE
            SYNTAX  INTEGER (1..40)
            ACCESS  read-only
            STATUS  mandatory
            DESCRIPTION
                " Alarm Status Index "
            ::= { gdsl4AlmStatusEntry 3 }

        gdsl4AlmStatusString  OBJECT-TYPE
            SYNTAX  DisplayString (SIZE (0..80))
            ACCESS  read-only
            STATUS  mandatory
            DESCRIPTION
                "Alarm Type String"
            ::= { gdsl4AlmStatusEntry 4 }

        gdsl4AlmStatusThreshold  OBJECT-TYPE
            SYNTAX  INTEGER
            ACCESS  read-write
            STATUS  mandatory
            DESCRIPTION
                " Alarm Threshold Value "
            ::= { gdsl4AlmStatusEntry 5 }

        gdsl4AlmStatusState  OBJECT-TYPE
            SYNTAX  INTEGER {
                    ok(1),
                    alarm(2),
                    disable(3),
                    none(4)
                }
            ACCESS  read-only
            STATUS  mandatory
            DESCRIPTION
                " Alarm Current State"
            ::= { gdsl4AlmStatusEntry 6 }

        gdsl4AlmStatusCount  OBJECT-TYPE
            SYNTAX  INTEGER
            ACCESS  read-only
            STATUS  mandatory
            DESCRIPTION
                " Alarm Count which happened "
            ::= { gdsl4AlmStatusEntry 7 }

        gdsl4AlmStatusEnable  OBJECT-TYPE
            SYNTAX  LsAlarmSeverity
            ACCESS  read-write
            STATUS  mandatory
            DESCRIPTION
                "Alarm is enabled or not"
            ::= { gdsl4AlmStatusEntry 8 }

--
--  Gdsl4 Status Config Table
--

        gdsl4StatusConfigTable  OBJECT-TYPE
            SYNTAX  SEQUENCE OF Gdsl4StatusConfigTableEntry
            ACCESS  not-accessible
            STATUS  mandatory
            DESCRIPTION
                " Gdsl Status Config Configuration "
            ::= { gdsl4-card 11 }

        gdsl4StatusConfigEntry  OBJECT-TYPE
            SYNTAX  Gdsl4StatusConfigTableEntry
            ACCESS  not-accessible
            STATUS  mandatory
            DESCRIPTION
                " "
            INDEX { gdsl4SCSlotIndex ,
                    gdsl4SCPortIndex }
            ::= { gdsl4StatusConfigTable 1 }

        Gdsl4StatusConfigTableEntry ::= SEQUENCE {
            gdsl4SCSlotIndex            LSSlotID,
            gdsl4SCPortIndex            PortID,
            gdsl4DS1SYNC                INTEGER,
            gdsl4DS1TxAIS               INTEGER,
            gdsl4DS1TxRAI               INTEGER,
            gdsl4DS1RxAIS               INTEGER,
            gdsl4DS1RxRAI               INTEGER,
            gdsl4DS1LOS                 INTEGER,
            gdsl4DS1LOF                 INTEGER,
            gdsl4dteDSR                 INTEGER,
            gdsl4dteCTS                 INTEGER,
            gdsl4dteDCD                 INTEGER,
            gdsl4dteDTR                 INTEGER,
            gdsl4dteRTS                 INTEGER,
            gdsl4PortCAS                INTEGER,
            gdsl4LAN1Status             INTEGER,
            gdsl4WAN1Status             INTEGER
        }

        gdsl4SCSlotIndex  OBJECT-TYPE
            SYNTAX  LSSlotID
            ACCESS  read-only
            STATUS  mandatory
            DESCRIPTION
                "Gshdsl4 slot"
            ::= { gdsl4StatusConfigEntry 1 }

        gdsl4SCPortIndex  OBJECT-TYPE
            SYNTAX  PortID
            ACCESS  read-only
            STATUS  mandatory
            DESCRIPTION
                " Port 1~4."
            ::= { gdsl4StatusConfigEntry 2 }

        gdsl4DS1SYNC  OBJECT-TYPE
            SYNTAX  INTEGER {
                    yes(1),
                    no(2),
                    xx(3)
                }
            ACCESS  read-only
            STATUS  mandatory
            DESCRIPTION
                " Gshdsl DS1 line status."
            ::= { gdsl4StatusConfigEntry 3 }

        gdsl4DS1TxAIS  OBJECT-TYPE
            SYNTAX  INTEGER {
                    yes(1),
                    no(2),
                    xx(3)
                }
            ACCESS  read-only
            STATUS  mandatory
            DESCRIPTION
                "Gshdsl DS1 line Tx Alarm Indication Signal."
            ::= { gdsl4StatusConfigEntry 4 }

        gdsl4DS1TxRAI  OBJECT-TYPE
            SYNTAX  INTEGER {
                    yes(1),
                    no(2),
                    xx(3)
                }
            ACCESS  read-only
            STATUS  mandatory
            DESCRIPTION
                " Gshdsl DS1 line Tx Remote Alarm Indication."
            ::= { gdsl4StatusConfigEntry 5 }

        gdsl4DS1RxAIS  OBJECT-TYPE
            SYNTAX  INTEGER {
                    yes(1),
                    no(2),
                    xx(3)
                }
            ACCESS  read-only
            STATUS  mandatory
            DESCRIPTION
                " Gshdsl DS1 line Rx Alarm Indication Signal."
            ::= { gdsl4StatusConfigEntry 6 }

        gdsl4DS1RxRAI  OBJECT-TYPE
            SYNTAX  INTEGER {
                    yes(1),
                    no(2),
                    xx(3)
                }
            ACCESS  read-only
            STATUS  mandatory
            DESCRIPTION
                " Gshdsl DS1 line Rx Remote Alarm Indication."
            ::= { gdsl4StatusConfigEntry 7 }

        gdsl4DS1LOS  OBJECT-TYPE
            SYNTAX  INTEGER {
                    yes(1),
                    no(2),
                    xx(3)
                }
            ACCESS  read-only
            STATUS  mandatory
            DESCRIPTION
                " Gshdsl DS1 line LOS Status."
            ::= { gdsl4StatusConfigEntry 8 }

        gdsl4DS1LOF  OBJECT-TYPE
            SYNTAX  INTEGER {
                    yes(1),
                    no(2),
                    xx(3)
                }
            ACCESS  read-only
            STATUS  mandatory
            DESCRIPTION
                " Gshdsl DS1 line LOF Status."
            ::= { gdsl4StatusConfigEntry 9 }

        gdsl4dteDSR  OBJECT-TYPE
            SYNTAX  INTEGER {
                    yes(1),
                    no(2),
                    xx(3)
                }
            ACCESS  read-only
            STATUS  mandatory
            DESCRIPTION
                " Gshdsl dte line DSR Status."
            ::= { gdsl4StatusConfigEntry 10 }

        gdsl4dteCTS  OBJECT-TYPE
            SYNTAX  INTEGER {
                    yes(1),
                    no(2),
                    xx(3)
                }
            ACCESS  read-only
            STATUS  mandatory
            DESCRIPTION
                " Gshdsl dte line CTS Status."
            ::= { gdsl4StatusConfigEntry 11 }

        gdsl4dteDCD  OBJECT-TYPE
            SYNTAX  INTEGER {
                    yes(1),
                    no(2),
                    xx(3)
                }
            ACCESS  read-only
            STATUS  mandatory
            DESCRIPTION
                " Gshdsl dte line DCD Status."
            ::= { gdsl4StatusConfigEntry 12 }

        gdsl4dteDTR  OBJECT-TYPE
            SYNTAX  INTEGER {
                    yes(1),
                    no(2),
                    xx(3)
                }
            ACCESS  read-only
            STATUS  mandatory
            DESCRIPTION
                " Gshdsl dte line DTR Status."
            ::= { gdsl4StatusConfigEntry 13 }

        gdsl4dteRTS  OBJECT-TYPE
            SYNTAX  INTEGER {
                    yes(1),
                    no(2),
                    xx(3)
                }
            ACCESS  read-only
            STATUS  mandatory
            DESCRIPTION
                " Gshdsl dte line RTS Status."
            ::= { gdsl4StatusConfigEntry 14 }

        gdsl4PortCAS  OBJECT-TYPE
            SYNTAX  INTEGER {
                    loss(1),
                    sync(2),
                    disable(3)
                }
            ACCESS  read-only
            STATUS  mandatory
            DESCRIPTION
                " Gshdsl CAS Status."
            ::= { gdsl4StatusConfigEntry 15 }

        gdsl4LAN1Status  OBJECT-TYPE
            SYNTAX  INTEGER {
                    down(1),
                    up(2),
                    na(3)
                }
            ACCESS  read-only
            STATUS  mandatory
            DESCRIPTION
                " LAN1 Status."
            ::= { gdsl4StatusConfigEntry 16 }

        gdsl4WAN1Status  OBJECT-TYPE
            SYNTAX  INTEGER {
                    down(1),
                    up(2),
                    na(3)
                }
            ACCESS  read-only
            STATUS  mandatory
            DESCRIPTION
                " WAN1 Status."
            ::= { gdsl4StatusConfigEntry 17 }

--
--  GDSL4 Info Table
--

        gdsl4InfoTable  OBJECT-TYPE
            SYNTAX  SEQUENCE OF Gdsl4InfoEntry
            ACCESS  not-accessible
            STATUS  mandatory
            DESCRIPTION
                " Key: gdsl4InfoUnitIndex "
            ::= { gdsl4-card 12 }

        gdsl4InfoEntry  OBJECT-TYPE
            SYNTAX  Gdsl4InfoEntry
            ACCESS  not-accessible
            STATUS  mandatory
            DESCRIPTION
                " "
            INDEX { gdsl4InfoSlotIndex ,
                    gdsl4InfoPortIndex }
            ::= { gdsl4InfoTable 1 }

        Gdsl4InfoEntry ::= SEQUENCE {
            gdsl4InfoSlotIndex          LSSlotID,
            gdsl4InfoPortIndex          PortID,
            gdsl4MasterNoiseMarginString    DisplayString (SIZE(0..80)),
            gdsl4MasterMaxNMRString         DisplayString (SIZE(0..80)),
            gdsl4MasterMinNMRString         DisplayString (SIZE(0..80)),
            gdsl4SlaveNoiseMarginString     DisplayString (SIZE(0..80)),
            gdsl4SlaveMaxNMRString          DisplayString (SIZE(0..80)),
            gdsl4SlaveMinNMRString          DisplayString (SIZE(0..80))
        }

        gdsl4InfoSlotIndex  OBJECT-TYPE
            SYNTAX  LSSlotID
            ACCESS  read-only
            STATUS  mandatory
            DESCRIPTION
                "Gshdsl4 slot"
            ::= { gdsl4InfoEntry 1 }

        gdsl4InfoPortIndex  OBJECT-TYPE
            SYNTAX  PortID
            ACCESS  read-only
            STATUS  mandatory
            DESCRIPTION
                " Port 1~4."
            ::= { gdsl4InfoEntry 2 }

        gdsl4MasterNoiseMarginString  OBJECT-TYPE
            SYNTAX  DisplayString (SIZE (0..80))
            ACCESS  read-only
            STATUS  mandatory
            DESCRIPTION
                "Noise Margin String"
            ::= { gdsl4InfoEntry 3 }

        gdsl4MasterMaxNMRString  OBJECT-TYPE
            SYNTAX  DisplayString (SIZE (0..80))
            ACCESS  read-only
            STATUS  mandatory
            DESCRIPTION
                "Max Noise Margin String"
            ::= { gdsl4InfoEntry 4 }

        gdsl4MasterMinNMRString  OBJECT-TYPE
            SYNTAX  DisplayString (SIZE (0..80))
            ACCESS  read-only
            STATUS  mandatory
            DESCRIPTION
                "Min Margin String"
            ::= { gdsl4InfoEntry 5 }

        gdsl4SlaveNoiseMarginString  OBJECT-TYPE
            SYNTAX  DisplayString (SIZE (0..80))
            ACCESS  read-only
            STATUS  mandatory
            DESCRIPTION
                "Noise Margin String"
            ::= { gdsl4InfoEntry 6 }

        gdsl4SlaveMaxNMRString  OBJECT-TYPE
            SYNTAX  DisplayString (SIZE (0..80))
            ACCESS  read-only
            STATUS  mandatory
            DESCRIPTION
                "Max Noise Margin String"
            ::= { gdsl4InfoEntry 7 }

        gdsl4SlaveMinNMRString  OBJECT-TYPE
            SYNTAX  DisplayString (SIZE (0..80))
            ACCESS  read-only
            STATUS  mandatory
            DESCRIPTION
                "Min Margin String"
            ::= { gdsl4InfoEntry 8 }

--
--  Command Control Table
--

        gdsl4CommandControlTable  OBJECT-TYPE
            SYNTAX  SEQUENCE OF Gdsl4CommandControlEntry
            ACCESS  not-accessible
            STATUS  mandatory
            DESCRIPTION
                "The command control table."
            ::= { gdsl4-card 13 }

        gdsl4CommandControlEntry  OBJECT-TYPE
            SYNTAX  Gdsl4CommandControlEntry
            ACCESS  not-accessible
            STATUS  mandatory
            DESCRIPTION
                "An entry in the command control table."
            INDEX { gdsl4CCSlotIndex ,
                    gdsl4CCPortIndex }
            ::= { gdsl4CommandControlTable 1 }

        Gdsl4CommandControlEntry ::= SEQUENCE {
            gdsl4CCSlotIndex            LSSlotID,
            gdsl4CCPortIndex            PortID,
            gdsl4ClearPerformance       INTEGER,
--               gdsl4ClearAlarmHistory
--                 INTEGER,
            gdsl4UnitReset              INTEGER,
            gdsl4UnitLoadDefault        INTEGER,
            gdsl4FarEndReset            INTEGER
        }

        gdsl4CCSlotIndex  OBJECT-TYPE
            SYNTAX  LSSlotID
            ACCESS  read-only
            STATUS  mandatory
            DESCRIPTION
                "Gshdsl4 slot"
            ::= { gdsl4CommandControlEntry 1 }

        gdsl4CCPortIndex  OBJECT-TYPE
            SYNTAX  PortID
            ACCESS  read-only
            STATUS  mandatory
            DESCRIPTION
                " Port 1~4."
            ::= { gdsl4CommandControlEntry 2 }

        gdsl4ClearPerformance    OBJECT-TYPE
            SYNTAX  INTEGER {
                    clear(1)
                }
            ACCESS  read-write
            STATUS  mandatory
            DESCRIPTION
                "Command: Clear User Performance"
            ::= { gdsl4CommandControlEntry 4 }

--         gdsl4ClearAlarmHistory    OBJECT-TYPE
--             SYNTAX  INTEGER {
--                         clear(1)
--                     }
--             ACCESS  read-write
--             STATUS  mandatory
--             DESCRIPTION
--                "Command: Clear Alarm History"
--             ::= { gdsl4CommandControlEntry 5 }

        gdsl4UnitReset    OBJECT-TYPE
            SYNTAX  INTEGER {
                    reset(1)
                }
            ACCESS  read-write
            STATUS  mandatory
            DESCRIPTION
                "Command: Reset G.SHDSL-4"
            ::= { gdsl4CommandControlEntry 6 }

        gdsl4UnitLoadDefault    OBJECT-TYPE
            SYNTAX  INTEGER {
                    load-default(1)
                }
            ACCESS  read-write
            STATUS  mandatory
            DESCRIPTION
                "Command: Load Default G.SHDSL-4"
            ::= { gdsl4CommandControlEntry 7 }

        gdsl4FarEndReset    OBJECT-TYPE
            SYNTAX  INTEGER {
                    reset(1)
                }
            ACCESS  read-write
            STATUS  mandatory
            DESCRIPTION
                "Command: Reset Far End System"
            ::= { gdsl4CommandControlEntry 8 }

--
--  SYSTEM Information Table
--

        gdsl4SystemInfoTable  OBJECT-TYPE
            SYNTAX  SEQUENCE OF Gdsl4SystemInformationEntry
            ACCESS  not-accessible
            STATUS  mandatory
            DESCRIPTION
                "The system information table."
            ::= { gdsl4-card 14 }

        gdsl4SystemInformationEntry  OBJECT-TYPE
            SYNTAX  Gdsl4SystemInformationEntry
            ACCESS  not-accessible
            STATUS  mandatory
            DESCRIPTION
                "An entry in the system information table."
            INDEX { gdsl4SISlotIndex }
            ::= { gdsl4SystemInfoTable 1 }

        Gdsl4SystemInformationEntry ::= SEQUENCE {
            gdsl4SISlotIndex            LSSlotID,
            gdsl4SoftwareVersion        DisplayString,
            gdsl4HardwareVersion        DisplayString
        }

        gdsl4SISlotIndex  OBJECT-TYPE
            SYNTAX  LSSlotID
            ACCESS  read-only
            STATUS  mandatory
            DESCRIPTION
                "Gshdsl4 slot"
            ::= { gdsl4SystemInformationEntry 1 }

        gdsl4SoftwareVersion  OBJECT-TYPE
            SYNTAX  DisplayString (SIZE (0..255) )
            ACCESS  read-only
            STATUS  mandatory
            DESCRIPTION
                " G.SHDSL-4 Software Version"
            ::= { gdsl4SystemInformationEntry 2 }

        gdsl4HardwareVersion  OBJECT-TYPE
            SYNTAX  DisplayString (SIZE (0..255) )
            ACCESS  read-only
            STATUS  mandatory
            DESCRIPTION
                " G.SHDSL-4 Hardware Version"
            ::= { gdsl4SystemInformationEntry 3 }


--
--  G.SHDSL-4 Customer Information Table
--

        gdsl4CustomerInfoTable  OBJECT-TYPE
            SYNTAX  SEQUENCE OF Gdsl4CustomerInfoEntry
            ACCESS  not-accessible
            STATUS  mandatory
            DESCRIPTION
                "The Customer Information table."
            ::= { gdsl4-card 99 }

        gdsl4CustomerInfoEntry  OBJECT-TYPE
            SYNTAX  Gdsl4CustomerInfoEntry
            ACCESS  not-accessible
            STATUS  mandatory
            DESCRIPTION
                "An entry in the Customer Information table."
            INDEX { gdsl4CISlotIndex , gdsl4CIPortIndex }
            ::= { gdsl4CustomerInfoTable 1 }

        Gdsl4CustomerInfoEntry ::= SEQUENCE {
            gdsl4CISlotIndex            LSSlotID,
            gdsl4CIPortIndex            PortID,
            gdsl4CICustomerInfo         DisplayString (SIZE(0..64))
        }

        gdsl4CISlotIndex    OBJECT-TYPE
            SYNTAX  LSSlotID
            ACCESS  read-only
            STATUS  mandatory
            DESCRIPTION
                "LS slot index"
            ::= { gdsl4CustomerInfoEntry 1 }

        gdsl4CIPortIndex    OBJECT-TYPE
            SYNTAX  PortID
            ACCESS  read-only
            STATUS  mandatory
            DESCRIPTION
                "Port number"
            ::= { gdsl4CustomerInfoEntry 2 }

        gdsl4CICustomerInfo  OBJECT-TYPE
            SYNTAX  DisplayString (SIZE (0..64) )
            ACCESS  read-write
            STATUS  mandatory
            DESCRIPTION
                "Customer information"
            ::= { gdsl4CustomerInfoEntry 3 }


--
--  Daughter Card Information Table
--

        gdsl4DCardInfoTable  OBJECT-TYPE
            SYNTAX  SEQUENCE OF Gdsl4DCardInfoEntry
            ACCESS  not-accessible
            STATUS  mandatory
            DESCRIPTION
                "The Daughter Card Information table."
            ::= { gdsl4-card 15 }

        gdsl4DCardInfoEntry  OBJECT-TYPE
            SYNTAX  Gdsl4DCardInfoEntry
            ACCESS  not-accessible
            STATUS  mandatory
            DESCRIPTION
                "An entry in the daughter card information table."
            INDEX { gdsl4DCISlotIndex ,
                    gdsl4DCIPortIndex }
            ::= { gdsl4DCardInfoTable 1 }

        Gdsl4DCardInfoEntry ::= SEQUENCE {
            gdsl4DCISlotIndex           LSSlotID,
            gdsl4DCIPortIndex           PortID,
            gdsl4DaughterCard           INTEGER
        }

        gdsl4DCISlotIndex  OBJECT-TYPE
            SYNTAX  LSSlotID
            ACCESS  read-only
            STATUS  mandatory
            DESCRIPTION
                "Gshdsl4 slot"
            ::= { gdsl4DCardInfoEntry 1 }

        gdsl4DCIPortIndex  OBJECT-TYPE
            SYNTAX  PortID
            ACCESS  read-only
            STATUS  mandatory
            DESCRIPTION
                " Port 1~4."
            ::= { gdsl4DCardInfoEntry 2 }

        gdsl4DaughterCard  OBJECT-TYPE
            SYNTAX  INTEGER {
                    no-daughter-card(1),
                    sealing-current-single(2),
                    sealing-current-daul(3),
                    line-power-single(4),
                    line-power-daul(5)
                }
            ACCESS  read-only
            STATUS  mandatory
            DESCRIPTION
                " G.SHDSL-4 Daughter Card "
            ::= { gdsl4DCardInfoEntry 3 }

--
--  GDSL4 ADVANCE SYSTEM Table
--

        gdsl4AdvanceSystemTable  OBJECT-TYPE
            SYNTAX  SEQUENCE OF Gdsl4AdvanceSystemEntry
            ACCESS  not-accessible
            STATUS  mandatory
            DESCRIPTION
                "The system control table."
            ::= { gdsl4-card 16 }

        gdsl4AdvanceSystemEntry  OBJECT-TYPE
            SYNTAX  Gdsl4AdvanceSystemEntry
            ACCESS  not-accessible
            STATUS  mandatory
            DESCRIPTION
                "An entry in the Advance system table."
            INDEX { gdsl4AdvSlotIndex ,
                    gdsl4AdvPortIndex ,
                    gdsl4AdvHTUIndex }
            ::= { gdsl4AdvanceSystemTable 1 }

        Gdsl4AdvanceSystemEntry ::= SEQUENCE {
            gdsl4AdvSlotIndex           LSSlotID,
            gdsl4AdvPortIndex           PortID,
            gdsl4AdvHTUIndex            INTEGER,
            gdsl4AnnexType              INTEGER,
            gdsl4ClockMode              INTEGER,
            gdsl4PSDMask                INTEGER,
            gdsl4PBOMode                INTEGER
        }

        gdsl4AdvSlotIndex  OBJECT-TYPE
            SYNTAX  LSSlotID
            ACCESS  read-only
            STATUS  mandatory
            DESCRIPTION
                "Gshdsl4 slot"
            ::= { gdsl4AdvanceSystemEntry 1 }

        gdsl4AdvPortIndex  OBJECT-TYPE
            SYNTAX  PortID
            ACCESS  read-only
            STATUS  mandatory
            DESCRIPTION
                " Port 1~4."
            ::= { gdsl4AdvanceSystemEntry 2 }

        gdsl4AdvHTUIndex   OBJECT-TYPE
            SYNTAX  INTEGER {
                    local(1),
                    remote(2)
                }
            ACCESS  read-only
            STATUS  mandatory
            DESCRIPTION
                "Local or Remote"
            ::= { gdsl4AdvanceSystemEntry 3 }

        gdsl4AnnexType  OBJECT-TYPE
            SYNTAX  INTEGER {
                    type-A(1),
                    type-B(2),
                    not-support(3)
                }
            ACCESS  read-write
            STATUS  mandatory
            DESCRIPTION
                "G.SHDSL Annex Type"
            ::= { gdsl4AdvanceSystemEntry 4 }

        gdsl4ClockMode  OBJECT-TYPE
            SYNTAX  INTEGER {
                    plesiochronous(1),
                    synchronous(2),
                    hybrid(3),
                    not-support(4)
                }
            ACCESS  read-write
            STATUS  mandatory
            DESCRIPTION
                " G.SHDSL Clock Mode"
            ::= { gdsl4AdvanceSystemEntry 5 }

        gdsl4PSDMask  OBJECT-TYPE
            SYNTAX  INTEGER {
                    symmetric(1),
                    asymmetric(2),
                    not-support(3)
                }
            ACCESS  read-write
            STATUS  mandatory
            DESCRIPTION
                " G.SHDSL PSD Mask"
            ::= { gdsl4AdvanceSystemEntry 6 }

        gdsl4PBOMode  OBJECT-TYPE
            SYNTAX  INTEGER {
                    automatic(1),
                    pbo-0-db(2),
                    pbo-1-db(3),
                    pbo-2-db(4),
                    pbo-3-db(5),
                    pbo-4-db(6),
                    pbo-5-db(7),
                    pbo-6-db(8),
                    pbo-7-db(9),
                    pbo-8-db(10),
                    pbo-9-db(11),
                    pbo-10-db(12),
                    pbo-11-db(13),
                    pbo-12-db(14),
                    pbo-13-db(15),
                    pbo-14-db(16),
                    pbo-15-db(17),
                    pbo-16-db(18),
                    pbo-17-db(19),
                    pbo-18-db(20),
                    pbo-19-db(21),
                    pbo-20-db(22),
                    pbo-21-db(23),
                    pbo-22-db(24),
                    pbo-23-db(25),
                    pbo-24-db(26),
                    pbo-25-db(27),
                    pbo-26-db(28),
                    pbo-27-db(29),
                    pbo-28-db(30),
                    pbo-29-db(31),
                    pbo-30-db(32),
                    pbo-31-db(33),
                    not-support(34)
                }
            ACCESS  read-write
            STATUS  mandatory
            DESCRIPTION
                " G.SHDSL PBO Mode"
            ::= { gdsl4AdvanceSystemEntry 7 }

--
--  GDSL4 Remote Link Identification Table
--

        gdsl4RemoteLinkIDTable  OBJECT-TYPE
            SYNTAX  SEQUENCE OF Gdsl4RemoteLinkIDEntry
            ACCESS  not-accessible
            STATUS  mandatory
            DESCRIPTION
                "The G.SHDSL Remote Link Identification Table."
            ::= { gdsl4-card 17 }

        gdsl4RemoteLinkIDEntry  OBJECT-TYPE
            SYNTAX  Gdsl4RemoteLinkIDEntry
            ACCESS  not-accessible
            STATUS  mandatory
            DESCRIPTION
                "An entry in the G.SHDSL Remote Link Identification table."
            INDEX { gdsl4RLSlotIndex ,
                    gdsl4RLPortIndex }
            ::= { gdsl4RemoteLinkIDTable 1 }

        Gdsl4RemoteLinkIDEntry ::= SEQUENCE {
            gdsl4RLSlotIndex            LSSlotID,
            gdsl4RLPortIndex            PortID,
            gdsl4RemoteLinkIDType       INTEGER,
            gdsl4RemoteLinkIDRack       INTEGER,
            gdsl4RemoteLinkIDSlotNumber INTEGER,
            gdsl4RemoteLinkIDPort       INTEGER,
            gdsl4RemoteLinkIDSerialNumber   INTEGER
        }

        gdsl4RLSlotIndex  OBJECT-TYPE
            SYNTAX  LSSlotID
            ACCESS  read-only
            STATUS  mandatory
            DESCRIPTION
                "Gshdsl4 slot"
            ::= { gdsl4RemoteLinkIDEntry 1 }

        gdsl4RLPortIndex  OBJECT-TYPE
            SYNTAX  PortID
            ACCESS  read-only
            STATUS  mandatory
            DESCRIPTION
                " Port 1~4."
            ::= { gdsl4RemoteLinkIDEntry 2 }

        gdsl4RemoteLinkIDType  OBJECT-TYPE
            SYNTAX  INTEGER {
                    notAvailable(0),
                    cpe(1),
                    an(2)
                }
            ACCESS  read-only
            STATUS  mandatory
            DESCRIPTION
                "Type of remote site."
            ::= { gdsl4RemoteLinkIDEntry 3 }

        gdsl4RemoteLinkIDRack  OBJECT-TYPE
            SYNTAX  INTEGER {
                    notAvailable(0)
                }
            ACCESS  read-only
            STATUS  mandatory
            DESCRIPTION
                "Remote Link Identification Rack"
            ::= { gdsl4RemoteLinkIDEntry 4 }

        gdsl4RemoteLinkIDSlotNumber  OBJECT-TYPE
            SYNTAX  INTEGER {
                    notAvailable(0)
                }
            ACCESS  read-only
            STATUS  mandatory
            DESCRIPTION
                "Remote Link Identification SlotNumber"
            ::= { gdsl4RemoteLinkIDEntry 5 }

        gdsl4RemoteLinkIDPort  OBJECT-TYPE
            SYNTAX  INTEGER {
                    notAvailable(0)
                }
            ACCESS  read-only
            STATUS  mandatory
            DESCRIPTION
                "Remote Link Identification Port"
            ::= { gdsl4RemoteLinkIDEntry 6 }

        gdsl4RemoteLinkIDSerialNumber  OBJECT-TYPE
            SYNTAX  INTEGER {
                    notAvailable(0)
                }
            ACCESS  read-only
            STATUS  mandatory
            DESCRIPTION
                "Remote Link Identification Serial Number"
            ::= { gdsl4RemoteLinkIDEntry 7 }

--
--  Seven Days Performance Table
--
        gdsl4SevenDaysPerfTable  OBJECT-TYPE
            SYNTAX  SEQUENCE OF Gdsl4SevenDaysPerfEntry
            ACCESS  not-accessible
            STATUS  mandatory
            DESCRIPTION
                "7 Days Performance Table"
            ::= { gdsl4-card 18 }

        gdsl4SevenDaysPerfEntry  OBJECT-TYPE
            SYNTAX  Gdsl4SevenDaysPerfEntry
            ACCESS  not-accessible
            STATUS  mandatory
            DESCRIPTION
                "7 days performance entry"
            INDEX { gdsl4DPSlotIndex ,
                    gdsl4DPPortIndex ,
                    gdsl4DaysPerfTypeIndex ,
                    gdsl4DaysIndex }
            ::= { gdsl4SevenDaysPerfTable 1 }

        Gdsl4SevenDaysPerfEntry ::= SEQUENCE  {
            gdsl4DPSlotIndex            LSSlotID,
            gdsl4DPPortIndex            PortID,
            gdsl4DaysPerfTypeIndex      INTEGER,
            gdsl4DaysIndex              INTEGER (1..7),
            gdsl4DateStrIndex           DisplayString (SIZE (0..255) ),
            gdsl4SevenDaysPerfES        INTEGER,
            gdsl4SevenDaysPerfSES       INTEGER,
            gdsl4SevenDaysPerfUAS       INTEGER
        }

        gdsl4DPSlotIndex  OBJECT-TYPE
            SYNTAX  LSSlotID
            ACCESS  read-only
            STATUS  mandatory
            DESCRIPTION
                "Gshdsl4 slot"
            ::= { gdsl4SevenDaysPerfEntry 1 }

        gdsl4DPPortIndex  OBJECT-TYPE
            SYNTAX  PortID
            ACCESS  read-only
            STATUS  mandatory
            DESCRIPTION
                " Port 1~4."
            ::= { gdsl4SevenDaysPerfEntry 2 }

        gdsl4DaysPerfTypeIndex  OBJECT-TYPE
            SYNTAX  INTEGER {
                    master-loop-1(1),
                    master-loop-2(2),
                    master-ds1(3),
                    slave-loop-1(4),
                    slave-loop-2(5),
                    slave-ds1(6)
                }
            ACCESS  read-only
            STATUS  mandatory
            DESCRIPTION
                "Performance Type"
            ::= { gdsl4SevenDaysPerfEntry 3 }

        gdsl4DaysIndex  OBJECT-TYPE
            SYNTAX  INTEGER (1..7)
            ACCESS  read-only
            STATUS  mandatory
            DESCRIPTION
                "Seven Days index "
            ::= { gdsl4SevenDaysPerfEntry 4 }

        gdsl4DateStrIndex  OBJECT-TYPE
            SYNTAX  DisplayString (SIZE (0..255) )
            ACCESS  read-only
            STATUS  mandatory
            DESCRIPTION
                "Seven Days String "
            ::= { gdsl4SevenDaysPerfEntry 5 }

        gdsl4SevenDaysPerfES  OBJECT-TYPE
            SYNTAX  INTEGER
            ACCESS  read-only
            STATUS  mandatory
            DESCRIPTION
                " ES Error Counter "
            ::= { gdsl4SevenDaysPerfEntry 6 }

        gdsl4SevenDaysPerfSES  OBJECT-TYPE
            SYNTAX  INTEGER
            ACCESS  read-only
            STATUS  mandatory
            DESCRIPTION
                " SES Error Counter "
            ::= { gdsl4SevenDaysPerfEntry 7 }

        gdsl4SevenDaysPerfUAS  OBJECT-TYPE
            SYNTAX  INTEGER
            ACCESS  read-only
            STATUS  mandatory
            DESCRIPTION
                " UAS Error Counter "
            ::= { gdsl4SevenDaysPerfEntry 8 }

--
-- GDSL4 Remote Fractional TABLE
--

    gdsl4RemoteFracTable                OBJECT IDENTIFIER ::= { gdsl4-card 19 }

--
-- GDSL4 Remote Fractional Config TABLE
--

        gdsl4RemFracConfigTable   OBJECT-TYPE
            SYNTAX  SEQUENCE OF Gdsl4RemFracConfigEntry
            ACCESS  not-accessible
            STATUS  mandatory
            DESCRIPTION
                "Remote Fractional Config Table"
            ::= { gdsl4RemoteFracTable 1 }

        gdsl4RemFracConfigEntry   OBJECT-TYPE
            SYNTAX  Gdsl4RemFracConfigEntry
            ACCESS  not-accessible
            STATUS  mandatory
            DESCRIPTION
                "Remote Fractional Config Entry "
            INDEX { gdsl4RFCSlotIndex ,
                    gdsl4RFCPortIndex ,
                    gdsl4RemoteFracNumber }
            ::= { gdsl4RemFracConfigTable 1 }

        Gdsl4RemFracConfigEntry ::= SEQUENCE {
            gdsl4RFCSlotIndex           LSSlotID,
            gdsl4RFCPortIndex           PortID,
            gdsl4RemoteFracNumber       INTEGER,
            gdsl4RemoteFracIfIndex      INTEGER
        }

        gdsl4RFCSlotIndex  OBJECT-TYPE
            SYNTAX  LSSlotID
            ACCESS  read-only
            STATUS  mandatory
            DESCRIPTION
                "Gshdsl4 slot"
            ::= { gdsl4RemFracConfigEntry 1 }

        gdsl4RFCPortIndex  OBJECT-TYPE
            SYNTAX  PortID
            ACCESS  read-only
            STATUS  mandatory
            DESCRIPTION
                " Port 1~4."
            ::= { gdsl4RemFracConfigEntry 2 }

        gdsl4RemoteFracNumber   OBJECT-TYPE
            SYNTAX  INTEGER (1..32)
            ACCESS  read-only
            STATUS  mandatory
            DESCRIPTION
                "Remote Fractional Number "
            ::= { gdsl4RemFracConfigEntry 3 }

        gdsl4RemoteFracIfIndex  OBJECT-TYPE
            SYNTAX  INTEGER {
                    chan-idle(1),
                    chan-ds1(2),
                    chan-x(3),
                    chan-dte(4),
                    chan-ethernet(5)
                }
            ACCESS  read-only
            STATUS  mandatory
            DESCRIPTION
                "Remote Fractional IfIndex"
            ::= { gdsl4RemFracConfigEntry 4 }

--
-- GDSL4 Set Remote Fractional TABLE
--

        gdsl4SetRemoteFracTable   OBJECT-TYPE
            SYNTAX  SEQUENCE OF Gdsl4SetRemoteFracEntry
            ACCESS  not-accessible
            STATUS  mandatory
            DESCRIPTION
                "Set Remote Fractional Table"
            ::= { gdsl4RemoteFracTable 2 }

        gdsl4SetRemoteFracEntry   OBJECT-TYPE
            SYNTAX  Gdsl4SetRemoteFracEntry
            ACCESS  not-accessible
            STATUS  mandatory
            DESCRIPTION
                "Set Remote Fractional Entry "
            INDEX { gdsl4SRFSlotIndex ,
                    gdsl4SRFPortIndex }
            ::= { gdsl4SetRemoteFracTable 1 }

        Gdsl4SetRemoteFracEntry ::= SEQUENCE {
            gdsl4SRFSlotIndex           LSSlotID,
            gdsl4SRFPortIndex           PortID,
            gdsl4StartFracNumber        INTEGER,
            gdsl4FracNumbers            INTEGER,
            gdsl4E1T1ClearStartFracNumber   INTEGER,
            gdsl4SetFracIfIndex             INTEGER
        }

        gdsl4SRFSlotIndex  OBJECT-TYPE
            SYNTAX  LSSlotID
            ACCESS  read-only
            STATUS  mandatory
            DESCRIPTION
                "Gshdsl4 slot"
            ::= { gdsl4SetRemoteFracEntry 1 }

        gdsl4SRFPortIndex  OBJECT-TYPE
            SYNTAX  PortID
            ACCESS  read-only
            STATUS  mandatory
            DESCRIPTION
                " Port 1~4."
            ::= { gdsl4SetRemoteFracEntry 2 }

        gdsl4StartFracNumber   OBJECT-TYPE
            SYNTAX  INTEGER (1..32)
            ACCESS  read-write
            STATUS  mandatory
            DESCRIPTION
                "Start Fractional Number "
            ::= { gdsl4SetRemoteFracEntry 3 }

        gdsl4FracNumbers   OBJECT-TYPE
            SYNTAX  INTEGER (1..32)
            ACCESS  read-write
            STATUS  mandatory
            DESCRIPTION
                "Number of Fractional"
            ::= { gdsl4SetRemoteFracEntry 4 }

        gdsl4E1T1ClearStartFracNumber   OBJECT-TYPE
            SYNTAX  INTEGER (1..32)
            ACCESS  read-write
            STATUS  mandatory
            DESCRIPTION
                "Remote E1/T1 Clear Start Fractional Number"
            ::= { gdsl4SetRemoteFracEntry 5 }

        gdsl4SetFracIfIndex  OBJECT-TYPE
            SYNTAX  INTEGER {
                    chan-idle(1),
                    chan-ds1(2),
                    chan-x(3),
                    chan-dte(4),
                    chan-ethernet(5)
                }
            ACCESS  read-write
            STATUS  mandatory
            DESCRIPTION
                "Set Fractional IfIndex"
            ::= { gdsl4SetRemoteFracEntry 6 }

--
-- Remote Bert Control Table
--

        gdsl4RemoteBertTable  OBJECT-TYPE
            SYNTAX  SEQUENCE OF Gdsl4RemoteBertEntry
            ACCESS  not-accessible
            STATUS  mandatory
            DESCRIPTION
                ""
            ::= { gdsl4-card 20 }

        gdsl4RemoteBertEntry  OBJECT-TYPE
            SYNTAX  Gdsl4RemoteBertEntry
            ACCESS  not-accessible
            STATUS  mandatory
            DESCRIPTION
                ""
            INDEX { gdsl4RBSlotIndex ,
                    gdsl4RBPortIndex }
            ::= { gdsl4RemoteBertTable 1 }

        Gdsl4RemoteBertEntry ::= SEQUENCE {
            gdsl4RBSlotIndex            LSSlotID,
            gdsl4RBPortIndex            PortID,
            gdsl4RemBertPatternType     INTEGER,
            gdsl4RemBertTestChannel     INTEGER,
            gdsl4RemBertTestControl     INTEGER,
            gdsl4RemBertStatus          INTEGER,
            gdsl4RemBertErrSecond       INTEGER,
            gdsl4RemBertErrCounter      INTEGER,
            gdsl4RemBertElapsedSecond   INTEGER,
            gdsl4RemBertUnsyncSecond    INTEGER
        }

        gdsl4RBSlotIndex  OBJECT-TYPE
            SYNTAX  LSSlotID
            ACCESS  read-only
            STATUS  mandatory
            DESCRIPTION
                "Gshdsl4 slot"
            ::= { gdsl4RemoteBertEntry 1 }

        gdsl4RBPortIndex  OBJECT-TYPE
            SYNTAX  PortID
            ACCESS  read-only
            STATUS  mandatory
            DESCRIPTION
                " Port 1~4."
            ::= { gdsl4RemoteBertEntry 2 }

        gdsl4RemBertPatternType  OBJECT-TYPE
            SYNTAX  INTEGER {
                    un-support(0),
--                      off(1),
                    bert-2-15-1(2),
                    bert-qrss(3)
                }
            ACCESS  read-write
            STATUS  mandatory
            DESCRIPTION
                "BERT Pattern Type"
            ::= { gdsl4RemoteBertEntry 3 }

        gdsl4RemBertTestChannel  OBJECT-TYPE
            SYNTAX  INTEGER {
                    un-support(0),
                    full(1)
                }
            ACCESS  read-write
            STATUS  mandatory
            DESCRIPTION
                "BERT Test Channel Type"
            ::= { gdsl4RemoteBertEntry 4 }

        gdsl4RemBertTestControl  OBJECT-TYPE
            SYNTAX  INTEGER {
                    un-support(0),
                    disable(1),
                    enable(2),
                    reset(3),
                    insert-error(4)
                }
            ACCESS  read-write
            STATUS  mandatory
            DESCRIPTION
                "BERT Test Control"
            ::= { gdsl4RemoteBertEntry 5 }

        gdsl4RemBertStatus  OBJECT-TYPE
            SYNTAX  INTEGER {
                    bert-unsync(1),
                    bert-sync(2),
                    bert-not-active(3)
                }
            ACCESS  read-only
            STATUS  mandatory
            DESCRIPTION
                "Remote BERT Status"
            ::= { gdsl4RemoteBertEntry 6 }

        gdsl4RemBertErrSecond  OBJECT-TYPE
            SYNTAX  INTEGER
            ACCESS  read-only
            STATUS  mandatory
            DESCRIPTION
                "Remote BERT Error Seconds"
            ::= { gdsl4RemoteBertEntry 7 }

        gdsl4RemBertErrCounter  OBJECT-TYPE
            SYNTAX  INTEGER
            ACCESS  read-only
            STATUS  mandatory
            DESCRIPTION
                "Remote BERT Error Counter"
            ::= { gdsl4RemoteBertEntry 8 }

        gdsl4RemBertElapsedSecond  OBJECT-TYPE
            SYNTAX  INTEGER
            ACCESS  read-only
            STATUS  mandatory
            DESCRIPTION
                "Remote BERT Elapsed Time"
            ::= { gdsl4RemoteBertEntry 9 }

        gdsl4RemBertUnsyncSecond  OBJECT-TYPE
            SYNTAX  INTEGER
            ACCESS  read-only
            STATUS  mandatory
            DESCRIPTION
                "Remote BERT Unsync Time"
            ::= { gdsl4RemoteBertEntry 10 }


--
--  G.shdsl card Remote Router Table
--
    gdsl4RouterConfig     OBJECT IDENTIFIER ::= { gdsl4-card 21 }
--
--  G.shdsl card remote NI Control Table
--

        gdsl4RtrNiControlTable  OBJECT-TYPE
            SYNTAX  SEQUENCE OF Gdsl4RtrNiControlEntry
            ACCESS  not-accessible
            STATUS  mandatory
            DESCRIPTION
                "Router NI Configuration Control Table"
            ::= { gdsl4RouterConfig 1 }

        gdsl4RouterNiControlEntry  OBJECT-TYPE
            SYNTAX  Gdsl4RtrNiControlEntry
            ACCESS  not-accessible
            STATUS  mandatory
            DESCRIPTION
                "Router NI Configuration Control Entry"
            INDEX { gdsl4RtrNiUnitIndex ,
                    gdsl4RtrNiPortIndex ,
                    gdsl4RtrNiIndex }
            ::= { gdsl4RtrNiControlTable 1 }

        Gdsl4RtrNiControlEntry ::= SEQUENCE {
            gdsl4RtrNiUnitIndex         LSSlotID,
            gdsl4RtrNiPortIndex         PortID,
            gdsl4RtrNiIndex             INTEGER,
            gdsl4RtrIPAddr              IpAddress,
            gdsl4RtrSubnetMask          IpAddress,
            gdsl4RtrFrame               INTEGER,
            gdsl4RtrRIP1                INTEGER,
            gdsl4RtrRIP2                INTEGER,
            gdsl4RtrMode                INTEGER
        }

        gdsl4RtrNiUnitIndex  OBJECT-TYPE
            SYNTAX  LSSlotID
            ACCESS  read-only
            STATUS  mandatory
            DESCRIPTION
                "LS slot index"
            ::= { gdsl4RouterNiControlEntry 1 }

        gdsl4RtrNiPortIndex  OBJECT-TYPE
            SYNTAX  PortID
            ACCESS  read-only
            STATUS  mandatory
            DESCRIPTION
                "Port 1~4, total 4 ports."
            ::= { gdsl4RouterNiControlEntry 2 }

        gdsl4RtrNiIndex  OBJECT-TYPE
            SYNTAX  INTEGER {
                    lan1(1),
                    wan1(2)
                }
            ACCESS  read-only
            STATUS  mandatory
            DESCRIPTION
                " Router Ni index"
            ::= { gdsl4RouterNiControlEntry 3 }

        gdsl4RtrIPAddr   OBJECT-TYPE
            SYNTAX  IpAddress
            ACCESS  read-write
            STATUS  mandatory
            DESCRIPTION
                " RTR IP Address"
            ::= { gdsl4RouterNiControlEntry 4 }

        gdsl4RtrSubnetMask OBJECT-TYPE
            SYNTAX  IpAddress
            ACCESS  read-write
            STATUS  mandatory
            DESCRIPTION
                " RTR net mask"
            ::= { gdsl4RouterNiControlEntry 5 }

        gdsl4RtrFrame  OBJECT-TYPE
            SYNTAX  INTEGER {
                    hdlc(1),
                    ppp(2),
--                      fr(3),
                    ethernet(4),
                    na(5)
                }
            ACCESS  read-write
            STATUS  mandatory
            DESCRIPTION
                " RTR Layer2 frame"
            ::= { gdsl4RouterNiControlEntry 6 }

        gdsl4RtrRIP1 OBJECT-TYPE
            SYNTAX  INTEGER {
                    disabled(1),
                    enabled(2),
                    na(3)
                }
            ACCESS  read-write
            STATUS  mandatory
            DESCRIPTION
                " RTR RIP1"
            ::= { gdsl4RouterNiControlEntry 7 }

        gdsl4RtrRIP2  OBJECT-TYPE
            SYNTAX  INTEGER {
                    disabled(1),
                    enabled(2),
                    na(3)
                }
            ACCESS  read-write
            STATUS  mandatory
            DESCRIPTION
                " RTR RIP2"
            ::= { gdsl4RouterNiControlEntry 8 }

        gdsl4RtrMode OBJECT-TYPE
            SYNTAX  INTEGER {
                    router(1),
                    bridge(2),
                    na(3)
                }
            ACCESS  read-write
            STATUS  mandatory
            DESCRIPTION
                " RTR mode"
            ::= { gdsl4RouterNiControlEntry 9 }

--
--  G.shdsl card remote Route Table
--

        gdsl4RtrRouteCtrlTable  OBJECT-TYPE
            SYNTAX  SEQUENCE OF Gdsl4RtrRouteCtrlEntry
            ACCESS  not-accessible
            STATUS  mandatory
            DESCRIPTION
                "Router Route Control Table"
            ::= { gdsl4RouterConfig 2 }

        gdsl4RouterRouteControlEntry  OBJECT-TYPE
            SYNTAX  Gdsl4RtrRouteCtrlEntry
            ACCESS  not-accessible
            STATUS  mandatory
            DESCRIPTION
                "Router Route Control Entry"
            INDEX { gdsl4RtrRUnitIndex ,
                    gdsl4RtrRPortIndex ,
                    gdsl4RtrEntry }
            ::= { gdsl4RtrRouteCtrlTable 1 }

        Gdsl4RtrRouteCtrlEntry ::= SEQUENCE {
            gdsl4RtrRUnitIndex          LSSlotID,
            gdsl4RtrRPortIndex          PortID,
            gdsl4RtrEntry               INTEGER (1..16),
            gdsl4RtrNetAddr             IpAddress,
            gdsl4RtrNetMask             IpAddress,
            gdsl4RtrGatewayAddr         IpAddress,
            gdsl4RtrNIAddr              IpAddress,
            gdsl4RtrMetric              INTEGER
        }

        gdsl4RtrRUnitIndex  OBJECT-TYPE
            SYNTAX  LSSlotID
            ACCESS  read-only
            STATUS  mandatory
            DESCRIPTION
                "LS slot index"
            ::= { gdsl4RouterRouteControlEntry 1 }

        gdsl4RtrRPortIndex  OBJECT-TYPE
            SYNTAX  PortID
            ACCESS  read-only
            STATUS  mandatory
            DESCRIPTION
                "Port 1~4, total 4 ports."
            ::= { gdsl4RouterRouteControlEntry 2 }

        gdsl4RtrEntry  OBJECT-TYPE
            SYNTAX  INTEGER (1..16)
            ACCESS  read-only
            STATUS  mandatory
            DESCRIPTION
                " Router Route Entry"
            ::= { gdsl4RouterRouteControlEntry 3 }


        gdsl4RtrNetAddr   OBJECT-TYPE
            SYNTAX  IpAddress
            ACCESS  read-write
            STATUS  mandatory
            DESCRIPTION
                " RTR route net Address"
            ::= { gdsl4RouterRouteControlEntry 4 }

        gdsl4RtrNetMask OBJECT-TYPE
            SYNTAX  IpAddress
            ACCESS  read-write
            STATUS  mandatory
            DESCRIPTION
                " RTR route net mask"
            ::= { gdsl4RouterRouteControlEntry 5 }

        gdsl4RtrGatewayAddr  OBJECT-TYPE
            SYNTAX  IpAddress
            ACCESS  read-write
            STATUS  mandatory
            DESCRIPTION
                " RTR route gateway Address"
            ::= { gdsl4RouterRouteControlEntry 6 }

        gdsl4RtrNIAddr  OBJECT-TYPE
            SYNTAX  IpAddress
            ACCESS  read-write
            STATUS  mandatory
            DESCRIPTION
                " RTR route NI Address"
            ::= { gdsl4RouterRouteControlEntry 7 }


        gdsl4RtrMetric OBJECT-TYPE
            SYNTAX  INTEGER {
                    na(255)
                }
            ACCESS  read-write
            STATUS  mandatory
            DESCRIPTION
                " RTR Route metric"
            ::= { gdsl4RouterRouteControlEntry 8 }

--
--  G.shdsl card remote Router Command
--
        gdsl4RtrCommandTable  OBJECT-TYPE
            SYNTAX  SEQUENCE OF Gdsl4RtrCmdEntry
            ACCESS  not-accessible
            STATUS  mandatory
            DESCRIPTION
                "Router Command Table"
            ::= { gdsl4RouterConfig 3 }

        gdsl4RtrCommandEntry  OBJECT-TYPE
            SYNTAX  Gdsl4RtrCmdEntry
            ACCESS  not-accessible
            STATUS  mandatory
            DESCRIPTION
                "Router Command Entry"
            INDEX { gdsl4RtrCmdUnitIndex ,
                    gdsl4RtrCmdPortIndex }
            ::= { gdsl4RtrCommandTable 1 }

        Gdsl4RtrCmdEntry ::= SEQUENCE {
            gdsl4RtrCmdUnitIndex        LSSlotID,
            gdsl4RtrCmdPortIndex        PortID,
            gdsl4RtrCommand             INTEGER,
            gdsl4CRCtransparency        INTEGER
        }

        gdsl4RtrCmdUnitIndex  OBJECT-TYPE
            SYNTAX  LSSlotID
            ACCESS  read-only
            STATUS  mandatory
            DESCRIPTION
                "LS slot index"
            ::= { gdsl4RtrCommandEntry 1 }

        gdsl4RtrCmdPortIndex  OBJECT-TYPE
            SYNTAX  PortID
            ACCESS  read-only
            STATUS  mandatory
            DESCRIPTION
                "Port 1~4, total 4 ports."
            ::= { gdsl4RtrCommandEntry 2 }

        gdsl4RtrCommand  OBJECT-TYPE
            SYNTAX  INTEGER {
                    reset(1),
                    load-default(2),
                    none(3),
                    re-get-map-cfg(11),
                    re-get-ni-cfg(12),
                    re-get-rtr-cfg(13),
                    re-get-crc-cfg(14),
                    re-get-all-cfg(15)
                }
            ACCESS  read-write
            STATUS  mandatory
            DESCRIPTION
                " Router Command(reset or load-default)"
            ::= { gdsl4RtrCommandEntry 3 }

        gdsl4CRCtransparency OBJECT-TYPE
            SYNTAX  INTEGER {
                    off(1),
                    on(2),
                    na(3)
                }
            ACCESS  read-write
            STATUS  mandatory
            DESCRIPTION
                " CRC transparency"
            ::= { gdsl4RtrCommandEntry 4 }


--
--  G.shdsl card remote Router Map
--
        gdsl4RtrMapTable  OBJECT-TYPE
            SYNTAX  SEQUENCE OF Gdsl4RtrMappingEntry
            ACCESS  not-accessible
            STATUS  mandatory
            DESCRIPTION
                "Router Map Table"
            ::= { gdsl4RouterConfig 4 }

        gdsl4RtrMapEntry  OBJECT-TYPE
            SYNTAX  Gdsl4RtrMappingEntry
            ACCESS  not-accessible
            STATUS  mandatory
            DESCRIPTION
                "Router Map Entry"
            INDEX { gdsl4RtrMapUnitIndex ,
                    gdsl4RtrMapPortIndex ,
                    gdsl4RtrMapTsIndex }
            ::= { gdsl4RtrMapTable 1 }

        Gdsl4RtrMappingEntry ::= SEQUENCE {
            gdsl4RtrMapUnitIndex        LSSlotID,
            gdsl4RtrMapPortIndex        PortID,
            gdsl4RtrMapTsIndex          TimeslotID,
            gdsl4RtrCh                  INTEGER
        }

        gdsl4RtrMapUnitIndex  OBJECT-TYPE
            SYNTAX  LSSlotID
            ACCESS  read-only
            STATUS  mandatory
            DESCRIPTION
                "LS slot index"
            ::= { gdsl4RtrMapEntry 1 }

        gdsl4RtrMapPortIndex  OBJECT-TYPE
            SYNTAX  PortID
            ACCESS  read-only
            STATUS  mandatory
            DESCRIPTION
                "Port 1~4, total 4 ports."
            ::= { gdsl4RtrMapEntry 2 }

        gdsl4RtrMapTsIndex  OBJECT-TYPE
            SYNTAX  TimeslotID
            ACCESS  read-only
            STATUS  mandatory
            DESCRIPTION
                " Timeslot 1~32, total 32 timeslots."
            ::= { gdsl4RtrMapEntry 3 }

        gdsl4RtrCh  OBJECT-TYPE
            SYNTAX  INTEGER {
                    idle(1),
                    wan1(2),
                    na(3)
                }
            ACCESS  read-write
            STATUS  mandatory
            DESCRIPTION
                "channel map data"
            ::= { gdsl4RtrMapEntry 4 }


--
--  G.shdsl card remote Bridge Config
--

    gdsl4RemoteBridgeConfig OBJECT IDENTIFIER ::= { gdsl4-card 22 }

--  G.shdsl card remote Bridge: config table
        gdsl4RemBridgeTable  OBJECT-TYPE
            SYNTAX  SEQUENCE OF Gdsl4RemBridgeEntry
            ACCESS  not-accessible
            STATUS  mandatory
            DESCRIPTION
                "Remote Bridge Table"
            ::= { gdsl4RemoteBridgeConfig 1 }

        gdsl4RemBridgeEntry  OBJECT-TYPE
            SYNTAX  Gdsl4RemBridgeEntry
            ACCESS  not-accessible
            STATUS  mandatory
            DESCRIPTION
                "Remote Bridge Entry"
            INDEX { gdsl4RBgSlotIndex ,
                    gdsl4RBgPortIndex }
            ::= { gdsl4RemBridgeTable 1 }

        Gdsl4RemBridgeEntry ::= SEQUENCE {
            gdsl4RBgSlotIndex           LSSlotID,
            gdsl4RBgPortIndex           PortID,
            gdsl4RemBrgAgeTime          INTEGER (10..1000000),
            gdsl4RemBrgCRC              INTEGER,
            gdsl4RemBrgLanSpeed         INTEGER
        }

        gdsl4RBgSlotIndex  OBJECT-TYPE
            SYNTAX  LSSlotID
            ACCESS  read-only
            STATUS  mandatory
            DESCRIPTION
                "LS slot index"
            ::= { gdsl4RemBridgeEntry 1 }

        gdsl4RBgPortIndex  OBJECT-TYPE
            SYNTAX  PortID
            ACCESS  read-only
            STATUS  mandatory
            DESCRIPTION
                "Port 1~4, total 4 ports."
            ::= { gdsl4RemBridgeEntry 2 }

        gdsl4RemBrgAgeTime  OBJECT-TYPE
            SYNTAX  INTEGER (10..1000000)
            ACCESS  read-write
            STATUS  mandatory
            DESCRIPTION
                "Remote Bridge: Age time 10~1000000 seconds."
            ::= { gdsl4RemBridgeEntry 3 }

        gdsl4RemBrgCRC  OBJECT-TYPE
            SYNTAX  INTEGER {
                    off(1),
                    on(2)
                }
            ACCESS  read-write
            STATUS  mandatory
            DESCRIPTION
                "Remote Bridge: CRC"
            ::= { gdsl4RemBridgeEntry 4 }

        gdsl4RemBrgLanSpeed  OBJECT-TYPE
            SYNTAX  INTEGER {
                    no(0),
                    half-duplex-10M(1),
                    full-duplex-10M(2),
                    half-duplex-100M(3),
                    full-duplex-100M(4),
                    auto-negotiation(5)
                }
            ACCESS  read-write
            STATUS  mandatory
            DESCRIPTION
                "Remote Bridge: LAN speed"
            ::= { gdsl4RemBridgeEntry 5 }


--  G.shdsl card remote VLAN: VLAN State Table
        gdsl4RemVlanStateTable  OBJECT-TYPE
            SYNTAX  SEQUENCE OF Gdsl4RemVlanStateEntry
            ACCESS  not-accessible
            STATUS  mandatory
            DESCRIPTION
                "Remote VLAN State Table"
            ::= { gdsl4RemoteBridgeConfig 2 }

        gdsl4RemVlanStateEntry  OBJECT-TYPE
            SYNTAX  Gdsl4RemVlanStateEntry
            ACCESS  not-accessible
            STATUS  mandatory
            DESCRIPTION
                "Remote VLAN State Entry"
            INDEX { gdsl4RVSSlotIndex ,
                    gdsl4RVSPortIndex }
            ::= { gdsl4RemVlanStateTable 1 }

        Gdsl4RemVlanStateEntry ::= SEQUENCE {
            gdsl4RVSSlotIndex           LSSlotID,
            gdsl4RVSPortIndex           PortID,
            gdsl4RemVlanEnable          INTEGER,
            gdsl4RemVlanMgmtVID         INTEGER (1..4095),
            gdsl4RemVlanRegenCRC        INTEGER
        }

        gdsl4RVSSlotIndex  OBJECT-TYPE
            SYNTAX  LSSlotID
            ACCESS  read-only
            STATUS  mandatory
            DESCRIPTION
                "LS slot index"
            ::= { gdsl4RemVlanStateEntry 1 }

        gdsl4RVSPortIndex  OBJECT-TYPE
            SYNTAX  PortID
            ACCESS  read-only
            STATUS  mandatory
            DESCRIPTION
                "Port 1~4, total 4 ports."
            ::= { gdsl4RemVlanStateEntry 2 }

        gdsl4RemVlanEnable  OBJECT-TYPE
            SYNTAX  INTEGER {
                    disable(1),
                    enable(2)
                }
            ACCESS  read-write
            STATUS  mandatory
            DESCRIPTION
                "Remote VLAN: disable or enable"
            ::= { gdsl4RemVlanStateEntry 3 }

        gdsl4RemVlanMgmtVID  OBJECT-TYPE
            SYNTAX  INTEGER (1..4095)
            ACCESS  read-write
            STATUS  mandatory
            DESCRIPTION
                "Remote VLAN: Magement VID"
            ::= { gdsl4RemVlanStateEntry 4 }

        gdsl4RemVlanRegenCRC  OBJECT-TYPE
            SYNTAX  INTEGER {
                    disable(1),
                    enable(2)
                }
            ACCESS  read-write
            STATUS  mandatory
            DESCRIPTION
                "Remote VLAN: regenate CRC"
            ::= { gdsl4RemVlanStateEntry 5 }


--  G.shdsl card remote Bridge: VLAN Control Table
        gdsl4RemVlanControlTable  OBJECT-TYPE
            SYNTAX  SEQUENCE OF Gdsl4RemVlanControlEntry
            ACCESS  not-accessible
            STATUS  mandatory
            DESCRIPTION
                "Remote VLAN Control Table"
            ::= { gdsl4RemoteBridgeConfig 3 }

        gdsl4RemVlanControlEntry  OBJECT-TYPE
            SYNTAX  Gdsl4RemVlanControlEntry
            ACCESS  not-accessible
            STATUS  mandatory
            DESCRIPTION
                "Remote VLAN Control Entry"
            INDEX { gdsl4RVCSlotIndex ,
                    gdsl4RVCPortIndex }
            ::= { gdsl4RemVlanControlTable 1 }

        Gdsl4RemVlanControlEntry ::= SEQUENCE {
            gdsl4RVCSlotIndex           LSSlotID,
            gdsl4RVCPortIndex           PortID,
            gdsl4RemVlanVID             INTEGER (1..4095),
            gdsl4RemVlanTAG             INTEGER,
            gdsl4RemVlanMember          INTEGER,
            gdsl4RemVlanCommand         INTEGER,
            gdsl4RemVlanResponse        INTEGER
        }

        gdsl4RVCSlotIndex  OBJECT-TYPE
            SYNTAX  LSSlotID
            ACCESS  read-only
            STATUS  mandatory
            DESCRIPTION
                "LS slot index"
            ::= { gdsl4RemVlanControlEntry 1 }

        gdsl4RVCPortIndex  OBJECT-TYPE
            SYNTAX  PortID
            ACCESS  read-only
            STATUS  mandatory
            DESCRIPTION
                "Port 1~4, total 4 ports."
            ::= { gdsl4RemVlanControlEntry 2 }

        gdsl4RemVlanVID  OBJECT-TYPE
            SYNTAX  INTEGER (1..4095)
            ACCESS  read-write
            STATUS  mandatory
            DESCRIPTION
                "Remote VLAN: VLAN ID"
            ::= { gdsl4RemVlanControlEntry 4 }

        gdsl4RemVlanTAG  OBJECT-TYPE
            SYNTAX  INTEGER {
                    untag(1),
                    tag(2)
                }
            ACCESS  read-write
            STATUS  mandatory
            DESCRIPTION
                "Remote VLAN: UNTAG or TAG"
            ::= { gdsl4RemVlanControlEntry 5 }

        gdsl4RemVlanMember  OBJECT-TYPE
            SYNTAX  INTEGER {
                    lan1(1),
                    wan1(2)
                }
            ACCESS  read-write
            STATUS  mandatory
            DESCRIPTION
                "Remote VLAN: Member is LAN1 or WAN1"
            ::= { gdsl4RemVlanControlEntry 6 }

        gdsl4RemVlanCommand  OBJECT-TYPE
            SYNTAX  INTEGER {
                    create-vid(1),
                    add-member(2),
                    deactive-vid(3),
                    remove-member(4)
                }
            ACCESS  read-write
            STATUS  mandatory
            DESCRIPTION
                "Remote VLAN: command"
            ::= { gdsl4RemVlanControlEntry 11 }

        gdsl4RemVlanResponse  OBJECT-TYPE
            SYNTAX  INTEGER {
                    ok(1),
                    vid-created-before(2),
                    vid-not-created-before(3),
                    not-empty(4),
                    no-response(11),
                    not-available(12)
                }
            ACCESS  read-only
            STATUS  mandatory
            DESCRIPTION
                "Remote VLAN: Set response"
            ::= { gdsl4RemVlanControlEntry 12 }


--  G.shdsl card remote Bridge: VLAN List Table
        gdsl4RemVlanListTable  OBJECT-TYPE
            SYNTAX  SEQUENCE OF Gdsl4RemVlanListEntry
            ACCESS  not-accessible
            STATUS  mandatory
            DESCRIPTION
                "Remote VLAN List Table"
            ::= { gdsl4RemoteBridgeConfig 4 }

        gdsl4RemVlanListEntry  OBJECT-TYPE
            SYNTAX  Gdsl4RemVlanListEntry
            ACCESS  not-accessible
            STATUS  mandatory
            DESCRIPTION
                "Remote VLAN List Entry"
            INDEX { gdsl4RVLSlotIndex ,
                    gdsl4RVLPortIndex ,
                    gdsl4RVLVLanIndex }
            ::= { gdsl4RemVlanListTable 1 }

        Gdsl4RemVlanListEntry ::= SEQUENCE {
            gdsl4RVLSlotIndex           LSSlotID,
            gdsl4RVLPortIndex           PortID,
            gdsl4RVLVLanIndex           INTEGER,
            gdsl4RVLVlanVID             INTEGER (1..4095),
            gdsl4RVLVlanTAGmember       DisplayString,
            gdsl4RVLVlanUNTAGmember     DisplayString
        }

        gdsl4RVLSlotIndex  OBJECT-TYPE
            SYNTAX  LSSlotID
            ACCESS  read-only
            STATUS  mandatory
            DESCRIPTION
                "LS slot index"
            ::= { gdsl4RemVlanListEntry 1 }

        gdsl4RVLPortIndex  OBJECT-TYPE
            SYNTAX  PortID
            ACCESS  read-only
            STATUS  mandatory
            DESCRIPTION
                "Port 1~4, total 4 ports."
            ::= { gdsl4RemVlanListEntry 2 }

        gdsl4RVLVLanIndex  OBJECT-TYPE
            SYNTAX  INTEGER
            ACCESS  read-only
            STATUS  mandatory
            DESCRIPTION
                "VLAN list index"
            ::= { gdsl4RemVlanListEntry 3 }

        gdsl4RVLVlanVID  OBJECT-TYPE
            SYNTAX  INTEGER (1..4095)
            ACCESS  read-only
            STATUS  mandatory
            DESCRIPTION
                "Remote VLAN: VLAN ID"
            ::= { gdsl4RemVlanListEntry 4 }

        gdsl4RVLVlanTAGmember  OBJECT-TYPE
            SYNTAX  DisplayString
            ACCESS  read-only
            STATUS  mandatory
            DESCRIPTION
                "Remote VLAN: TAG member"
            ::= { gdsl4RemVlanListEntry 5 }

        gdsl4RVLVlanUNTAGmember  OBJECT-TYPE
            SYNTAX  DisplayString
            ACCESS  read-only
            STATUS  mandatory
            DESCRIPTION
                "Remote VLAN: UNTAG member"
            ::= { gdsl4RemVlanListEntry 6 }


--  G.shdsl card remote Bridge: VLAN Port Table
        gdsl4RemVlanPortTable  OBJECT-TYPE
            SYNTAX  SEQUENCE OF Gdsl4RemVlanPortEntry
            ACCESS  not-accessible
            STATUS  mandatory
            DESCRIPTION
                "Remote VLAN Port Table"
            ::= { gdsl4RemoteBridgeConfig 5 }

        gdsl4RemVlanPortEntry  OBJECT-TYPE
            SYNTAX  Gdsl4RemVlanPortEntry
            ACCESS  not-accessible
            STATUS  mandatory
            DESCRIPTION
                "Remote VLAN Port Entry"
            INDEX { gdsl4RVPSlotIndex ,
                    gdsl4RVPPortIndex ,
                    gdsl4RVPVPIndex }
            ::= { gdsl4RemVlanPortTable 1 }

        Gdsl4RemVlanPortEntry ::= SEQUENCE {
            gdsl4RVPSlotIndex           LSSlotID,
            gdsl4RVPPortIndex           PortID,
            gdsl4RVPVPIndex             INTEGER,
            gdsl4RVPVlanPVID            INTEGER (1..4095),
            gdsl4RVPVlanFrameType       INTEGER,
            gdsl4RVPVlanIngressFilter   INTEGER,
            gdsl4RVPSetResponse         INTEGER
        }

        gdsl4RVPSlotIndex  OBJECT-TYPE
            SYNTAX  LSSlotID
            ACCESS  read-only
            STATUS  mandatory
            DESCRIPTION
                "LS slot index"
            ::= { gdsl4RemVlanPortEntry 1 }

        gdsl4RVPPortIndex  OBJECT-TYPE
            SYNTAX  PortID
            ACCESS  read-only
            STATUS  mandatory
            DESCRIPTION
                "Port 1~4, total 4 ports."
            ::= { gdsl4RemVlanPortEntry 2 }

        gdsl4RVPVPIndex  OBJECT-TYPE
            SYNTAX  INTEGER {
                    lan1(1),
                    wan1(2)
                }
            ACCESS  read-only
            STATUS  mandatory
            DESCRIPTION
                "VLAN Port index"
            ::= { gdsl4RemVlanPortEntry 3 }

        gdsl4RVPVlanPVID  OBJECT-TYPE
            SYNTAX  INTEGER (1..4095)
            ACCESS  read-write
            STATUS  mandatory
            DESCRIPTION
                "Remote VLAN: VLAN ID"
            ::= { gdsl4RemVlanPortEntry 4 }

        gdsl4RVPVlanFrameType  OBJECT-TYPE
            SYNTAX  INTEGER {
                    all(1),
                    tag-only(2)
                }
            ACCESS  read-write
            STATUS  mandatory
            DESCRIPTION
                "Remote VLAN: Frame Type"
            ::= { gdsl4RemVlanPortEntry 5 }

        gdsl4RVPVlanIngressFilter  OBJECT-TYPE
            SYNTAX  INTEGER {
                    disable(1),
                    enable(2)
                }
            ACCESS  read-write
            STATUS  mandatory
            DESCRIPTION
                "Remote VLAN: Ingress Filter"
            ::= { gdsl4RemVlanPortEntry 6 }


        gdsl4RVPSetResponse  OBJECT-TYPE
            SYNTAX  INTEGER {
                    ok(1),
                    vid-not-created-before(3),
                    no-response(11),
                    not-available(12)
                }
            ACCESS  read-only
            STATUS  mandatory
            DESCRIPTION
                "Remote VLAN: Set response"
            ::= { gdsl4RemVlanPortEntry 7 }

        gdsl4TotalCard   OBJECT-TYPE
            SYNTAX  INTEGER
            ACCESS  read-only
            STATUS  mandatory
            DESCRIPTION
                "Total cards of GDSL4"
            ::= { gdsl4-card 100 }

--======================================================================--
--======================================================================--
--  Dry Contact MIB
--======================================================================--
--======================================================================--

--
--  INPUTS SYSTEM Table
--

        dcInputSystemTable  OBJECT-TYPE
            SYNTAX  SEQUENCE OF DCInputSystemEntry
            ACCESS  not-accessible
            STATUS  mandatory
            DESCRIPTION
                "Dry Contact Inputs system control table."
            ::= { dc-card 1 }

        dcInputSystemEntry  OBJECT-TYPE
            SYNTAX  DCInputSystemEntry
            ACCESS  not-accessible
            STATUS  mandatory
            DESCRIPTION
                "An entry in the dc inputs system table."
            INDEX { dcISSlotIndex ,
                    dcInputPairIndex }
            ::= { dcInputSystemTable 1 }

        DCInputSystemEntry ::= SEQUENCE {
            dcISSlotIndex               LSSlotID,
            dcInputPairIndex            INTEGER,
            dcAlarmStatus               INTEGER,
            dcAlarmTrigger              LsAlarmSeverity,
            dcAlarmMessage              DisplayString (SIZE(0..255))
        }

        dcISSlotIndex  OBJECT-TYPE
            SYNTAX  LSSlotID
            ACCESS  read-only
            STATUS  mandatory
            DESCRIPTION
                "DC slot"
            ::= { dcInputSystemEntry 1 }

        dcInputPairIndex  OBJECT-TYPE
            SYNTAX  INTEGER {
                    n1-pair1(1),
                    n1-pair2(2),
                    n1-pair3(3),
                    n1-pair4(4),
                    n2-pair1(5),
                    n2-pair2(6),
                    n2-pair3(7),
                    n2-pair4(8)
                }
            ACCESS  read-only
            STATUS  mandatory
            DESCRIPTION
                " N1 Pair 1~4 & N2 Pair 1~4."
            ::= { dcInputSystemEntry 2 }

        dcAlarmStatus  OBJECT-TYPE
            SYNTAX  INTEGER {
                    ok(1),
                    alarm(2)
                }
            ACCESS  read-only
            STATUS  mandatory
            DESCRIPTION
                "Normal or Alarm."
            ::= { dcInputSystemEntry 3 }

        dcAlarmTrigger  OBJECT-TYPE
            SYNTAX  LsAlarmSeverity
            ACCESS  read-write
            STATUS  mandatory
            DESCRIPTION
                "Send Alarm Trap ON or OFF"
            ::= { dcInputSystemEntry 4 }

        dcAlarmMessage  OBJECT-TYPE
            SYNTAX  DisplayString (SIZE (0..255) )
            ACCESS  read-write
            STATUS  mandatory
            DESCRIPTION
                "Alarm Message."
            ::= { dcInputSystemEntry 5 }


--
--  OUTPUTS SYSTEM Table
--

        dcOutputSystemTable  OBJECT-TYPE
            SYNTAX  SEQUENCE OF DCOutputSystemEntry
            ACCESS  not-accessible
            STATUS  mandatory
            DESCRIPTION
                "Dry Contact Outputs system control table."
            ::= { dc-card 2 }

        dcOutputSystemEntry  OBJECT-TYPE
            SYNTAX  DCOutputSystemEntry
            ACCESS  not-accessible
            STATUS  mandatory
            DESCRIPTION
                "An entry in the dc outputs system table."
            INDEX { dcOSSlotIndex ,
                    dcOutputPairIndex }
            ::= { dcOutputSystemTable 1 }

        DCOutputSystemEntry ::= SEQUENCE {
            dcOSSlotIndex               LSSlotID,
            dcOutputPairIndex           INTEGER,
            dcRelayStatus               INTEGER,
            dcRelaySetup                INTEGER
        }

        dcOSSlotIndex  OBJECT-TYPE
            SYNTAX  LSSlotID
            ACCESS  read-only
            STATUS  mandatory
            DESCRIPTION
                "DC slot"
            ::= { dcOutputSystemEntry 1 }

        dcOutputPairIndex  OBJECT-TYPE
            SYNTAX  INTEGER {
                    u1(1),
                    u2(2),
                    u3(3),
                    u4(4),
                    u5(5),
                    u6(6),
                    u7(7),
                    u8(8)
                }
            ACCESS  read-only
            STATUS  mandatory
            DESCRIPTION
                " U1~U8."
            ::= { dcOutputSystemEntry 2 }

        dcRelayStatus  OBJECT-TYPE
            SYNTAX  INTEGER {
                    normal(1),
                    operated(2)
                }
            ACCESS  read-only
            STATUS  mandatory
            DESCRIPTION
                "Normal or Operated."
            ::= { dcOutputSystemEntry 3 }

        dcRelaySetup  OBJECT-TYPE
            SYNTAX  INTEGER {
                    normal(1),
                    operated(2)
                }
            ACCESS  read-write
            STATUS  mandatory
            DESCRIPTION
                "Relay Open or Short."
            ::= { dcOutputSystemEntry 4 }

--
--  Command Control Table
--

        dcCommandControlTable  OBJECT-TYPE
            SYNTAX  SEQUENCE OF DCCommandControlEntry
            ACCESS  not-accessible
            STATUS  mandatory
            DESCRIPTION
                "The command control table."
            ::= { dc-card 3 }

        dcCommandControlEntry  OBJECT-TYPE
            SYNTAX  DCCommandControlEntry
            ACCESS  not-accessible
            STATUS  mandatory
            DESCRIPTION
                "An entry in the command control table."
            INDEX { dcCCSlotIndex }
            ::= { dcCommandControlTable 1 }

        DCCommandControlEntry ::= SEQUENCE {
            dcCCSlotIndex               LSSlotID,
            dcUnitLoadDefault           INTEGER,
            dcChannel                   INTEGER
        }

        dcCCSlotIndex  OBJECT-TYPE
            SYNTAX  LSSlotID
            ACCESS  read-only
            STATUS  mandatory
            DESCRIPTION
                "DC slot"
            ::= { dcCommandControlEntry 1 }

        dcUnitLoadDefault    OBJECT-TYPE
            SYNTAX  INTEGER {
                    load-default(1)
                }
            ACCESS  read-write
            STATUS  mandatory
            DESCRIPTION
                "Command: Load Default Dry Contact"
            ::= { dcCommandControlEntry 2 }

        dcChannel    OBJECT-TYPE
            SYNTAX  INTEGER {
                    controller(1),
                    ds0x2(2),
                    ds0x16(3)
                }
            ACCESS  read-write
            STATUS  mandatory
            DESCRIPTION
                "Command: Dry Contact Channel"
            ::= { dcCommandControlEntry 3 }

--
--  SYSTEM Information Table
--

        dcSystemInfoTable  OBJECT-TYPE
            SYNTAX  SEQUENCE OF DCSystemInformation
            ACCESS  not-accessible
            STATUS  mandatory
            DESCRIPTION
                "The system information table."
            ::= { dc-card 4 }

        dcSystemInfoEntry  OBJECT-TYPE
            SYNTAX  DCSystemInformation
            ACCESS  not-accessible
            STATUS  mandatory
            DESCRIPTION
                "An entry in the system information table."
            INDEX {
                    dcSISlotIndex
                }
            ::= { dcSystemInfoTable 1 }

        DCSystemInformation ::= SEQUENCE {
            dcSISlotIndex               LSSlotID,
            dcFPGAVersion               DisplayString
        }

        dcSISlotIndex  OBJECT-TYPE
            SYNTAX  LSSlotID
            ACCESS  read-only
            STATUS  mandatory
            DESCRIPTION
                "DC slot"
            ::= { dcSystemInfoEntry 1 }

        dcFPGAVersion  OBJECT-TYPE
            SYNTAX  DisplayString (SIZE (0..255) )
            ACCESS  read-only
            STATUS  mandatory
            DESCRIPTION
                " Dry Contact FPGA Version"
            ::= { dcSystemInfoEntry 2 }

--
--  Input Relay Control Table
--

        dcInputRelayCtrlTable  OBJECT-TYPE
            SYNTAX  SEQUENCE OF DcInputRelayCtrlEntry
            ACCESS  not-accessible
            STATUS  mandatory
            DESCRIPTION
                "The command control table."
            ::= { dc-card 5 }

        dcInputRelayCtrlEntry  OBJECT-TYPE
            SYNTAX  DcInputRelayCtrlEntry
            ACCESS  not-accessible
            STATUS  mandatory
            DESCRIPTION
                "Input Relay Control Table."
            INDEX { dcnIndex , dcnInputPairIndex }
            ::= { dcInputRelayCtrlTable 1 }

        DcInputRelayCtrlEntry ::= SEQUENCE {
            dcnIndex                   LSSlotID,
            dcnInputPairIndex          INTEGER,
            dcTrigger                  INTEGER
        }

        dcnIndex  OBJECT-TYPE
            SYNTAX  LSSlotID
            ACCESS  read-only
            STATUS  mandatory
            DESCRIPTION
                "Slot 1~12, total 12 slots."
            ::= { dcInputRelayCtrlEntry 1 }

        dcnInputPairIndex  OBJECT-TYPE
            SYNTAX  INTEGER {
                    n1-pair1(1),
                    n1-pair2(2),
                    n1-pair3(3),
                    n1-pair4(4),
                    n2-pair1(5),
                    n2-pair2(6),
                    n2-pair3(7),
                    n2-pair4(8)
                }
            ACCESS  read-only
            STATUS  mandatory
            DESCRIPTION
                " N1 Pair 1~4 & N2 Pair 1~4."
            ::= { dcInputRelayCtrlEntry 2 }

        dcTrigger    OBJECT-TYPE
            SYNTAX  INTEGER {
                    normal-close(1),
                    normal-open(2)
                }
            ACCESS  read-write
            STATUS  mandatory
            DESCRIPTION
                "Command: Dry Contact normal(0/1)"
            ::= { dcInputRelayCtrlEntry 3 }

        dcTotalCard   OBJECT-TYPE
            SYNTAX  INTEGER
            ACCESS  read-only
            STATUS  mandatory
            DESCRIPTION
                "Total cards of DC"
            ::= { dc-card 100 }

--======================================================================--
--======================================================================--
--  FOM MIB
--======================================================================--
--======================================================================--

--
--  SYSTEM Control Table
--

        fomSystemControlTable  OBJECT-TYPE
            SYNTAX  SEQUENCE OF FomSystemControlEntry
            ACCESS  not-accessible
            STATUS  mandatory
            DESCRIPTION
                "FOM E1 control table."
            ::= { fom1card 1 }

        fomSystemControlEntry  OBJECT-TYPE
            SYNTAX  FomSystemControlEntry
            ACCESS  not-accessible
            STATUS  mandatory
            DESCRIPTION
                "An entry in the FOM control table."
            INDEX { fomSCslot , fomSCport }
            ::= { fomSystemControlTable 1 }

        FomSystemControlEntry ::= SEQUENCE  {
            fomSCslot                   LSSlotID,
            fomSCport                   PortID,
            fomFrame                    INTEGER,
            fomCRC                      INTEGER,
            fomRAI                      INTEGER,
            fomCAS                      INTEGER,
            fomAIS                      INTEGER,
            fomIdleCode                 INTEGER,
            fomSabit                    INTEGER,
            fomSSM                      INTEGER,
            fomOOS                      INTEGER
        }

        fomSCslot  OBJECT-TYPE
            SYNTAX  LSSlotID
            ACCESS  read-only
            STATUS  mandatory
            DESCRIPTION
                "1FOMA slot index"
            ::= { fomSystemControlEntry 1 }

        fomSCport  OBJECT-TYPE
            SYNTAX  PortID
            ACCESS  read-only
            STATUS  mandatory
            DESCRIPTION
                "Port 1 to 4, total 4 ports."
            ::= { fomSystemControlEntry 2 }

        fomFrame  OBJECT-TYPE
            SYNTAX  INTEGER   {
                    on(1),
                    off(2)
                }
            ACCESS  read-write
            STATUS  mandatory
            DESCRIPTION
                "FOM E1 frame format"
            ::= { fomSystemControlEntry 3 }

        fomCRC  OBJECT-TYPE
            SYNTAX  INTEGER   {
                    on(1),
                    off(2)
                }
            ACCESS  read-write
            STATUS  mandatory
            DESCRIPTION
                "FOM E1 Cycle Redundancy Check OFF/ON"
            ::= { fomSystemControlEntry 4 }

        fomRAI  OBJECT-TYPE
            SYNTAX  INTEGER   {
                    off(1),
                    on(2)
                }
            ACCESS  read-write
            STATUS  mandatory
            DESCRIPTION
                "RAI-ON indicates that RAI (Remote Alarm Indication) ON."
            ::= { fomSystemControlEntry 5 }

        fomCAS  OBJECT-TYPE
            SYNTAX  INTEGER   {
                    off(1),
                    on(2)
                }
            ACCESS  read-write
            STATUS  mandatory
            DESCRIPTION
                "CAS or CCS"
            ::= { fomSystemControlEntry 6 }

        fomAIS  OBJECT-TYPE
            SYNTAX  INTEGER   {
                    off(1),
                    unframe(2)
                }
            ACCESS  read-write
            STATUS  mandatory
            DESCRIPTION
                "AIS OFF/UNFRAME"
            ::= { fomSystemControlEntry 7 }

        fomIdleCode  OBJECT-TYPE
            SYNTAX  INTEGER
            ACCESS  read-write
            STATUS  mandatory
            DESCRIPTION
                "E1 Idle Code Value"
            ::= { fomSystemControlEntry 8 }

        fomSabit  OBJECT-TYPE
            SYNTAX  INTEGER   {
                    notSupport(0),
                    sa4(4),
                    sa5(5),
                    sa6(6),
                    sa7(7),
                    sa8(8)
                }
            ACCESS  read-write
            STATUS  mandatory
            DESCRIPTION
                "E1 Sa bit"
            ::= { fomSystemControlEntry 9 }

        fomSSM  OBJECT-TYPE
            SYNTAX  INTEGER   {
                    notSupport(0),
                    off(1),
                    on(2)
                }
            ACCESS  read-write
            STATUS  mandatory
            DESCRIPTION
                "SSM OFF/ON"
            ::= { fomSystemControlEntry 10 }

        fomOOS  OBJECT-TYPE
            SYNTAX  INTEGER   {
                    b0001(1),
                    b0010(2),
                    b0011(3),
                    b0100(4),
                    b0101(5),
                    b0110(6),
                    b0111(7),
                    b1000(8),
                    b1001(9),
                    b1010(10),
                    b1011(11),
                    b1100(12),
                    b1101(13),
                    b1110(14),
                    b1111(15)
                }
            ACCESS  read-write
            STATUS  mandatory
            DESCRIPTION
                "OOS"
            ::= { fomSystemControlEntry 11 }

--
--  FOM Status Table
--

        fomStatusTable  OBJECT-TYPE
            SYNTAX  SEQUENCE OF FomStatusEntry
            ACCESS  not-accessible
            STATUS  mandatory
            DESCRIPTION
                "The FOM status table."
            ::= { fom1card 2 }

        fomStatusEntry  OBJECT-TYPE
            SYNTAX  FomStatusEntry
            ACCESS  not-accessible
            STATUS  mandatory
            DESCRIPTION
                "An entry in the FOM status table."
            INDEX { fomSTslot , fomSTport ,
                    fomStatusNumIndex }
            ::= { fomStatusTable 1 }

        FomStatusEntry ::= SEQUENCE {
            fomSTslot                   LSSlotID,
            fomSTport                   PortID,
            fomStatusNumIndex           INTEGER,
            fomType                     INTEGER,
            fomOpticalLOS               INTEGER,
            fomOpticalLOF               INTEGER,
            fomOpticalFE                INTEGER,
            fomOpticalFCS               INTEGER,
            fomOpticalEOC               INTEGER,
            fomE1LOF                    INTEGER,
            fomE1CRC                    INTEGER,
            fomE1RxAIS                  INTEGER,
            fomE1RxRAI                  INTEGER,
            fomE1TxAIS                  INTEGER,
            fomE1TxRAI                  INTEGER,
            fomE1LOS                    INTEGER,
            fomE1BPVCRC                 INTEGER
        }

        fomSTslot  OBJECT-TYPE
            SYNTAX  LSSlotID
            ACCESS  read-only
            STATUS  mandatory
            DESCRIPTION
                "1FOMA slot index"
            ::= { fomStatusEntry 1 }

        fomSTport  OBJECT-TYPE
            SYNTAX  PortID
            ACCESS  read-only
            STATUS  mandatory
            DESCRIPTION
                "Port 1 to 4, total 4 ports."
            ::= { fomStatusEntry 2 }

        fomStatusNumIndex  OBJECT-TYPE
            SYNTAX  INTEGER {
                    local(1),
                    remote(2)
                }
            ACCESS  read-only
            STATUS  mandatory
            DESCRIPTION
                " local or Remote Status "
            ::= { fomStatusEntry 3 }

        fomType  OBJECT-TYPE
            SYNTAX  INTEGER {
                    unknown(1),
                    fom8MStandAloneWithCPU(2),
                    fom8MStandAloneWithoutCPU(4),
                    fom8MCard(5)
                }
            ACCESS  read-only
            STATUS  mandatory
            DESCRIPTION
                " Fom Type "
            ::= { fomStatusEntry 4 }

        fomOpticalLOS  OBJECT-TYPE
            SYNTAX  INTEGER {
                    no(1),
                    yes(2)
                }
            ACCESS  read-only
            STATUS  mandatory
            DESCRIPTION
                " Fom Optical LOS "
            ::= { fomStatusEntry 5 }

        fomOpticalLOF  OBJECT-TYPE
            SYNTAX  INTEGER {
                    no(1),
                    yes(2)
                }
            ACCESS  read-only
            STATUS  mandatory
            DESCRIPTION
                " Fom Optical LOF "
            ::= { fomStatusEntry 6 }

        fomOpticalFE  OBJECT-TYPE
            SYNTAX  INTEGER
            ACCESS  read-only
            STATUS  mandatory
            DESCRIPTION
                " Fom Optical Framing Error Counter "
            ::= { fomStatusEntry 7 }

        fomOpticalFCS  OBJECT-TYPE
            SYNTAX  INTEGER
            ACCESS  read-only
            STATUS  mandatory
            DESCRIPTION
                " Fom Optical Frame Checksum Error Counter "
            ::= { fomStatusEntry 8 }

        fomOpticalEOC  OBJECT-TYPE
            SYNTAX  INTEGER
            ACCESS  read-only
            STATUS  mandatory
            DESCRIPTION
                " Fom Optical EOC-M Frame Checksum Error Counter "
            ::= { fomStatusEntry 9 }

        fomE1LOF  OBJECT-TYPE
            SYNTAX  INTEGER {
                    no(1),
                    yes(2),
                    xx(3),
                    lossOfCas(4)
                }
            ACCESS  read-only
            STATUS  mandatory
            DESCRIPTION
                " Fom E1 LOF "
            ::= { fomStatusEntry 10 }

        fomE1CRC  OBJECT-TYPE
            SYNTAX  INTEGER
            ACCESS  read-only
            STATUS  mandatory
            DESCRIPTION
                " Fom E1 CRC Error Counter "
            ::= { fomStatusEntry 11 }

        fomE1RxAIS  OBJECT-TYPE
            SYNTAX  INTEGER {
                    no(1),
                    ais(2),
                    xx(3)
                }
            ACCESS  read-only
            STATUS  mandatory
            DESCRIPTION
                " FOM E1 line Rx Alarm Indication Signal."
            ::= { fomStatusEntry 12 }

        fomE1RxRAI  OBJECT-TYPE
            SYNTAX  INTEGER {
                    no(1),
                    rai(2),
                    xx(3)
                }
            ACCESS  read-only
            STATUS  mandatory
            DESCRIPTION
                " FOM E1 line Rx Remote Alarm Indication."
            ::= { fomStatusEntry 13 }

        fomE1TxAIS  OBJECT-TYPE
            SYNTAX  INTEGER {
                    no(1),
                    ais(2),
                    xx(3)
                }
            ACCESS  read-only
            STATUS  mandatory
            DESCRIPTION
                " FOM E1 line Tx Alarm Indication Signal."
            ::= { fomStatusEntry 14 }

        fomE1TxRAI  OBJECT-TYPE
            SYNTAX  INTEGER {
                    no(1),
                    rai(2),
                    xx(3)
                }
            ACCESS  read-only
            STATUS  mandatory
            DESCRIPTION
                " FOM E1 line Tx Remote Alarm Indication."
            ::= { fomStatusEntry 15 }

        fomE1LOS  OBJECT-TYPE
            SYNTAX  INTEGER {
                    no(1),
                    yes(2),
                    xx(3)
                }
            ACCESS  read-only
            STATUS  mandatory
            DESCRIPTION
                " Remote O9310 E1 LOS "
            ::= { fomStatusEntry 16 }

        fomE1BPVCRC  OBJECT-TYPE
            SYNTAX  INTEGER
            ACCESS  read-only
            STATUS  mandatory
            DESCRIPTION
                " Remote E1 BPV or CRC Error Counter "
            ::= { fomStatusEntry 17 }

--
-- Diagnostic Control Table
--

        fomDiagTable  OBJECT-TYPE
            SYNTAX  SEQUENCE OF FomDiagEntry
            ACCESS  not-accessible
            STATUS  mandatory
            DESCRIPTION
                ""
            ::= { fom1card 3 }

        fomDiagEntry  OBJECT-TYPE
            SYNTAX  FomDiagEntry
            ACCESS  not-accessible
            STATUS  mandatory
            DESCRIPTION
                ""
            INDEX { fomDIslot , fomDIport }
            ::= { fomDiagTable 1 }

        FomDiagEntry ::= SEQUENCE {
            fomDIslot                   LSSlotID,
            fomDIport                   PortID,
            fomLocalOpticalLoopback     INTEGER,
            fomLocalE1Loopback          INTEGER,
            fomRemoteOpticalLoopback    INTEGER,
            fomRemoteE1Loopback         INTEGER,
            fomBertControl              INTEGER,
            fomBertStatus               INTEGER,
            fomElapseSeconds            INTEGER,
            fomErrorSeconds             INTEGER,
            fomErrorBits                INTEGER,
            fomAccessRemoteLB           INTEGER,
            fomRemoteCallLocalOpticalLB INTEGER,
            fomRemoteCallLocalE1LB      INTEGER
        }

        fomDIslot  OBJECT-TYPE
            SYNTAX  LSSlotID
            ACCESS  read-only
            STATUS  mandatory
            DESCRIPTION
                "1FOMA slot index"
            ::= { fomDiagEntry 1 }

        fomDIport  OBJECT-TYPE
            SYNTAX  PortID
            ACCESS  read-only
            STATUS  mandatory
            DESCRIPTION
                "Port 1 to 4, total 4 ports."
            ::= { fomDiagEntry 2 }

        fomLocalOpticalLoopback  OBJECT-TYPE
            SYNTAX  INTEGER {
                    noLoopback(1),
--                    localLoopback(2),
                    lineLoopback(3)
                }
            ACCESS  read-write
            STATUS  mandatory
            DESCRIPTION
                "Fom Local Optical Loopback Type"
            ::= { fomDiagEntry 3 }

        fomLocalE1Loopback  OBJECT-TYPE
            SYNTAX  INTEGER {
                    noLoopback(1),
                    localLoopback(2),
                    payLoadLoopback(3)
                }
            ACCESS  read-write
            STATUS  mandatory
            DESCRIPTION
                "Fom Local E1 Loopback Type"
            ::= { fomDiagEntry 4 }

        fomRemoteOpticalLoopback  OBJECT-TYPE
            SYNTAX  INTEGER {
                    noLoopback(1),
--                    localLoopback(2),
                    payLoadLoopback(3)
                }
            ACCESS  read-write
            STATUS  mandatory
            DESCRIPTION
                "Fom Remote Optical Loopback Type"
            ::= { fomDiagEntry 5 }

        fomRemoteE1Loopback  OBJECT-TYPE
            SYNTAX  INTEGER {
                    noLoopback(1),
                    localLoopback(2),
                    payLoadLoopback(3)
                }
            ACCESS  read-write
            STATUS  mandatory
            DESCRIPTION
                "Fom Remote E1 Loopback Type"
            ::= { fomDiagEntry 6 }

        fomBertControl  OBJECT-TYPE
            SYNTAX  INTEGER {
                    bertOff(1),
                    bertOn(2),
                    reset(3),
                    injectError(4)
                }
            ACCESS  read-write
            STATUS  mandatory
            DESCRIPTION
                "BERT Control"
            ::= { fomDiagEntry 7 }

        fomBertStatus  OBJECT-TYPE
            SYNTAX  INTEGER {
                    bertSync(1),
                    bertUnsync(2),
                    bertNotActive(3)
                }
            ACCESS  read-only
            STATUS  mandatory
            DESCRIPTION
                "BERT Status"
            ::= { fomDiagEntry 8 }

        fomElapseSeconds  OBJECT-TYPE
            SYNTAX  INTEGER
            ACCESS  read-only
            STATUS  mandatory
            DESCRIPTION
                "Elapse seconds"
            ::= { fomDiagEntry 9 }

        fomErrorSeconds OBJECT-TYPE
            SYNTAX  INTEGER
            ACCESS  read-only
            STATUS  mandatory
            DESCRIPTION
                "Error seconds"
            ::= { fomDiagEntry 10 }

        fomErrorBits  OBJECT-TYPE
            SYNTAX  INTEGER
            ACCESS  read-only
            STATUS  mandatory
            DESCRIPTION
                "Error bits"
            ::= { fomDiagEntry 11 }

        fomAccessRemoteLB  OBJECT-TYPE
            SYNTAX  INTEGER {
                    enable(1),
                    disable(2)
                }
            ACCESS  read-write
            STATUS  mandatory
            DESCRIPTION
                "FOM Access Remote Loopback Control"
            ::= { fomDiagEntry 12 }

        fomRemoteCallLocalOpticalLB  OBJECT-TYPE
            SYNTAX  INTEGER {
                    noLoopback(1),
                    localLoopback(2),
                    payLoadLoopback(3)
                }
            ACCESS  read-only
            STATUS  mandatory
            DESCRIPTION
                "Remote Called Local Optical Loopback Type"
            ::= { fomDiagEntry 13 }

        fomRemoteCallLocalE1LB  OBJECT-TYPE
            SYNTAX  INTEGER {
                    noLoopback(1),
                    localLoopback(2),
                    payLoadLoopback(3)
                }
            ACCESS  read-only
            STATUS  mandatory
            DESCRIPTION
                "Remote Called Local E1 Loopback Type"
            ::= { fomDiagEntry 14 }

--
--  Alarm Status Table
--

    fomAlarmStatus   OBJECT IDENTIFIER ::= { fom1card 4 }

--
-- FOM Optical Alarm Status Table
--

        fomOpticalAlmStatusTable  OBJECT-TYPE
            SYNTAX  SEQUENCE OF FomOpticalAlmStatusEntry
            ACCESS  not-accessible
            STATUS  mandatory
            DESCRIPTION
                " Fom Optical Alarm Status Table "
            ::= { fomAlarmStatus 1 }

        fomOpticalAlmStatusEntry  OBJECT-TYPE
            SYNTAX  FomOpticalAlmStatusEntry
            ACCESS  not-accessible
            STATUS  mandatory
            DESCRIPTION
                " "
            INDEX { fomOAslot , fomOpticalAlmNumber }
            ::= { fomOpticalAlmStatusTable 1 }

        FomOpticalAlmStatusEntry ::= SEQUENCE {
            fomOAslot                   LSSlotID,
            fomOpticalAlmNumber         INTEGER,
            fomOpticalAlmString         DisplayString,
            fomOpticalAlmState          INTEGER,
            fomOpticalAlmCount          INTEGER,
            fomOpticalAlmThreshold      INTEGER,
            fomOpticalAlmEnable         LsAlarmSeverity
        }

        fomOAslot  OBJECT-TYPE
            SYNTAX  LSSlotID
            ACCESS  read-only
            STATUS  mandatory
            DESCRIPTION
                "1FOMA slot index"
            ::= { fomOpticalAlmStatusEntry 1 }

        fomOpticalAlmNumber  OBJECT-TYPE
            SYNTAX  INTEGER (1..40)
            ACCESS  read-only
            STATUS  mandatory
            DESCRIPTION
                " Fom optical Alarm Status Index "
            ::= { fomOpticalAlmStatusEntry 2 }

        fomOpticalAlmString  OBJECT-TYPE
            SYNTAX  DisplayString (SIZE (0..80))
            ACCESS  read-only
            STATUS  mandatory
            DESCRIPTION
                "Fom optical Alarm Type String"
            ::= { fomOpticalAlmStatusEntry 3 }

        fomOpticalAlmState  OBJECT-TYPE
            SYNTAX  INTEGER {
                    ok(1),
                    alarm(2),
                    disable(3),
                    none(4)
                }
            ACCESS  read-only
            STATUS  mandatory
            DESCRIPTION
                " Fom optical Alarm Current State"
            ::= { fomOpticalAlmStatusEntry 4 }

        fomOpticalAlmCount  OBJECT-TYPE
            SYNTAX  INTEGER
            ACCESS  read-only
            STATUS  mandatory
            DESCRIPTION
                " Fom optical Alarm Count which happened "
            ::= { fomOpticalAlmStatusEntry 5 }

        fomOpticalAlmThreshold  OBJECT-TYPE
            SYNTAX  INTEGER
            ACCESS  read-write
            STATUS  mandatory
            DESCRIPTION
                " Fom optical Alarm Threshold "
            ::= { fomOpticalAlmStatusEntry 6 }

        fomOpticalAlmEnable  OBJECT-TYPE
            SYNTAX  LsAlarmSeverity
            ACCESS  read-write
            STATUS  mandatory
            DESCRIPTION
                "Fom optical Alarm is enabled or not"
            ::= { fomOpticalAlmStatusEntry 7 }

--
-- FOM E1 Alarm Status Table
--

        fomE1AlmStatusTable  OBJECT-TYPE
            SYNTAX  SEQUENCE OF FomE1AlmStatusEntry
            ACCESS  not-accessible
            STATUS  mandatory
            DESCRIPTION
                " Fom E1 Alarm Status Table "
            ::= { fomAlarmStatus 2 }

        fomE1AlmStatusEntry  OBJECT-TYPE
            SYNTAX  FomE1AlmStatusEntry
            ACCESS  not-accessible
            STATUS  mandatory
            DESCRIPTION
                " "
            INDEX { fomEAslot , fomEAport ,
                    fomE1AlmNumber }
            ::= { fomE1AlmStatusTable 1 }

        FomE1AlmStatusEntry ::= SEQUENCE {
            fomEAslot                   LSSlotID,
            fomEAport                   PortID,
            fomE1AlmNumber              INTEGER,
            fomE1AlmString              DisplayString,
            fomE1AlmState               INTEGER,
            fomE1AlmCount               INTEGER,
            fomE1AlmThreshold           INTEGER,
            fomE1AlmEnable              LsAlarmSeverity
        }

        fomEAslot  OBJECT-TYPE
            SYNTAX  LSSlotID
            ACCESS  read-only
            STATUS  mandatory
            DESCRIPTION
                "1FOMA slot index"
            ::= { fomE1AlmStatusEntry 1 }

        fomEAport  OBJECT-TYPE
            SYNTAX  PortID
            ACCESS  read-only
            STATUS  mandatory
            DESCRIPTION
                "Port 1 to 4, total 4 ports."
            ::= { fomE1AlmStatusEntry 2 }

        fomE1AlmNumber  OBJECT-TYPE
            SYNTAX  INTEGER (1..40)
            ACCESS  read-only
            STATUS  mandatory
            DESCRIPTION
                " Fom E1 Alarm Status Index "
            ::= { fomE1AlmStatusEntry 3 }

        fomE1AlmString  OBJECT-TYPE
            SYNTAX  DisplayString (SIZE (0..80))
            ACCESS  read-only
            STATUS  mandatory
            DESCRIPTION
                "Fom E1 Alarm Type String"
            ::= { fomE1AlmStatusEntry 4 }

        fomE1AlmState  OBJECT-TYPE
            SYNTAX  INTEGER {
                    ok(1),
                    alarm(2),
                    disable(3),
                    none(4)
                }
            ACCESS  read-only
            STATUS  mandatory
            DESCRIPTION
                " Fom E1 Alarm Current State"
            ::= { fomE1AlmStatusEntry 5 }

        fomE1AlmCount  OBJECT-TYPE
            SYNTAX  INTEGER
            ACCESS  read-only
            STATUS  mandatory
            DESCRIPTION
                " Fom E1 Alarm Count which happened "
            ::= { fomE1AlmStatusEntry 6 }

        fomE1AlmThreshold  OBJECT-TYPE
            SYNTAX  INTEGER
            ACCESS  read-write
            STATUS  mandatory
            DESCRIPTION
                " Fom E1 Alarm Threshold "
            ::= { fomE1AlmStatusEntry 7 }

        fomE1AlmEnable  OBJECT-TYPE
            SYNTAX  LsAlarmSeverity
            ACCESS  read-write
            STATUS  mandatory
            DESCRIPTION
                "Fom E1 Alarm is enabled or not"
            ::= { fomE1AlmStatusEntry 8 }


--
--  Command Control Table
--

        fomCommandControlTable  OBJECT-TYPE
            SYNTAX  SEQUENCE OF FomCommandControlEntry
            ACCESS  not-accessible
            STATUS  mandatory
            DESCRIPTION
                "The command control table."
            ::= { fom1card 5 }

        fomCommandControlEntry  OBJECT-TYPE
            SYNTAX  FomCommandControlEntry
            ACCESS  not-accessible
            STATUS  mandatory
            DESCRIPTION
                "An entry in the command control table."
            INDEX { fomCCslot , fomCCport }
            ::= { fomCommandControlTable 1 }

        FomCommandControlEntry ::= SEQUENCE {
            fomCCslot                   LSSlotID,
            fomCCport                   PortID,
            fomClearAlarmHistory        INTEGER,
            fomClearOpticalError        INTEGER,
            fomClearE1CRCError          INTEGER,
            fomClearAllErrorCounters    INTEGER,
            fomUnitLoadDefault          INTEGER,
            fomClearPerformanceData     INTEGER
        }

        fomCCslot  OBJECT-TYPE
            SYNTAX  LSSlotID
            ACCESS  read-only
            STATUS  mandatory
            DESCRIPTION
                "1FOMA slot index"
            ::= { fomCommandControlEntry 1 }

        fomCCport  OBJECT-TYPE
            SYNTAX  PortID
            ACCESS  read-only
            STATUS  mandatory
            DESCRIPTION
                "Port 1 to 4, total 4 ports."
            ::= { fomCommandControlEntry 2 }

        fomClearAlarmHistory    OBJECT-TYPE
            SYNTAX  INTEGER {
                    no(0),
                    clear(1)
                }
            ACCESS  read-write
            STATUS  mandatory
            DESCRIPTION
                "Command: Clear Alarm History"
            ::= { fomCommandControlEntry 3 }

        fomClearOpticalError    OBJECT-TYPE
            SYNTAX  INTEGER {
                    no(0),
                    allCounters(1),
                    feCounter(2),
                    fcsCounter(3),
                    eocCounter(4)
                }
            ACCESS  read-write
            STATUS  mandatory
            DESCRIPTION
                "Command: Clear Optical Error Counter"
            ::= { fomCommandControlEntry 4 }

        fomClearE1CRCError    OBJECT-TYPE
            SYNTAX  INTEGER {
                    no(0),
                    clear(1)
                }
            ACCESS  read-write
            STATUS  mandatory
            DESCRIPTION
                "Command: Clear E1 CRC Error Counter"
            ::= { fomCommandControlEntry 5 }

        fomClearAllErrorCounters    OBJECT-TYPE
            SYNTAX  INTEGER {
                    no(0),
                    local(1),
                    remote(2)
                }
            ACCESS  read-write
            STATUS  mandatory
            DESCRIPTION
                "Command: Clear All Local or Remote Error Counters"
            ::= { fomCommandControlEntry 6 }

        fomUnitLoadDefault    OBJECT-TYPE
            SYNTAX  INTEGER {
                    no(0),
                    loadDefault(1)
                }
            ACCESS  read-write
            STATUS  mandatory
            DESCRIPTION
                "Command: Load Default Fom"
            ::= { fomCommandControlEntry 7 }

        fomClearPerformanceData    OBJECT-TYPE
            SYNTAX  INTEGER {
                    no(0),
                    clear(1)
                }
            ACCESS  read-write
            STATUS  mandatory
            DESCRIPTION
                "Command: Clear performance data"
            ::= { fomCommandControlEntry 8 }

--
--  SYSTEM Information Table
--

        fomSystemInfoTable  OBJECT-TYPE
            SYNTAX  SEQUENCE OF FomSystemInfoEntry
            ACCESS  not-accessible
            STATUS  mandatory
            DESCRIPTION
                "The system information table."
            ::= {fom1card 6 }

        fomSystemInfoEntry  OBJECT-TYPE
            SYNTAX  FomSystemInfoEntry
            ACCESS  not-accessible
            STATUS  mandatory
            DESCRIPTION
                "An entry in the system information table."
            INDEX { fomSIslot }
            ::= { fomSystemInfoTable 1 }

        FomSystemInfoEntry ::= SEQUENCE {
            fomSIslot                   LSSlotID,
            fomFPGAVersion              DisplayString,
            fomPCBVersion               DisplayString,
            fomLinkID                   INTEGER,
            fomRemoteLinkID             INTEGER
        }

        fomSIslot  OBJECT-TYPE
            SYNTAX  LSSlotID
            ACCESS  read-only
            STATUS  mandatory
            DESCRIPTION
                "1FOMA slot index"
            ::= { fomSystemInfoEntry 1 }

        fomFPGAVersion  OBJECT-TYPE
            SYNTAX  DisplayString
            ACCESS  read-only
            STATUS  mandatory
            DESCRIPTION
                " Fom FPGA Version"
            ::= { fomSystemInfoEntry 2 }

        fomPCBVersion  OBJECT-TYPE
            SYNTAX  DisplayString
            ACCESS  read-only
            STATUS  mandatory
            DESCRIPTION
                " Fom PCB Version"
            ::= { fomSystemInfoEntry 3 }

        fomLinkID  OBJECT-TYPE
            SYNTAX  INTEGER
            ACCESS  read-only
            STATUS  mandatory
            DESCRIPTION
                " Local Link ID or Serial Number "
            ::= { fomSystemInfoEntry 4 }

        fomRemoteLinkID  OBJECT-TYPE
            SYNTAX  INTEGER{
                    notAvailable(0)
                }
            ACCESS  read-only
            STATUS  mandatory
            DESCRIPTION
                " Remote Link ID or Serial Number "
            ::= { fomSystemInfoEntry 5 }

--
--  FOM Optical Type Table
--

        fomOpticalTypeTable  OBJECT-TYPE
            SYNTAX  SEQUENCE OF FomOpticalTypeEntry
            ACCESS  not-accessible
            STATUS  mandatory
            DESCRIPTION
                "The FOM Optical Type table."
            ::= { fom1card 7 }

        fomOpticalTypeEntry  OBJECT-TYPE
            SYNTAX  FomOpticalTypeEntry
            ACCESS  not-accessible
            STATUS  mandatory
            DESCRIPTION
                "An entry in the FOM Optical Type table."
            INDEX { fomOTslot }
            ::= { fomOpticalTypeTable 1 }

        FomOpticalTypeEntry ::= SEQUENCE {
            fomOTslot                   LSSlotID,
            fomOpticalOutline           INTEGER,
            fomOpticalType              INTEGER,
            fomOpticalXMTDistance       INTEGER
        }

        fomOTslot  OBJECT-TYPE
            SYNTAX  LSSlotID
            ACCESS  read-only
            STATUS  mandatory
            DESCRIPTION
                "1FOMA slot index"
            ::= { fomOpticalTypeEntry 1 }

        fomOpticalOutline  OBJECT-TYPE
            SYNTAX  INTEGER {
                    sc(1),
                    fc(2)
                }
            ACCESS  read-only
            STATUS  mandatory
            DESCRIPTION
                " Optical Outline "
            ::= { fomOpticalTypeEntry 2 }

        fomOpticalType  OBJECT-TYPE
            SYNTAX  INTEGER {
                    dual1310(1),
                    dual1550(2),
                    singleM(3),
                    singleS(4)
                }
            ACCESS  read-only
            STATUS  mandatory
            DESCRIPTION
                " Fom Optical Type "
            ::= { fomOpticalTypeEntry 3 }

        fomOpticalXMTDistance  OBJECT-TYPE
            SYNTAX  INTEGER {
                    small(1),
                    middle(2),
                    large(3),
                    other(4)
                }
            ACCESS  read-only
            STATUS  mandatory
            DESCRIPTION
                " Fom Optical XMT Distance "
            ::= { fomOpticalTypeEntry 4 }

--
--  FOM APSD Setup
--

        fomApsdSetupTable  OBJECT-TYPE
            SYNTAX  SEQUENCE OF FomApsdSetupEntry
            ACCESS  not-accessible
            STATUS  mandatory
            DESCRIPTION
                "The FOM APSD Setup table."
            ::= { fom1card 8 }

        fomApsdSetupEntry  OBJECT-TYPE
            SYNTAX  FomApsdSetupEntry
            ACCESS  not-accessible
            STATUS  mandatory
            DESCRIPTION
                "An entry in the FOM APSD Setup table."
            INDEX { fomASslot }
            ::= { fomApsdSetupTable 1 }

        FomApsdSetupEntry ::= SEQUENCE {
            fomASslot                   LSSlotID,
            fomApsdEnable               INTEGER,
            fomPulseRepeatTime          INTEGER,
            fomManualRestart            INTEGER,
            fomLaserStatus              INTEGER
        }

        fomASslot  OBJECT-TYPE
            SYNTAX  LSSlotID
            ACCESS  read-only
            STATUS  mandatory
            DESCRIPTION
                "1FOMA slot index"
            ::= { fomApsdSetupEntry 1 }

        fomApsdEnable  OBJECT-TYPE
            SYNTAX  INTEGER {
                    off(1),
                    on(2)
                }
            ACCESS  read-write
            STATUS  mandatory
            DESCRIPTION
                " Optical APSD Enable "
            ::= { fomApsdSetupEntry 2 }

        fomPulseRepeatTime  OBJECT-TYPE
            SYNTAX  INTEGER  (100..300)
            ACCESS  read-write
            STATUS  mandatory
            DESCRIPTION
                " Laser Pulse repetition time for automatic restart(sec) "
            ::= { fomApsdSetupEntry 3 }

        fomManualRestart  OBJECT-TYPE
            SYNTAX  INTEGER {
                    off(1),
                    start(2)
                }
            ACCESS  read-write
            STATUS  mandatory
            DESCRIPTION
                " Laser Manual Restart "
            ::= { fomApsdSetupEntry 4 }

        fomLaserStatus  OBJECT-TYPE
            SYNTAX  INTEGER {
                    laserOn(1),
                    laserOff(2)
                }
            ACCESS  read-only
            STATUS  mandatory
            DESCRIPTION
                " Laser Status "
            ::= { fomApsdSetupEntry 5 }

--
--  FOM Current Performance Table
--

    fomCurrentPerformance OBJECT IDENTIFIER ::= { fom1card 9 }

--
-- FOM Optical Current Performance Table
--
        fomOptCurrentPerfTable  OBJECT-TYPE
            SYNTAX  SEQUENCE OF FomOptCurrentPerfEntry
            ACCESS  not-accessible
            STATUS  mandatory
            DESCRIPTION
                "FOM Optical Current Performance Table"
            ::= { fomCurrentPerformance 1 }

        fomOptCurrentPerfEntry  OBJECT-TYPE
            SYNTAX  FomOptCurrentPerfEntry
            ACCESS  not-accessible
            STATUS  mandatory
            DESCRIPTION
                "FOM Optical current performance entry"
            INDEX { fomOCPslot }
            ::= { fomOptCurrentPerfTable 1 }

        FomOptCurrentPerfEntry ::= SEQUENCE  {
            fomOCPslot                  LSSlotID,
            fomOptCurrentPerfES     INTEGER,
            fomOptCurrentPerfSES    INTEGER,
            fomOptCurrentPerfUAS    INTEGER,
            fomOptCurr15MinTimeElapsed  INTEGER,
            fomOptValid15MinInterval    INTEGER
        }

        fomOCPslot  OBJECT-TYPE
            SYNTAX  LSSlotID
            ACCESS  read-only
            STATUS  mandatory
            DESCRIPTION
                "1FOMA slot index"
            ::= { fomOptCurrentPerfEntry 1 }

        fomOptCurrentPerfES  OBJECT-TYPE
            SYNTAX  INTEGER
            ACCESS  read-only
            STATUS  mandatory
            DESCRIPTION
                " ESS Error Counter "
            ::= { fomOptCurrentPerfEntry 2 }

        fomOptCurrentPerfSES  OBJECT-TYPE
            SYNTAX  INTEGER
            ACCESS  read-only
            STATUS  mandatory
            DESCRIPTION
                " SES Error Counter "
            ::= { fomOptCurrentPerfEntry 3 }

        fomOptCurrentPerfUAS  OBJECT-TYPE
            SYNTAX  INTEGER
            ACCESS  read-only
            STATUS  mandatory
            DESCRIPTION
                " UAS Error Counter "
            ::= { fomOptCurrentPerfEntry 4 }

        fomOptCurr15MinTimeElapsed  OBJECT-TYPE
            SYNTAX  INTEGER
            ACCESS  read-only
            STATUS  mandatory
            DESCRIPTION
                " Current 15-minute time elapsed"
            ::= { fomOptCurrentPerfEntry 5 }

        fomOptValid15MinInterval  OBJECT-TYPE
            SYNTAX  INTEGER
            ACCESS  read-only
            STATUS  mandatory
            DESCRIPTION
                " Current 1-day Valid 15-min interval"
            ::= { fomOptCurrentPerfEntry 6 }

--
-- FOM E1 Current Performance Table
--
        fomE1CurrentPerfTable  OBJECT-TYPE
            SYNTAX  SEQUENCE OF FomE1CurrentPerfEntry
            ACCESS  not-accessible
            STATUS  mandatory
            DESCRIPTION
                "FOM E1 Current Performance Table"
            ::= { fomCurrentPerformance 2 }

        fomE1CurrentPerfEntry  OBJECT-TYPE
            SYNTAX  FomE1CurrentPerfEntry
            ACCESS  not-accessible
            STATUS  mandatory
            DESCRIPTION
                "FOM E1 current performance entry"
            INDEX { fomECPslot , fomECPport }
            ::= { fomE1CurrentPerfTable 1 }

        FomE1CurrentPerfEntry ::= SEQUENCE  {
            fomECPslot                  LSSlotID,
            fomECPport                  PortID,
            fomE1CurrentPerfES          INTEGER,
            fomE1CurrentPerfSES         INTEGER,
            fomE1CurrentPerfUAS         INTEGER,
            fomE1CurrentPerfCRC         INTEGER,
            fomE1Curr15MinTimeElapsed   INTEGER,
            fomE1Valid15MinInterval     INTEGER
        }

        fomECPslot  OBJECT-TYPE
            SYNTAX  LSSlotID
            ACCESS  read-only
            STATUS  mandatory
            DESCRIPTION
                "1FOMA slot index"
            ::= { fomE1CurrentPerfEntry 1 }

        fomECPport  OBJECT-TYPE
            SYNTAX  PortID
            ACCESS  read-only
            STATUS  mandatory
            DESCRIPTION
                "Port 1 to 4, total 4 ports."
            ::= { fomE1CurrentPerfEntry 2 }

        fomE1CurrentPerfES  OBJECT-TYPE
            SYNTAX  INTEGER
            ACCESS  read-only
            STATUS  mandatory
            DESCRIPTION
                " ESS Error Counter "
            ::= { fomE1CurrentPerfEntry 3 }

        fomE1CurrentPerfSES  OBJECT-TYPE
            SYNTAX  INTEGER
            ACCESS  read-only
            STATUS  mandatory
            DESCRIPTION
                " SES Error Counter "
            ::= { fomE1CurrentPerfEntry 4 }

        fomE1CurrentPerfUAS  OBJECT-TYPE
            SYNTAX  INTEGER
            ACCESS  read-only
            STATUS  mandatory
            DESCRIPTION
                " UAS Error Counter "
            ::= { fomE1CurrentPerfEntry 5 }

        fomE1CurrentPerfCRC  OBJECT-TYPE
            SYNTAX  INTEGER
            ACCESS  read-only
            STATUS  mandatory
            DESCRIPTION
                " CRC Error Counter "
            ::= { fomE1CurrentPerfEntry 6 }

        fomE1Curr15MinTimeElapsed  OBJECT-TYPE
            SYNTAX  INTEGER
            ACCESS  read-only
            STATUS  mandatory
            DESCRIPTION
                " Current 15-minute time elapsed"
            ::= { fomE1CurrentPerfEntry 7 }

        fomE1Valid15MinInterval  OBJECT-TYPE
            SYNTAX  INTEGER
            ACCESS  read-only
            STATUS  mandatory
            DESCRIPTION
                " Current 1-day Valid 15-min interval"
            ::= { fomE1CurrentPerfEntry 8 }

--
--  FOM Interval Performance Table
--

    fomIntervalPerformance  OBJECT IDENTIFIER ::= { fom1card 10 }

--
--  FOM Optical Interval Performance Table
--

        fomOptIntervalPerfTable  OBJECT-TYPE
            SYNTAX  SEQUENCE OF FomOptIntervalPerEntry
            ACCESS  not-accessible
            STATUS  mandatory
            DESCRIPTION
                "FOM Optical Interval Performance Table"
            ::= { fomIntervalPerformance 1 }

        fomOptIntervalPerEntry  OBJECT-TYPE
            SYNTAX  FomOptIntervalPerEntry
            ACCESS  not-accessible
            STATUS  mandatory
            DESCRIPTION
                "FOM Optical interval performance entry"
            INDEX { fomOIPslot , fomOptIntervalNo }
            ::= { fomOptIntervalPerfTable 1 }

        FomOptIntervalPerEntry ::= SEQUENCE {
            fomOIPslot                  LSSlotID,
            fomOptIntervalNo            INTEGER,
            fomOptIntervalPerfES    INTEGER,
            fomOptIntervalPerfSES   INTEGER,
            fomOptIntervalPerfUAS   INTEGER
        }

        fomOIPslot  OBJECT-TYPE
            SYNTAX  LSSlotID
            ACCESS  read-only
            STATUS  mandatory
            DESCRIPTION
                "1FOMA slot index"
            ::= { fomOptIntervalPerEntry 1 }

        fomOptIntervalNo  OBJECT-TYPE
            SYNTAX  INTEGER (1..96)
            ACCESS  read-only
            STATUS  mandatory
            DESCRIPTION
                " Interval Index "
            ::= { fomOptIntervalPerEntry 2 }

        fomOptIntervalPerfES  OBJECT-TYPE
            SYNTAX  INTEGER
            ACCESS  read-only
            STATUS  mandatory
            DESCRIPTION
                " ES Error Counter "
            ::= { fomOptIntervalPerEntry 3 }

        fomOptIntervalPerfSES  OBJECT-TYPE
            SYNTAX  INTEGER
            ACCESS  read-only
            STATUS  mandatory
            DESCRIPTION
                " SES Error Counter "
            ::= { fomOptIntervalPerEntry 4 }

        fomOptIntervalPerfUAS  OBJECT-TYPE
            SYNTAX  INTEGER
            ACCESS  read-only
            STATUS  mandatory
            DESCRIPTION
                " UAS Error Counter "
            ::= { fomOptIntervalPerEntry 5 }

--
--  FOM E1 Interval Performance Table
--

        fomE1IntervalPerfTable  OBJECT-TYPE
            SYNTAX  SEQUENCE OF FomE1IntervalPerEntry
            ACCESS  not-accessible
            STATUS  mandatory
            DESCRIPTION
                "FOM E1 Interval Performance Table"
            ::= { fomIntervalPerformance 2 }

        fomE1IntervalPerEntry  OBJECT-TYPE
            SYNTAX  FomE1IntervalPerEntry
            ACCESS  not-accessible
            STATUS  mandatory
            DESCRIPTION
                "FOM E1 interval performance entry"
            INDEX { fomEIPslot , fomEIPport ,
                    fomE1IntervalNo }
            ::= { fomE1IntervalPerfTable 1 }

        FomE1IntervalPerEntry ::= SEQUENCE {
            fomEIPslot                  LSSlotID,
            fomEIPport                  PortID,
            fomE1IntervalNo             INTEGER,
            fomE1IntervalPerfES         INTEGER,
            fomE1IntervalPerfSES        INTEGER,
            fomE1IntervalPerfUAS        INTEGER,
            fomE1IntervalPerfCRC        INTEGER
        }

        fomEIPslot  OBJECT-TYPE
            SYNTAX  LSSlotID
            ACCESS  read-only
            STATUS  mandatory
            DESCRIPTION
                "1FOMA slot index"
            ::= { fomE1IntervalPerEntry 1 }

        fomEIPport  OBJECT-TYPE
            SYNTAX  PortID
            ACCESS  read-only
            STATUS  mandatory
            DESCRIPTION
                "Port 1 to 4, total 4 ports."
            ::= { fomE1IntervalPerEntry 2 }

        fomE1IntervalNo  OBJECT-TYPE
            SYNTAX  INTEGER (1..96)
            ACCESS  read-only
            STATUS  mandatory
            DESCRIPTION
                " Interval Index "
            ::= { fomE1IntervalPerEntry 3 }

        fomE1IntervalPerfES  OBJECT-TYPE
            SYNTAX  INTEGER
            ACCESS  read-only
            STATUS  mandatory
            DESCRIPTION
                " ES Error Counter "
            ::= { fomE1IntervalPerEntry 4 }

        fomE1IntervalPerfSES  OBJECT-TYPE
            SYNTAX  INTEGER
            ACCESS  read-only
            STATUS  mandatory
            DESCRIPTION
                " SES Error Counter "
            ::= { fomE1IntervalPerEntry 5 }

        fomE1IntervalPerfUAS  OBJECT-TYPE
            SYNTAX  INTEGER
            ACCESS  read-only
            STATUS  mandatory
            DESCRIPTION
                " UAS Error Counter "
            ::= { fomE1IntervalPerEntry 6 }

        fomE1IntervalPerfCRC  OBJECT-TYPE
            SYNTAX  INTEGER
            ACCESS  read-only
            STATUS  mandatory
            DESCRIPTION
                " CRC Error Counter "
            ::= { fomE1IntervalPerEntry 7 }

--
--  FOM Total Performance Table
--

    fomTotalPerformance   OBJECT IDENTIFIER ::= { fom1card 11 }

--
--  FOM Optical Total Performance Table
--

        fomOptTotalPerfTable  OBJECT-TYPE
            SYNTAX  SEQUENCE OF FomOptTotalPerfEntry
            ACCESS  not-accessible
            STATUS  mandatory
            DESCRIPTION
                "FOM Optical Total Performance Table"
            ::= { fomTotalPerformance 1 }

        fomOptTotalPerfEntry  OBJECT-TYPE
            SYNTAX  FomOptTotalPerfEntry
            ACCESS  not-accessible
            STATUS  mandatory
            DESCRIPTION
                "FOM Optical Total performance table"
            INDEX { fomOTPslot }
            ::= { fomOptTotalPerfTable 1 }

        FomOptTotalPerfEntry ::= SEQUENCE  {
            fomOTPslot                  LSSlotID,
            fomOptTotalPerfES       INTEGER,
            fomOptTotalPerfSES      INTEGER,
            fomOptTotalPerfUAS      INTEGER
        }

        fomOTPslot  OBJECT-TYPE
            SYNTAX  LSSlotID
            ACCESS  read-only
            STATUS  mandatory
            DESCRIPTION
                "1FOMA slot index"
            ::= { fomOptTotalPerfEntry 1 }

        fomOptTotalPerfES  OBJECT-TYPE
            SYNTAX  INTEGER
            ACCESS  read-only
            STATUS  mandatory
            DESCRIPTION
                " ES Error Counter "
            ::= { fomOptTotalPerfEntry 2 }

        fomOptTotalPerfSES  OBJECT-TYPE
            SYNTAX  INTEGER
            ACCESS  read-only
            STATUS  mandatory
            DESCRIPTION
                " SES Error Counter "
            ::= { fomOptTotalPerfEntry 3 }

        fomOptTotalPerfUAS  OBJECT-TYPE
            SYNTAX  INTEGER
            ACCESS  read-only
            STATUS  mandatory
            DESCRIPTION
                " UAS Error Counter "
            ::= { fomOptTotalPerfEntry 4 }

--
--  FOM E1 Total Performance Table
--

        fomE1TotalPerfTable  OBJECT-TYPE
            SYNTAX  SEQUENCE OF FomE1TotalPerfEntry
            ACCESS  not-accessible
            STATUS  mandatory
            DESCRIPTION
                "FOM E1 Total Performance Table"
            ::= { fomTotalPerformance 2 }

        fomE1TotalPerfEntry  OBJECT-TYPE
            SYNTAX  FomE1TotalPerfEntry
            ACCESS  not-accessible
            STATUS  mandatory
            DESCRIPTION
                "FOM E1 Total performance table"
            INDEX { fomETPslot , fomETPport }
            ::= { fomE1TotalPerfTable 1 }

        FomE1TotalPerfEntry ::= SEQUENCE  {
            fomETPslot                  LSSlotID,
            fomETPport                  PortID,
            fomE1TotalPerfES            INTEGER,
            fomE1TotalPerfSES           INTEGER,
            fomE1TotalPerfUAS           INTEGER,
            fomE1TotalPerfCRC           INTEGER
        }

        fomETPslot  OBJECT-TYPE
            SYNTAX  LSSlotID
            ACCESS  read-only
            STATUS  mandatory
            DESCRIPTION
                "1FOMA slot index"
            ::= { fomE1TotalPerfEntry 1 }

        fomETPport  OBJECT-TYPE
            SYNTAX  PortID
            ACCESS  read-only
            STATUS  mandatory
            DESCRIPTION
                "Port 1 to 4, total 4 ports."
            ::= { fomE1TotalPerfEntry 2 }

        fomE1TotalPerfES  OBJECT-TYPE
            SYNTAX  INTEGER
            ACCESS  read-only
            STATUS  mandatory
            DESCRIPTION
                " ES Error Counter "
            ::= { fomE1TotalPerfEntry 3 }

        fomE1TotalPerfSES  OBJECT-TYPE
            SYNTAX  INTEGER
            ACCESS  read-only
            STATUS  mandatory
            DESCRIPTION
                " SES Error Counter "
            ::= { fomE1TotalPerfEntry 4 }

        fomE1TotalPerfUAS  OBJECT-TYPE
            SYNTAX  INTEGER
            ACCESS  read-only
            STATUS  mandatory
            DESCRIPTION
                " UAS Error Counter "
            ::= { fomE1TotalPerfEntry 5 }

        fomE1TotalPerfCRC  OBJECT-TYPE
            SYNTAX  INTEGER
            ACCESS  read-only
            STATUS  mandatory
            DESCRIPTION
                " CRC Error Counter "
            ::= { fomE1TotalPerfEntry 6 }

--
--  FOM Seven Days Performance Table
--

    fomSevenDaysPerformance   OBJECT IDENTIFIER ::= { fom1card 12 }

--
--  FOM Optical Seven Days Performance Table
--
        fomOptSevenDaysPerfTable  OBJECT-TYPE
            SYNTAX  SEQUENCE OF FomOptSevenDaysPerfEntry
            ACCESS  not-accessible
            STATUS  mandatory
            DESCRIPTION
                "FOM Optical 7 Days Performance Table"
            ::= { fomSevenDaysPerformance 1 }

        fomOptSevenDaysPerfEntry  OBJECT-TYPE
            SYNTAX  FomOptSevenDaysPerfEntry
            ACCESS  not-accessible
            STATUS  mandatory
            DESCRIPTION
                "FOM Optical 7 days performance entry"
            INDEX { fomOSDslot , fomOptDaysIndex }
            ::= { fomOptSevenDaysPerfTable 1 }

        FomOptSevenDaysPerfEntry ::= SEQUENCE  {
            fomOSDslot                  LSSlotID,
            fomOptDaysIndex             INTEGER,
            fomOptDateString            DisplayString,
            fomOptSevenDaysPerfES   INTEGER,
            fomOptSevenDaysPerfSES  INTEGER,
            fomOptSevenDaysPerfUAS  INTEGER
        }

        fomOSDslot  OBJECT-TYPE
            SYNTAX  LSSlotID
            ACCESS  read-only
            STATUS  mandatory
            DESCRIPTION
                "1FOMA slot index"
            ::= { fomOptSevenDaysPerfEntry 1 }

        fomOptDaysIndex  OBJECT-TYPE
            SYNTAX  INTEGER (1..7)
            ACCESS  read-only
            STATUS  mandatory
            DESCRIPTION
                "Seven Days index "
            ::= { fomOptSevenDaysPerfEntry 2 }

        fomOptDateString  OBJECT-TYPE
            SYNTAX  DisplayString
            ACCESS  read-only
            STATUS  mandatory
            DESCRIPTION
                "Seven Days String "
            ::= { fomOptSevenDaysPerfEntry 3 }

        fomOptSevenDaysPerfES  OBJECT-TYPE
            SYNTAX  INTEGER
            ACCESS  read-only
            STATUS  mandatory
            DESCRIPTION
                " ES Error Counter "
            ::= { fomOptSevenDaysPerfEntry 4 }

        fomOptSevenDaysPerfSES  OBJECT-TYPE
            SYNTAX  INTEGER
            ACCESS  read-only
            STATUS  mandatory
            DESCRIPTION
                " SES Error Counter "
            ::= { fomOptSevenDaysPerfEntry 5 }

        fomOptSevenDaysPerfUAS  OBJECT-TYPE
            SYNTAX  INTEGER
            ACCESS  read-only
            STATUS  mandatory
            DESCRIPTION
                " UAS Error Counter "
            ::= { fomOptSevenDaysPerfEntry 6 }

--
--  FOM E1 Seven Days Performance Table
--
        fomE1SevenDaysPerfTable  OBJECT-TYPE
            SYNTAX  SEQUENCE OF FomE1SevenDaysPerfEntry
            ACCESS  not-accessible
            STATUS  mandatory
            DESCRIPTION
                "FOM E1 7 Days Performance Table"
            ::= { fomSevenDaysPerformance 2 }

        fomE1SevenDaysPerfEntry  OBJECT-TYPE
            SYNTAX  FomE1SevenDaysPerfEntry
            ACCESS  not-accessible
            STATUS  mandatory
            DESCRIPTION
                "FOM E1 7 days performance entry"
            INDEX { fomESDslot , fomESDport ,
                    fomE1DaysIndex }
            ::= { fomE1SevenDaysPerfTable 1 }

        FomE1SevenDaysPerfEntry ::= SEQUENCE  {
            fomESDslot                  LSSlotID,
            fomESDport                  PortID,
            fomE1DaysIndex              INTEGER,
            fomE1DateString             DisplayString,
            fomE1SevenDaysPerfES        INTEGER,
            fomE1SevenDaysPerfSES       INTEGER,
            fomE1SevenDaysPerfUAS       INTEGER,
            fomE1SevenDaysPerfCRC       INTEGER
        }

        fomESDslot  OBJECT-TYPE
            SYNTAX  LSSlotID
            ACCESS  read-only
            STATUS  mandatory
            DESCRIPTION
                "1FOMA slot index"
            ::= { fomE1SevenDaysPerfEntry 1 }

        fomESDport  OBJECT-TYPE
            SYNTAX  PortID
            ACCESS  read-only
            STATUS  mandatory
            DESCRIPTION
                "Port 1 to 4, total 4 ports."
            ::= { fomE1SevenDaysPerfEntry 2 }

        fomE1DaysIndex  OBJECT-TYPE
            SYNTAX  INTEGER (1..7)
            ACCESS  read-only
            STATUS  mandatory
            DESCRIPTION
                "Seven Days index "
            ::= { fomE1SevenDaysPerfEntry 3 }

        fomE1DateString  OBJECT-TYPE
            SYNTAX  DisplayString
            ACCESS  read-only
            STATUS  mandatory
            DESCRIPTION
                "Seven Days String "
            ::= { fomE1SevenDaysPerfEntry 4 }

        fomE1SevenDaysPerfES  OBJECT-TYPE
            SYNTAX  INTEGER
            ACCESS  read-only
            STATUS  mandatory
            DESCRIPTION
                " ES Error Counter "
            ::= { fomE1SevenDaysPerfEntry 5 }

        fomE1SevenDaysPerfSES  OBJECT-TYPE
            SYNTAX  INTEGER
            ACCESS  read-only
            STATUS  mandatory
            DESCRIPTION
                " SES Error Counter "
            ::= { fomE1SevenDaysPerfEntry 6 }

        fomE1SevenDaysPerfUAS  OBJECT-TYPE
            SYNTAX  INTEGER
            ACCESS  read-only
            STATUS  mandatory
            DESCRIPTION
                " UAS Error Counter "
            ::= { fomE1SevenDaysPerfEntry 7 }

        fomE1SevenDaysPerfCRC  OBJECT-TYPE
            SYNTAX  INTEGER
            ACCESS  read-only
            STATUS  mandatory
            DESCRIPTION
                " CRC Error Counter "
            ::= { fomE1SevenDaysPerfEntry 8 }

        fom1TotalCard   OBJECT-TYPE
            SYNTAX  INTEGER
            ACCESS  read-only
            STATUS  mandatory
            DESCRIPTION
                "Total cards of FOM1"
            ::= { fom1card 100 }


--======================================================================--
--======================================================================--
--  LS-OPTICAL MIB
--======================================================================--
--======================================================================--

--
--  SYSTEM Control Table
--

        lsoSystemControlTable  OBJECT-TYPE
            SYNTAX  SEQUENCE OF LsoSystemControlEntry
            ACCESS  not-accessible
            STATUS  mandatory
            DESCRIPTION
                "LS-OPTICAL control table."
            ::= { ls-optical-card 1 }

        lsoSystemControlEntry  OBJECT-TYPE
            SYNTAX  LsoSystemControlEntry
            ACCESS  not-accessible
            STATUS  mandatory
            DESCRIPTION
                "An entry in the LS-OPTICAL control table."
            INDEX { lsoSCSlotIndex ,
                    lsoSCPortIndex }
            ::= { lsoSystemControlTable 1 }

        LsoSystemControlEntry ::= SEQUENCE  {
            lsoSCSlotIndex              LSSlotID,
            lsoSCPortIndex              PortID,
            lsoMode                     INTEGER,
            lsoReceiveBW                INTEGER,
            lsoTransmitBW               INTEGER,
            lsoALS                      INTEGER
        }

        lsoSCSlotIndex  OBJECT-TYPE
            SYNTAX  LSSlotID
            ACCESS  read-only
            STATUS  mandatory
            DESCRIPTION
                "LSO slot"
            ::= { lsoSystemControlEntry 1 }

        lsoSCPortIndex  OBJECT-TYPE
            SYNTAX  PortID
            ACCESS  read-only
            STATUS  mandatory
            DESCRIPTION
                "Port 1 to 4, total 4 ports."
            ::= { lsoSystemControlEntry 2 }

        lsoMode  OBJECT-TYPE
            SYNTAX  INTEGER   {
                    manual(1),
                    auto(2)
                }
            ACCESS  read-write
            STATUS  mandatory
            DESCRIPTION
                "LS-OPTICAL Mode"
            ::= { lsoSystemControlEntry 3 }

        lsoReceiveBW  OBJECT-TYPE
            SYNTAX  INTEGER (0..12)
            ACCESS  read-only
            STATUS  mandatory
            DESCRIPTION
                "LS-OPTICAL reveive bandwidth(0~12 TS)"
            ::= { lsoSystemControlEntry 4 }

        lsoTransmitBW  OBJECT-TYPE
            SYNTAX  INTEGER (0..12)
            ACCESS  read-write
            STATUS  mandatory
            DESCRIPTION
                "LS-OPTICAL transmit bandwidth(0~12 TS)"
            ::= { lsoSystemControlEntry 5 }

        lsoALS  OBJECT-TYPE
            SYNTAX  INTEGER   {
                    disable(1),
                    enable(2)
                }
            ACCESS  read-write
            STATUS  mandatory
            DESCRIPTION
                "LS-OPTICAL Auto Laser Shutdown(ALS)"
            ::= { lsoSystemControlEntry 6 }

--
--  Status Table
--

        lsoStatusTable  OBJECT-TYPE
            SYNTAX  SEQUENCE OF LsoStatusEntry
            ACCESS  not-accessible
            STATUS  mandatory
            DESCRIPTION
                "The LS-OPTICAL status table."
            ::= { ls-optical-card 2 }

        lsoStatusEntry  OBJECT-TYPE
            SYNTAX  LsoStatusEntry
            ACCESS  not-accessible
            STATUS  mandatory
            DESCRIPTION
                "An entry in the LS-OPTICAL status table."
            INDEX { lsoStSlotIndex ,
                    lsoStPortIndex }
            ::= { lsoStatusTable 1 }

        LsoStatusEntry ::= SEQUENCE {
            lsoStSlotIndex              LSSlotID,
            lsoStPortIndex              PortID,
            lsoLOS                      INTEGER,
            lsoYEL                      INTEGER,
            lsoFramingERR               INTEGER,
            lsoPayloadERR               INTEGER
        }

        lsoStSlotIndex  OBJECT-TYPE
            SYNTAX  LSSlotID
            ACCESS  read-only
            STATUS  mandatory
            DESCRIPTION
                "LSO slot"
            ::= { lsoStatusEntry 1 }

        lsoStPortIndex  OBJECT-TYPE
            SYNTAX  PortID
            ACCESS  read-only
            STATUS  mandatory
            DESCRIPTION
                "Port 1 to 4, total 4 ports."
            ::= { lsoStatusEntry 2 }

        lsoLOS  OBJECT-TYPE
            SYNTAX  INTEGER {
                    no(1),
                    yes(2)
                }
            ACCESS  read-only
            STATUS  mandatory
            DESCRIPTION
                " LS-OPTICAL Line LOS "
            ::= { lsoStatusEntry 3 }

        lsoYEL  OBJECT-TYPE
            SYNTAX  INTEGER {
                    no(1),
                    yel(2)
                }
            ACCESS  read-only
            STATUS  mandatory
            DESCRIPTION
                " LS-OPTICAL Line YEL "
            ::= { lsoStatusEntry 4 }

        lsoFramingERR  OBJECT-TYPE
            SYNTAX  INTEGER
            ACCESS  read-only
            STATUS  mandatory
            DESCRIPTION
                " LS-OPTICAL Framing Error Counter "
            ::= { lsoStatusEntry 5 }

        lsoPayloadERR  OBJECT-TYPE
            SYNTAX  INTEGER
            ACCESS  read-only
            STATUS  mandatory
            DESCRIPTION
                " LS-OPTICAL Payload Error Counter "
            ::= { lsoStatusEntry 6 }

--
-- Diagnostic Control Table
--

        lsoDiagTable  OBJECT-TYPE
            SYNTAX  SEQUENCE OF LsoDiagEntry
            ACCESS  not-accessible
            STATUS  mandatory
            DESCRIPTION
                "Diagnostic Control Table"
            ::= { ls-optical-card 3 }

        lsoDiagEntry  OBJECT-TYPE
            SYNTAX  LsoDiagEntry
            ACCESS  not-accessible
            STATUS  mandatory
            DESCRIPTION
                "Diagnostic Control Table Entry"
            INDEX { lsoDiagSlotIndex ,
                    lsoDiagPortIndex }
            ::= { lsoDiagTable 1 }

        LsoDiagEntry ::= SEQUENCE {
            lsoDiagSlotIndex            LSSlotID,
            lsoDiagPortIndex            PortID,
            lsoLoopback                 INTEGER
--               lsoBertControl
--                 INTEGER,
--               lsoBertStatus
--                 INTEGER,
--               lsoElapseSeconds
--                 INTEGER,
--               lsoErrorSeconds
--                 INTEGER,
--               lsoErrorBits
--                 INTEGER




    }

        lsoDiagSlotIndex  OBJECT-TYPE
            SYNTAX  LSSlotID
            ACCESS  read-only
            STATUS  mandatory
            DESCRIPTION
                "LSO slot"
            ::= { lsoDiagEntry 1 }

        lsoDiagPortIndex  OBJECT-TYPE
            SYNTAX  PortID
            ACCESS  read-only
            STATUS  mandatory
            DESCRIPTION
                "Port 1 to 4, total 4 ports."
            ::= { lsoDiagEntry 2 }

        lsoLoopback  OBJECT-TYPE
            SYNTAX  INTEGER {
                    no-loopback(1),
                    local-loopback(2),
                    payLoad-loopback(3),
                    line-loopback(4)
                }
            ACCESS  read-write
            STATUS  mandatory
            DESCRIPTION
                "Loopback Type"
            ::= { lsoDiagEntry 3 }

--         lsoBertControl  OBJECT-TYPE
--             SYNTAX  INTEGER {
--                        bert-off(1),
--                        bert-on(2),
--                        reset(3),
--                        inject-error(4)
--                     }
--             ACCESS  read-write
--             STATUS  mandatory
--             DESCRIPTION
--                "BERT Control"
--             ::= { lsoDiagEntry 4 }
--
--        lsoBertStatus  OBJECT-TYPE
--             SYNTAX  INTEGER {
--                        bert-sync(1),
--                        bert-unsync(2),
--                        bert-not-active(3)
--                     }
--             ACCESS  read-only
--             STATUS  mandatory
--             DESCRIPTION
--                "BERT Status"
--             ::= { lsoDiagEntry 5 }
--
--        lsoElapseSeconds  OBJECT-TYPE
--             SYNTAX  INTEGER
--             ACCESS  read-only
--             STATUS  mandatory
--             DESCRIPTION
--                "Elapse seconds"
--             ::= { lsoDiagEntry 6 }
--
--         lsoErrorSeconds OBJECT-TYPE
--             SYNTAX  INTEGER
--             ACCESS  read-only
--             STATUS  mandatory
--             DESCRIPTION
--                "Error seconds"
--             ::= { lsoDiagEntry 7 }
--
--         lsoErrorBits  OBJECT-TYPE
--             SYNTAX  INTEGER
--             ACCESS  read-only
--             STATUS  mandatory
--             DESCRIPTION
--                "Error bits"
--             ::= { lsoDiagEntry 8 }

--
-- Alarm Status Table
--

        lsoAlmStatusTable  OBJECT-TYPE
            SYNTAX  SEQUENCE OF LsoAlmStatusEntry
            ACCESS  not-accessible
            STATUS  mandatory
            DESCRIPTION
                "Alarm Status Table"
            ::= { ls-optical-card 4 }

        lsoAlmStatusEntry  OBJECT-TYPE
            SYNTAX  LsoAlmStatusEntry
            ACCESS  not-accessible
            STATUS  mandatory
            DESCRIPTION
                "Alarm Status Table Entry"
            INDEX { lsoASSlotIndex ,
                    lsoASPortIndex ,
                    lsoAlmNumber }
            ::= { lsoAlmStatusTable 1 }

        LsoAlmStatusEntry ::= SEQUENCE {
            lsoASSlotIndex              LSSlotID,
            lsoASPortIndex              PortID,
            lsoAlmNumber                INTEGER,
            lsoAlmString                DisplayString,
            lsoAlmState                 INTEGER,
            lsoAlmCount                 INTEGER,
            lsoAlmThreshold             INTEGER,
            lsoAlmEnable                LsAlarmSeverity
        }

        lsoASSlotIndex  OBJECT-TYPE
            SYNTAX  LSSlotID
            ACCESS  read-only
            STATUS  mandatory
            DESCRIPTION
                "LSO slot"
            ::= { lsoAlmStatusEntry 1 }

        lsoASPortIndex  OBJECT-TYPE
            SYNTAX  PortID
            ACCESS  read-only
            STATUS  mandatory
            DESCRIPTION
                "Port 1 to 4, total 4 ports."
            ::= { lsoAlmStatusEntry 2 }

        lsoAlmNumber  OBJECT-TYPE
            SYNTAX  INTEGER (1..40)
            ACCESS  read-only
            STATUS  mandatory
            DESCRIPTION
                "Alarm Status Index"
            ::= { lsoAlmStatusEntry 3 }

        lsoAlmString  OBJECT-TYPE
            SYNTAX  DisplayString (SIZE (0..80))
            ACCESS  read-only
            STATUS  mandatory
            DESCRIPTION
                "Alarm Type String"
            ::= { lsoAlmStatusEntry 4 }

        lsoAlmState  OBJECT-TYPE
            SYNTAX  INTEGER {
                    ok(1),
                    alarm(2),
                    disable(3),
                    none(4)
                }
            ACCESS  read-only
            STATUS  mandatory
            DESCRIPTION
                "Alarm Current State"
            ::= { lsoAlmStatusEntry 5 }

        lsoAlmCount  OBJECT-TYPE
            SYNTAX  INTEGER
            ACCESS  read-only
            STATUS  mandatory
            DESCRIPTION
                "Alarm Count which happened"
            ::= { lsoAlmStatusEntry 6 }

        lsoAlmThreshold  OBJECT-TYPE
            SYNTAX  INTEGER
            ACCESS  read-write
            STATUS  mandatory
            DESCRIPTION
                "Alarm Threshold"
            ::= { lsoAlmStatusEntry 7 }

        lsoAlmEnable  OBJECT-TYPE
            SYNTAX  LsAlarmSeverity
            ACCESS  read-write
            STATUS  mandatory
            DESCRIPTION
                "Alarm is enabled or not"
            ::= { lsoAlmStatusEntry 8 }

--
--  Command Control Table
--

        lsoCommandControlTable  OBJECT-TYPE
            SYNTAX  SEQUENCE OF LsoCommandControlEntry
            ACCESS  not-accessible
            STATUS  mandatory
            DESCRIPTION
                "The command control table."
            ::= { ls-optical-card 5 }

        lsoCommandControlEntry  OBJECT-TYPE
            SYNTAX  LsoCommandControlEntry
            ACCESS  not-accessible
            STATUS  mandatory
            DESCRIPTION
                "An entry in the command control table."
            INDEX { lsoCCSlotIndex }
            ::= { lsoCommandControlTable 1 }

        LsoCommandControlEntry ::= SEQUENCE {
            lsoCCSlotIndex              LSSlotID,
--               lsoClearCardAlarmHistory
--                 INTEGER,
            lsoClearCardPerformanceData INTEGER,
            lsoCardLoadDefault          INTEGER
        }

        lsoCCSlotIndex  OBJECT-TYPE
            SYNTAX  LSSlotID
            ACCESS  read-only
            STATUS  mandatory
            DESCRIPTION
                "LSO slot"
            ::= { lsoCommandControlEntry 1 }

--         lsoClearCardAlarmHistory    OBJECT-TYPE
--             SYNTAX  INTEGER {
--                         clear(1)
--                     }
--             ACCESS  read-write
--             STATUS  mandatory
--             DESCRIPTION
--                "Clear Card Alarm History"
--             ::= { lsoCommandControlEntry 2 }

        lsoClearCardPerformanceData    OBJECT-TYPE
            SYNTAX  INTEGER {
                    clear(1)
                }
            ACCESS  read-write
            STATUS  mandatory
            DESCRIPTION
                "Clear card performance data"
            ::= { lsoCommandControlEntry 3 }

        lsoCardLoadDefault    OBJECT-TYPE
            SYNTAX  INTEGER {
                    load-default(1)
                }
            ACCESS  read-write
            STATUS  mandatory
            DESCRIPTION
                "Card Load Default"
            ::= { lsoCommandControlEntry 4 }

--
--  SYSTEM Information Table
--

        lsoSystemInfoTable  OBJECT-TYPE
            SYNTAX  SEQUENCE OF LsoSystemInformationEntry
            ACCESS  not-accessible
            STATUS  mandatory
            DESCRIPTION
                "The system information table."
            ::= {ls-optical-card 6 }

        lsoSystemInformationEntry  OBJECT-TYPE
            SYNTAX  LsoSystemInformationEntry
            ACCESS  not-accessible
            STATUS  mandatory
            DESCRIPTION
                "An entry in the system information table."
            INDEX { lsoSISlotIndex }
            ::= { lsoSystemInfoTable 1 }

        LsoSystemInformationEntry ::= SEQUENCE {
            lsoSISlotIndex              LSSlotID,
            lsoFPGAVersion              DisplayString,
            lsoPCBVersion               DisplayString,
            lsoBOMVersion               DisplayString,
            lsoPortNumber               INTEGER,
            lsoOpticalModule            DisplayString
        }

        lsoSISlotIndex  OBJECT-TYPE
            SYNTAX  LSSlotID
            ACCESS  read-only
            STATUS  mandatory
            DESCRIPTION
                "LSO slot"
            ::= { lsoSystemInformationEntry 1 }

        lsoFPGAVersion  OBJECT-TYPE
            SYNTAX  DisplayString (SIZE (0..255) )
            ACCESS  read-only
            STATUS  mandatory
            DESCRIPTION
                "FPGA Version"
            ::= { lsoSystemInformationEntry 2 }

        lsoPCBVersion  OBJECT-TYPE
            SYNTAX  DisplayString (SIZE (0..255) )
            ACCESS  read-only
            STATUS  mandatory
            DESCRIPTION
                "PCB Version"
            ::= { lsoSystemInformationEntry 3 }

        lsoBOMVersion  OBJECT-TYPE
            SYNTAX  DisplayString (SIZE (0..255) )
            ACCESS  read-only
            STATUS  mandatory
            DESCRIPTION
                "BOM Version"
            ::= { lsoSystemInformationEntry 4 }

        lsoPortNumber  OBJECT-TYPE
            SYNTAX  INTEGER
            ACCESS  read-only
            STATUS  mandatory
            DESCRIPTION
                "Number of port in card"
            ::= { lsoSystemInformationEntry 5 }

        lsoOpticalModule  OBJECT-TYPE
            SYNTAX  DisplayString (SIZE (0..59) )
            ACCESS  read-only
            STATUS  mandatory
            DESCRIPTION
                "Optical module type"
            ::= { lsoSystemInformationEntry 6 }

--
--  Performance Table
--
    lsoPerformanceReport         OBJECT IDENTIFIER ::= { ls-optical-card 7 }

--
-- Current Performance Table
--
        lsoCurrentPerfTable  OBJECT-TYPE
            SYNTAX  SEQUENCE OF LsoCurrentPerfEntry
            ACCESS  not-accessible
            STATUS  mandatory
            DESCRIPTION
                "Current Performance Table"
            ::= { lsoPerformanceReport 1 }

        lsoCurrentPerfEntry  OBJECT-TYPE
            SYNTAX  LsoCurrentPerfEntry
            ACCESS  not-accessible
            STATUS  mandatory
            DESCRIPTION
                "Current performance entry"
            INDEX { lsoCPSlotIndex ,
                    lsoCPPortIndex ,
                    lsoCurrPerfRegType }
            ::= { lsoCurrentPerfTable 1 }

        LsoCurrentPerfEntry ::= SEQUENCE  {
            lsoCPSlotIndex              LSSlotID,
            lsoCPPortIndex              PortID,
            lsoCurrPerfRegType          INTEGER,
            lsoCurrentPerfES            INTEGER,
            lsoCurrentPerfSES           INTEGER,
            lsoCurrentPerfUAS           INTEGER,
            lsoCurr15MinTimeElapsed     INTEGER,
            lsoValid15MinInterval       INTEGER
        }

        lsoCPSlotIndex  OBJECT-TYPE
            SYNTAX  LSSlotID
            ACCESS  read-only
            STATUS  mandatory
            DESCRIPTION
                "LSO slot"
            ::= { lsoCurrentPerfEntry 1 }

        lsoCPPortIndex  OBJECT-TYPE
            SYNTAX  PortID
            ACCESS  read-only
            STATUS  mandatory
            DESCRIPTION
                "Port 1 to 4, total 4 ports."
            ::= { lsoCurrentPerfEntry 2 }

        lsoCurrPerfRegType  OBJECT-TYPE
            SYNTAX  INTEGER {
                    user(1),
                    line(2)
                }
            ACCESS  read-only
            STATUS  mandatory
            DESCRIPTION
                " Performance Register Type "
            ::= { lsoCurrentPerfEntry 3 }

        lsoCurrentPerfES  OBJECT-TYPE
            SYNTAX  INTEGER
            ACCESS  read-only
            STATUS  mandatory
            DESCRIPTION
                " ESS Error Counter "
            ::= { lsoCurrentPerfEntry 4 }

        lsoCurrentPerfSES  OBJECT-TYPE
            SYNTAX  INTEGER
            ACCESS  read-only
            STATUS  mandatory
            DESCRIPTION
                " SES Error Counter "
            ::= { lsoCurrentPerfEntry 5 }

        lsoCurrentPerfUAS  OBJECT-TYPE
            SYNTAX  INTEGER
            ACCESS  read-only
            STATUS  mandatory
            DESCRIPTION
                " UAS Error Counter "
            ::= { lsoCurrentPerfEntry 6 }

        lsoCurr15MinTimeElapsed  OBJECT-TYPE
            SYNTAX  INTEGER
            ACCESS  read-only
            STATUS  mandatory
            DESCRIPTION
                " Current 15-minute time elapsed"
            ::= { lsoCurrentPerfEntry 7 }

        lsoValid15MinInterval  OBJECT-TYPE
            SYNTAX  INTEGER
            ACCESS  read-only
            STATUS  mandatory
            DESCRIPTION
                " Current 1-day Valid 15-min interval"
            ::= { lsoCurrentPerfEntry 8 }

--
--  Interval Performance Table
--

        lsoIntervalPerfTable  OBJECT-TYPE
            SYNTAX  SEQUENCE OF LsoIntervalPerfEntry
            ACCESS  not-accessible
            STATUS  mandatory
            DESCRIPTION
                "Interval Performance Table"
            ::= { lsoPerformanceReport 2 }

        lsoIntervalPerfEntry  OBJECT-TYPE
            SYNTAX  LsoIntervalPerfEntry
            ACCESS  not-accessible
            STATUS  mandatory
            DESCRIPTION
                "FOM Optical interval performance entry"
            INDEX { lsoIPSlotIndex ,
                    lsoIPPortIndex ,
                    lsoIntvPerfRegType ,
                    lsoIntervalPerfNumber }
            ::= { lsoIntervalPerfTable 1 }

        LsoIntervalPerfEntry ::= SEQUENCE {
            lsoIPSlotIndex              LSSlotID,
            lsoIPPortIndex              PortID,
            lsoIntvPerfRegType          INTEGER,
            lsoIntervalPerfNumber       INTEGER  (1..96),
            lsoIntervalPerfES           INTEGER,
            lsoIntervalPerfSES          INTEGER,
            lsoIntervalPerfUAS          INTEGER
        }

        lsoIPSlotIndex  OBJECT-TYPE
            SYNTAX  LSSlotID
            ACCESS  read-only
            STATUS  mandatory
            DESCRIPTION
                "LSO slot"
            ::= { lsoIntervalPerfEntry 1 }

        lsoIPPortIndex  OBJECT-TYPE
            SYNTAX  PortID
            ACCESS  read-only
            STATUS  mandatory
            DESCRIPTION
                "Port 1 to 4, total 4 ports."
            ::= { lsoIntervalPerfEntry 2 }

        lsoIntvPerfRegType  OBJECT-TYPE
            SYNTAX  INTEGER {
                    user(1),
                    line(2)
                }
            ACCESS  read-only
            STATUS  mandatory
            DESCRIPTION
                " Performance Register Type "
            ::= { lsoIntervalPerfEntry 3 }

        lsoIntervalPerfNumber  OBJECT-TYPE
            SYNTAX  INTEGER (1..96)
            ACCESS  read-only
            STATUS  mandatory
            DESCRIPTION
                " Interval Index "
            ::= { lsoIntervalPerfEntry 4 }

        lsoIntervalPerfES  OBJECT-TYPE
            SYNTAX  INTEGER
            ACCESS  read-only
            STATUS  mandatory
            DESCRIPTION
                " ES Error Counter "
            ::= { lsoIntervalPerfEntry 5 }

        lsoIntervalPerfSES  OBJECT-TYPE
            SYNTAX  INTEGER
            ACCESS  read-only
            STATUS  mandatory
            DESCRIPTION
                " SES Error Counter "
            ::= { lsoIntervalPerfEntry 6 }

        lsoIntervalPerfUAS  OBJECT-TYPE
            SYNTAX  INTEGER
            ACCESS  read-only
            STATUS  mandatory
            DESCRIPTION
                " UAS Error Counter "
            ::= { lsoIntervalPerfEntry 7 }

--
--  Total Performance Table
--

        lsoTotalPerfTable  OBJECT-TYPE
            SYNTAX  SEQUENCE OF LsoTotalPerfEntry
            ACCESS  not-accessible
            STATUS  mandatory
            DESCRIPTION
                "Total Performance Table"
            ::= { lsoPerformanceReport 3 }

        lsoTotalPerfEntry  OBJECT-TYPE
            SYNTAX  LsoTotalPerfEntry
            ACCESS  not-accessible
            STATUS  mandatory
            DESCRIPTION
                "Total performance table"
            INDEX { lsoTPSlotIndex ,
                    lsoTPPortIndex ,
                    lsoTotalPerfRegType }
            ::= { lsoTotalPerfTable 1 }

        LsoTotalPerfEntry ::= SEQUENCE  {
            lsoTPSlotIndex              LSSlotID,
            lsoTPPortIndex              PortID,
            lsoTotalPerfRegType         INTEGER,
            lsoTotalPerfES              INTEGER,
            lsoTotalPerfSES             INTEGER,
            lsoTotalPerfUAS             INTEGER
        }

        lsoTPSlotIndex  OBJECT-TYPE
            SYNTAX  LSSlotID
            ACCESS  read-only
            STATUS  mandatory
            DESCRIPTION
                "LSO slot"
            ::= { lsoTotalPerfEntry 1 }

        lsoTPPortIndex  OBJECT-TYPE
            SYNTAX  PortID
            ACCESS  read-only
            STATUS  mandatory
            DESCRIPTION
                "Port 1 to 4, total 4 ports."
            ::= { lsoTotalPerfEntry 2 }

        lsoTotalPerfRegType  OBJECT-TYPE
            SYNTAX  INTEGER {
                    user(1),
                    line(2)
                }
            ACCESS  read-only
            STATUS  mandatory
            DESCRIPTION
                " Performance Register Type "
            ::= { lsoTotalPerfEntry 3 }

        lsoTotalPerfES  OBJECT-TYPE
            SYNTAX  INTEGER
            ACCESS  read-only
            STATUS  mandatory
            DESCRIPTION
                " ES Error Counter "
            ::= { lsoTotalPerfEntry 4 }

        lsoTotalPerfSES  OBJECT-TYPE
            SYNTAX  INTEGER
            ACCESS  read-only
            STATUS  mandatory
            DESCRIPTION
                " SES Error Counter "
            ::= { lsoTotalPerfEntry 5 }

        lsoTotalPerfUAS  OBJECT-TYPE
            SYNTAX  INTEGER
            ACCESS  read-only
            STATUS  mandatory
            DESCRIPTION
                " UAS Error Counter "
            ::= { lsoTotalPerfEntry 6 }

--
--  Seven Days Performance Table
--
        lsoSevenDaysPerfTable  OBJECT-TYPE
            SYNTAX  SEQUENCE OF LsoSevenDaysPerfEntry
            ACCESS  not-accessible
            STATUS  mandatory
            DESCRIPTION
                "7 Days Performance Table"
            ::= { lsoPerformanceReport 4 }

        lsoSevenDaysPerfEntry  OBJECT-TYPE
            SYNTAX  LsoSevenDaysPerfEntry
            ACCESS  not-accessible
            STATUS  mandatory
            DESCRIPTION
                "7 days performance entry"
            INDEX { lsoDPSlotIndex ,
                    lsoDPPortIndex ,
                    lsoSevenDaysPerfRegType ,
                    lsoDaysIndex }
            ::= { lsoSevenDaysPerfTable 1 }

        LsoSevenDaysPerfEntry ::= SEQUENCE  {
            lsoDPSlotIndex              LSSlotID,
            lsoDPPortIndex              PortID,
            lsoSevenDaysPerfRegType     INTEGER,
            lsoDaysIndex                INTEGER (1..7),
            lsoDateStrIndex             DisplayString (SIZE (0..255) ),
            lsoSevenDaysPerfES          INTEGER,
            lsoSevenDaysPerfSES         INTEGER,
            lsoSevenDaysPerfUAS         INTEGER
        }

        lsoDPSlotIndex  OBJECT-TYPE
            SYNTAX  LSSlotID
            ACCESS  read-only
            STATUS  mandatory
            DESCRIPTION
                "LSO slot"
            ::= { lsoSevenDaysPerfEntry 1 }

        lsoDPPortIndex  OBJECT-TYPE
            SYNTAX  PortID
            ACCESS  read-only
            STATUS  mandatory
            DESCRIPTION
                "Port 1 to 4, total 4 ports."
            ::= { lsoSevenDaysPerfEntry 2 }

        lsoSevenDaysPerfRegType  OBJECT-TYPE
            SYNTAX  INTEGER {
                    user(1),
                    line(2)
                }
            ACCESS  read-only
            STATUS  mandatory
            DESCRIPTION
                " Performance Register Type "
            ::= { lsoSevenDaysPerfEntry 3 }

        lsoDaysIndex  OBJECT-TYPE
            SYNTAX  INTEGER (1..7)
            ACCESS  read-only
            STATUS  mandatory
            DESCRIPTION
                "Seven Days index "
            ::= { lsoSevenDaysPerfEntry 4 }

        lsoDateStrIndex  OBJECT-TYPE
            SYNTAX  DisplayString (SIZE (0..255) )
            ACCESS  read-only
            STATUS  mandatory
            DESCRIPTION
                "Seven Days String "
            ::= { lsoSevenDaysPerfEntry 5 }

        lsoSevenDaysPerfES  OBJECT-TYPE
            SYNTAX  INTEGER
            ACCESS  read-only
            STATUS  mandatory
            DESCRIPTION
                " ES Error Counter "
            ::= { lsoSevenDaysPerfEntry 6 }

        lsoSevenDaysPerfSES  OBJECT-TYPE
            SYNTAX  INTEGER
            ACCESS  read-only
            STATUS  mandatory
            DESCRIPTION
                " SES Error Counter "
            ::= { lsoSevenDaysPerfEntry 7 }

        lsoSevenDaysPerfUAS  OBJECT-TYPE
            SYNTAX  INTEGER
            ACCESS  read-only
            STATUS  mandatory
            DESCRIPTION
                " UAS Error Counter "
            ::= { lsoSevenDaysPerfEntry 8 }

        lsoTotalCard   OBJECT-TYPE
            SYNTAX  INTEGER
            ACCESS  read-only
            STATUS  mandatory
            DESCRIPTION
                "Total cards of LS-optical"
            ::= { ls-optical-card 100 }

--======================================================================--
--======================================================================--
--  OCT-RT-B MIB
--======================================================================--
--======================================================================--
--
--  Alarm Status Table
--

        r8AlmStatusTable  OBJECT-TYPE
            SYNTAX  SEQUENCE OF R8AlmStatusEntry
            ACCESS  not-accessible
            STATUS  mandatory
            DESCRIPTION
                " Alarm Status Table "
            ::= { oct-rt-b-card 1 }

        r8AlmStatusEntry  OBJECT-TYPE
            SYNTAX  R8AlmStatusEntry
            ACCESS  not-accessible
            STATUS  mandatory
            DESCRIPTION
                " "
            INDEX { r8ASSlotIndex ,
                    r8AlmStatusNumber }
            ::= { r8AlmStatusTable 1 }

        R8AlmStatusEntry ::= SEQUENCE {
            r8ASSlotIndex               LSSlotID,
            r8AlmStatusNumber           INTEGER (1..40),
            r8AlmStatusString           DisplayString,
            r8AlmStatusState            INTEGER,
            r8AlmStatusCount            INTEGER,
            r8AlmStatusEnable           LsAlarmSeverity
        }

        r8ASSlotIndex  OBJECT-TYPE
            SYNTAX  LSSlotID
            ACCESS  read-only
            STATUS  mandatory
            DESCRIPTION
                "R8 slot"
            ::= { r8AlmStatusEntry 1 }

        r8AlmStatusNumber  OBJECT-TYPE
            SYNTAX  INTEGER (1..40)
            ACCESS  read-only
            STATUS  mandatory
            DESCRIPTION
                " Alarm Status Index "
            ::= { r8AlmStatusEntry 2 }

        r8AlmStatusString  OBJECT-TYPE
            SYNTAX  DisplayString (SIZE (0..80))
            ACCESS  read-only
            STATUS  mandatory
            DESCRIPTION
                "Alarm Type String"
            ::= { r8AlmStatusEntry 3 }

        r8AlmStatusState  OBJECT-TYPE
            SYNTAX  INTEGER {
                    ok(1),
                    alarm(2),
                    disable(3),
                    none(4)
                }
            ACCESS  read-only
            STATUS  mandatory
            DESCRIPTION
                " Alarm Current State"
            ::= { r8AlmStatusEntry 4 }

        r8AlmStatusCount  OBJECT-TYPE
            SYNTAX  INTEGER
            ACCESS  read-only
            STATUS  mandatory
            DESCRIPTION
                " Alarm Count which happened "
            ::= { r8AlmStatusEntry 5 }

        r8AlmStatusEnable  OBJECT-TYPE
            SYNTAX  LsAlarmSeverity
            ACCESS  read-write
            STATUS  mandatory
            DESCRIPTION
                "Alarm is enabled or not"
            ::= { r8AlmStatusEntry 6 }

--
--  Command Control Table
--

        r8CommandControlTable  OBJECT-TYPE
            SYNTAX  SEQUENCE OF R8CommandControlEntry
            ACCESS  not-accessible
            STATUS  mandatory
            DESCRIPTION
                "The command control table."
            ::= { oct-rt-b-card 2 }

        r8CommandControlEntry  OBJECT-TYPE
            SYNTAX  R8CommandControlEntry
            ACCESS  not-accessible
            STATUS  mandatory
            DESCRIPTION
                "An entry in the command control table."
            INDEX { r8CCSlotIndex }
            ::= { r8CommandControlTable 1 }

        R8CommandControlEntry ::= SEQUENCE {
            r8CCSlotIndex               LSSlotID,
--               r8ClearAlarmHistory
--                 INTEGER,
            r8LoadDefaultAlarmCfg       INTEGER,
            r8Reset                     INTEGER,
            r8ReturnToDefault           INTEGER,
            r8SaveConfig                INTEGER
        }

        r8CCSlotIndex  OBJECT-TYPE
            SYNTAX  LSSlotID
            ACCESS  read-only
            STATUS  mandatory
            DESCRIPTION
                "R8 slot"
            ::= { r8CommandControlEntry 1 }

--         r8ClearAlarmHistory    OBJECT-TYPE
--             SYNTAX  INTEGER {
--                         clear(1)
--                     }
--             ACCESS  read-write
--             STATUS  mandatory
--             DESCRIPTION
--                "Command: Clear Alarm History"
--             ::= { r8CommandControlEntry 2 }

        r8LoadDefaultAlarmCfg    OBJECT-TYPE
            SYNTAX  INTEGER {
                    load-default(1)
                }
            ACCESS  read-write
            STATUS  mandatory
            DESCRIPTION
                "Command: Load Default Alarm Config"
            ::= { r8CommandControlEntry 3 }

        r8Reset    OBJECT-TYPE
            SYNTAX  INTEGER {
                    reset(1)
                }
            ACCESS  read-write
            STATUS  mandatory
            DESCRIPTION
                "Command: Reset Card"
            ::= { r8CommandControlEntry 4 }

        r8ReturnToDefault    OBJECT-TYPE
            SYNTAX  INTEGER {
                    return-to-default(1)
                }
            ACCESS  read-write
            STATUS  mandatory
            DESCRIPTION
                "Command: Return to default"
            ::= { r8CommandControlEntry 5 }

        r8SaveConfig    OBJECT-TYPE
            SYNTAX  INTEGER {
                    save-config(1)
                }
            ACCESS  read-write
            STATUS  mandatory
            DESCRIPTION
                "Command: Save config"
            ::= { r8CommandControlEntry 6 }

--
-- OCT-RT-B Bridge
--

    r8Bridge                      OBJECT IDENTIFIER ::= { oct-rt-b-card 3 }

--
-- OCT-RT-B Create and Destroy Bridge
--

        r8CreateDestroyBridge  OBJECT-TYPE
            SYNTAX  SEQUENCE OF R8CreateDestroyBridgeEntry
            ACCESS  not-accessible
            STATUS  mandatory
            DESCRIPTION
                "OCT-RT-B Create and Destroy Bridge Table."
            ::= { r8Bridge 1 }

        r8CreateDestroyBridgeEntry  OBJECT-TYPE
            SYNTAX  R8CreateDestroyBridgeEntry
            ACCESS  not-accessible
            STATUS  mandatory
            DESCRIPTION
                "OCT-RT-B Create and Destroy Bridge Entry"
            INDEX { r8CDBSlotIndex }
            ::= { r8CreateDestroyBridge 1 }

        R8CreateDestroyBridgeEntry ::= SEQUENCE {
            r8CDBSlotIndex              LSSlotID,
            r8BridgeName                DisplayString,
            r8BridgeMacAddr             DisplayString,
            r8BridgeCMD                 INTEGER
        }

        r8CDBSlotIndex  OBJECT-TYPE
            SYNTAX  LSSlotID
            ACCESS  read-only
            STATUS  mandatory
            DESCRIPTION
                "R8 slot"
            ::= { r8CreateDestroyBridgeEntry 1 }

        r8BridgeName  OBJECT-TYPE
            SYNTAX  DisplayString (SIZE (0..8))
            ACCESS  read-write
            STATUS  mandatory
            DESCRIPTION
                "Bridge Name"
            ::= { r8CreateDestroyBridgeEntry 2 }

        r8BridgeMacAddr  OBJECT-TYPE
            SYNTAX  DisplayString (SIZE (0..20))
            ACCESS  read-write
            STATUS  mandatory
            DESCRIPTION
                "Bridge Management Mac (xx:xx:xx:xx:xx:xx)"
            ::= { r8CreateDestroyBridgeEntry 3 }

        r8BridgeCMD  OBJECT-TYPE
            SYNTAX  INTEGER {
                    create(1),
                    destroy(2)
                }
            ACCESS  read-write
            STATUS  mandatory
            DESCRIPTION
                "Lan Index"
            ::= { r8CreateDestroyBridgeEntry 4 }

--
-- OCT-RT-B Bridge Config Table
--

        r8BridgeCFG  OBJECT-TYPE
            SYNTAX  SEQUENCE OF R8BridgeCFGEntry
            ACCESS  not-accessible
            STATUS  mandatory
            DESCRIPTION
                "R8 Bridge Config Table."
            ::= { r8Bridge 2 }

        r8BridgeCFGEntry  OBJECT-TYPE
            SYNTAX  R8BridgeCFGEntry
            ACCESS  not-accessible
            STATUS  mandatory
            DESCRIPTION
                "R8 Bridge Config Entry"
            INDEX { r8BCSlotIndex ,
                    r8BrgGroupID }
            ::= { r8BridgeCFG 1 }

        R8BridgeCFGEntry ::= SEQUENCE {
            r8BCSlotIndex               LSSlotID,
            r8BrgGroupID                INTEGER,
            r8BrgName                   DisplayString,
            r8BrgManagementAddr         DisplayString,
            r8BrgManagementMac          DisplayString,
            r8BrgMacAgingTime           INTEGER,
            r8BrgCRC                    INTEGER,
            r8BrgManageState            INTEGER,
            r8BrgInboundPolicy          DisplayString,
            r8BrgOutboundPolicy         DisplayString,
            r8BrgSTPState               INTEGER,
            r8BrgSTPProtocolVersion     INTEGER,
            r8BrgSTPHelloTime           INTEGER,
            r8BrgSTPMacAgingTime        INTEGER,
            r8BrgSTPForwardDelay        INTEGER,
            r8BrgSTPPriority            INTEGER,
            r8BrgL2PDUtunneling         INTEGER,
            r8BrgRoutingProtocol        INTEGER
        }

        r8BCSlotIndex  OBJECT-TYPE
            SYNTAX  LSSlotID
            ACCESS  read-only
            STATUS  mandatory
            DESCRIPTION
                "R8 slot"
            ::= { r8BridgeCFGEntry 1 }

        r8BrgGroupID  OBJECT-TYPE
            SYNTAX  INTEGER
            ACCESS  read-only
            STATUS  mandatory
            DESCRIPTION
                "Bridge Group ID"
            ::= { r8BridgeCFGEntry 2 }

        r8BrgName  OBJECT-TYPE
            SYNTAX  DisplayString (SIZE (0..8))
            ACCESS  read-only
            STATUS  mandatory
            DESCRIPTION
                "Bridge Group Name"
            ::= { r8BridgeCFGEntry 3 }

        r8BrgManagementAddr  OBJECT-TYPE
            SYNTAX  DisplayString (SIZE (0..20))
            ACCESS  read-write
            STATUS  mandatory
            DESCRIPTION
                "Bridge Management IP Address(xxx.xxx.xxx.xxx/xx)"
            ::= { r8BridgeCFGEntry 4 }

        r8BrgManagementMac  OBJECT-TYPE
            SYNTAX  DisplayString (SIZE (0..20))
            ACCESS  read-only
            STATUS  mandatory
            DESCRIPTION
                "Bridge Management Mac (xx:xx:xx:xx:xx:xx)"
            ::= { r8BridgeCFGEntry 5 }

        r8BrgMacAgingTime  OBJECT-TYPE
            SYNTAX  INTEGER (10..1000000)
            ACCESS  read-write
            STATUS  mandatory
            DESCRIPTION
                "Bridge MAC Aging Time(10-1000000 Sec)"
            ::= { r8BridgeCFGEntry 6 }

        r8BrgCRC  OBJECT-TYPE
            SYNTAX  INTEGER {
                    disable(1),
                    enable(2)
                }
            ACCESS  read-write
            STATUS  mandatory
            DESCRIPTION
                "Disable/Enable CRC"
            ::= { r8BridgeCFGEntry 7 }

        r8BrgManageState  OBJECT-TYPE
            SYNTAX  INTEGER {
                    disable(1),
                    enable(2)
                }
            ACCESS  read-write
            STATUS  mandatory
            DESCRIPTION
                "Indicated whether the mgmt attached with epilogue"
            ::= { r8BridgeCFGEntry 8 }

        r8BrgInboundPolicy  OBJECT-TYPE
            SYNTAX  DisplayString (SIZE (0..10))
            ACCESS  read-write
            STATUS  mandatory
            DESCRIPTION
                "Bridge Inbound policy"
            ::= { r8BridgeCFGEntry 9 }

        r8BrgOutboundPolicy  OBJECT-TYPE
            SYNTAX  DisplayString (SIZE (0..10))
            ACCESS  read-write
            STATUS  mandatory
            DESCRIPTION
                "Bridge Inbound policy"
            ::= { r8BridgeCFGEntry 10 }

        r8BrgSTPState  OBJECT-TYPE
            SYNTAX  INTEGER {
                    disable(1),
                    enable(2)
                }
            ACCESS  read-write
            STATUS  mandatory
            DESCRIPTION
                "Bridge Spanning Tree disable/enable"
            ::= { r8BridgeCFGEntry 11 }

        r8BrgSTPProtocolVersion  OBJECT-TYPE
            SYNTAX  INTEGER {
                    stp(1),
                    rstp(3)
                }
            ACCESS  read-only
            STATUS  mandatory
            DESCRIPTION
                "Bridge Spanning Tree Protocol Version"
            ::= { r8BridgeCFGEntry 12 }

        r8BrgSTPHelloTime  OBJECT-TYPE
            SYNTAX  INTEGER (1..10)
            ACCESS  read-write
            STATUS  mandatory
            DESCRIPTION
                "Bridge Spanning Tree Hello Time(1-10 Sec)"
            ::= { r8BridgeCFGEntry 13 }

        r8BrgSTPMacAgingTime  OBJECT-TYPE
            SYNTAX  INTEGER (6..40)
            ACCESS  read-write
            STATUS  mandatory
            DESCRIPTION
                "Bridge Spanning Tree Aging Time(6-40 Sec)"
            ::= { r8BridgeCFGEntry 14 }

        r8BrgSTPForwardDelay OBJECT-TYPE
            SYNTAX  INTEGER (4..30)
            ACCESS  read-write
            STATUS  mandatory
            DESCRIPTION
                "Bridge Spanning Tree Forward Delay Time(4-30 Sec)"
            ::= { r8BridgeCFGEntry 15 }

        r8BrgSTPPriority OBJECT-TYPE
            SYNTAX  INTEGER (0..65535)
            ACCESS  read-write
            STATUS  mandatory
            DESCRIPTION
                "Bridge Spanning Tree Priority (0-65535)"
            ::= { r8BridgeCFGEntry 16 }

        r8BrgL2PDUtunneling  OBJECT-TYPE
            SYNTAX  INTEGER {
                    disable(1),
                    enable(2),
                    na(3)
                }
            ACCESS  read-write
            STATUS  mandatory
            DESCRIPTION
                "Disable/Enable BPDU"
            ::= { r8BridgeCFGEntry 17 }

        r8BrgRoutingProtocol  OBJECT-TYPE
            SYNTAX  INTEGER {
                    ripV1(1),
                    ripV2(2),
                    disable(4),
                    notSupport(5)
                }
            ACCESS  read-write
            STATUS  mandatory
            DESCRIPTION
                "Set Bridge routing protocol"
            ::= { r8BridgeCFGEntry 18 }


--
-- OCT-RT-B Bridge STP Info
--

        r8BrgSTPInfo  OBJECT-TYPE
            SYNTAX  SEQUENCE OF R8BrgSTPInfoEntry
            ACCESS  not-accessible
            STATUS  mandatory
            DESCRIPTION
                "Bridge Spanning Tree information Table."
            ::= { r8Bridge 3 }

        r8BrgSTPInfoEntry  OBJECT-TYPE
            SYNTAX  R8BrgSTPInfoEntry
            ACCESS  not-accessible
            STATUS  mandatory
            DESCRIPTION
                "Bridge Spanning Tree information Entry"
            INDEX { r8BSISlotIndex ,
                    r8BrgSIID ,
                    r8STPIndex }
            ::= { r8BrgSTPInfo 1 }

        R8BrgSTPInfoEntry ::= SEQUENCE {
            r8BSISlotIndex              LSSlotID,
            r8BrgSIID                   INTEGER,
            r8STPIndex                  INTEGER,
            r8STPName                   DisplayString,
            r8STPBridgeID               DisplayString,
            r8STPHelloTime              INTEGER,
            r8STPMaxAgingTime           INTEGER,
            r8STPForwardDelay           INTEGER,
            r8STPRootCost               INTEGER
        }

        r8BSISlotIndex  OBJECT-TYPE
            SYNTAX  LSSlotID
            ACCESS  read-only
            STATUS  mandatory
            DESCRIPTION
                "R8 slot"
            ::= { r8BrgSTPInfoEntry 1 }

        r8BrgSIID  OBJECT-TYPE
            SYNTAX  INTEGER
            ACCESS  read-only
            STATUS  mandatory
            DESCRIPTION
                "Bridge Group ID"
            ::= { r8BrgSTPInfoEntry 2 }

        r8STPIndex  OBJECT-TYPE
            SYNTAX  INTEGER
            ACCESS  read-only
            STATUS  mandatory
            DESCRIPTION
                "STP index"
            ::= { r8BrgSTPInfoEntry 3 }

        r8STPName  OBJECT-TYPE
            SYNTAX  DisplayString (SIZE (0..10))
            ACCESS  read-only
            STATUS  mandatory
            DESCRIPTION
                "Spanning tree Name"
            ::= { r8BrgSTPInfoEntry 4 }

        r8STPBridgeID  OBJECT-TYPE
            SYNTAX  DisplayString (SIZE (0..30))
            ACCESS  read-only
            STATUS  mandatory
            DESCRIPTION
                "Spanning tree Bridge Id"
            ::= { r8BrgSTPInfoEntry 5 }

        r8STPHelloTime  OBJECT-TYPE
            SYNTAX  INTEGER
            ACCESS  read-only
            STATUS  mandatory
            DESCRIPTION
                "Spanning Tree Hello Time interval"
            ::= { r8BrgSTPInfoEntry 6 }

        r8STPMaxAgingTime  OBJECT-TYPE
            SYNTAX  INTEGER
            ACCESS  read-only
            STATUS  mandatory
            DESCRIPTION
                "Spanning Tree Maximum Aging Time interval"
            ::= { r8BrgSTPInfoEntry 7 }

        r8STPForwardDelay OBJECT-TYPE
            SYNTAX  INTEGER
            ACCESS  read-only
            STATUS  mandatory
            DESCRIPTION
                "Spanning Tree Forward Delay Time interval"
            ::= { r8BrgSTPInfoEntry 8 }

        r8STPRootCost OBJECT-TYPE
            SYNTAX  INTEGER
            ACCESS  read-only
            STATUS  mandatory
            DESCRIPTION
                "Bridge Spanning Tree Post Cost"
            ::= { r8BrgSTPInfoEntry 9 }

--
-- OCT-RT-B STP Port Info
--

        r8BrgStpPortInfo  OBJECT-TYPE
            SYNTAX  SEQUENCE OF R8BrgStpPortInfoEntry
            ACCESS  not-accessible
            STATUS  mandatory
            DESCRIPTION
                "Spanning Tree Port information Table."
            ::= { r8Bridge 4 }

        r8BrgStpPortInfoEntry  OBJECT-TYPE
            SYNTAX  R8BrgStpPortInfoEntry
            ACCESS  not-accessible
            STATUS  mandatory
            DESCRIPTION
                "Spanning Tree Port information Entry"
            INDEX { r8BSPISlotIndex ,
                    r8BrgSPIID ,
                    r8StpPortIndex }
            ::= { r8BrgStpPortInfo 1 }

        R8BrgStpPortInfoEntry::= SEQUENCE {
            r8BSPISlotIndex             LSSlotID,
            r8BrgSPIID                  INTEGER,
            r8StpPortIndex              INTEGER,
            r8StpPortName               DisplayString,
            r8StpState                  INTEGER,
            r8StpPriority               INTEGER,
            r8StpCost                   INTEGER,
            r8StpEdgePort               INTEGER,
            r8StpLinkType               INTEGER,
            r8StpRootPort               INTEGER
        }

        r8BSPISlotIndex  OBJECT-TYPE
            SYNTAX  LSSlotID
            ACCESS  read-only
            STATUS  mandatory
            DESCRIPTION
                "R8 slot"
            ::= { r8BrgStpPortInfoEntry 1 }

        r8BrgSPIID  OBJECT-TYPE
            SYNTAX  INTEGER
            ACCESS  read-only
            STATUS  mandatory
            DESCRIPTION
                "Bridge Group ID"
            ::= { r8BrgStpPortInfoEntry 2 }

        r8StpPortIndex  OBJECT-TYPE
            SYNTAX  INTEGER
            ACCESS  read-only
            STATUS  mandatory
            DESCRIPTION
                "STP Port Number Index"
            ::= { r8BrgStpPortInfoEntry 3 }

        r8StpPortName  OBJECT-TYPE
            SYNTAX  DisplayString (SIZE (0..20))
            ACCESS  read-only
            STATUS  mandatory
            DESCRIPTION
                "Stp Port Name"
            ::= { r8BrgStpPortInfoEntry 4 }

        r8StpState  OBJECT-TYPE
            SYNTAX  INTEGER{
                    disable(1),
                    listen(2),
                    learn(3),
                    forward(4),
                    block(5),
                    down(6)
                }
            ACCESS  read-only
            STATUS  mandatory
            DESCRIPTION
                "Stp Port state"
            ::= { r8BrgStpPortInfoEntry 5 }

        r8StpPriority  OBJECT-TYPE
            SYNTAX  INTEGER (0..255)
            ACCESS  read-write
            STATUS  mandatory
            DESCRIPTION
                "STP Port priority"
            ::= { r8BrgStpPortInfoEntry 6 }

        r8StpCost  OBJECT-TYPE
            SYNTAX  INTEGER (1..65535)
            ACCESS  read-write
            STATUS  mandatory
            DESCRIPTION
                "STP Port priority"
            ::= { r8BrgStpPortInfoEntry 7 }

        r8StpEdgePort  OBJECT-TYPE
            SYNTAX  INTEGER{
                    disable(1),
                    enable(2)
                }
            ACCESS  read-write
            STATUS  mandatory
            DESCRIPTION
                "STP Port priority"
            ::= { r8BrgStpPortInfoEntry 8 }

        r8StpLinkType  OBJECT-TYPE
            SYNTAX  INTEGER{
                    shared(1),
                    p-to-p(2),
                    auto(3)
                }
            ACCESS  read-write
            STATUS  mandatory
            DESCRIPTION
                "STP Port priority"
            ::= { r8BrgStpPortInfoEntry 9 }

        r8StpRootPort  OBJECT-TYPE
            SYNTAX  INTEGER{
                    no(1),
                    yes(2)
                }
            ACCESS  read-only
            STATUS  mandatory
            DESCRIPTION
                "Stp Port root status"
            ::= { r8BrgStpPortInfoEntry 10 }

--
-- OCT-RT-B Bridge Add or Delete Interface Table
--

        r8BrgAddDelInterface  OBJECT-TYPE
            SYNTAX  SEQUENCE OF R8BrgAddDelInterfaceEntry
            ACCESS  not-accessible
            STATUS  mandatory
            DESCRIPTION
                "Add or delete interface to bridge group Table."
            ::= { r8Bridge 5 }

        r8BrgAddDelInterfaceEntry  OBJECT-TYPE
            SYNTAX  R8BrgAddDelInterfaceEntry
            ACCESS  not-accessible
            STATUS  mandatory
            DESCRIPTION
                "Add or delete interface to bridge group Entry"
            INDEX { r8BADISlotIndex }
            ::= { r8BrgAddDelInterface 1 }

        R8BrgAddDelInterfaceEntry::= SEQUENCE {
            r8BADISlotIndex             LSSlotID,
            r8BrgAddDelBrgName          DisplayString,
            r8BrgAddDelInterfaceName    DisplayString,
            r8BrgAddDelInterfaceCMD     INTEGER
        }

        r8BADISlotIndex  OBJECT-TYPE
            SYNTAX  LSSlotID
            ACCESS  read-only
            STATUS  mandatory
            DESCRIPTION
                "R8 slot"
            ::= { r8BrgAddDelInterfaceEntry 1 }

        r8BrgAddDelBrgName  OBJECT-TYPE
            SYNTAX  DisplayString (SIZE (0..8))
            ACCESS  read-write
            STATUS  mandatory
            DESCRIPTION
                "Bridge Group Name"
            ::= { r8BrgAddDelInterfaceEntry 2 }

        r8BrgAddDelInterfaceName  OBJECT-TYPE
            SYNTAX  DisplayString (SIZE (0..20))
            ACCESS  read-write
            STATUS  mandatory
            DESCRIPTION
                "Interface Name(lan1-8/wan1-64/wanX pvc1-16)"
            ::= { r8BrgAddDelInterfaceEntry 3 }

        r8BrgAddDelInterfaceCMD  OBJECT-TYPE
            SYNTAX  INTEGER{
                    add(1),
                    delete(2)
                }
            ACCESS  read-write
            STATUS  mandatory
            DESCRIPTION
                "Add interface to Bridge Mode or (delete)add interface
                to router mode"
            ::= { r8BrgAddDelInterfaceEntry 4 }

--
-- OCT-RT-B Interface Control Table
--

    r8Interface                        OBJECT IDENTIFIER ::= { oct-rt-b-card 4 }

--
-- OCT-RT-B LAN
--

    r8IntfLAN                          OBJECT IDENTIFIER ::= { r8Interface 1 }

--
-- R8 LAN Config Table
--

        r8LanCFG  OBJECT-TYPE
            SYNTAX  SEQUENCE OF R8LanCFGEntry
            ACCESS  not-accessible
            STATUS  mandatory
            DESCRIPTION
                "LAN Config Table."
            ::= { r8IntfLAN 1 }

        r8LanCFGEntry  OBJECT-TYPE
            SYNTAX  R8LanCFGEntry
            ACCESS  not-accessible
            STATUS  mandatory
            DESCRIPTION
                "LAN Config Entry"
            INDEX { r8LCSlotIndex ,
                    r8LanIndex }
            ::= { r8LanCFG 1 }

        R8LanCFGEntry ::= SEQUENCE {
            r8LCSlotIndex               LSSlotID,
            r8LanIndex                  INTEGER,
            r8LanIPAddr                 DisplayString,
--               r8LanAliasIPAddr1
--                 DisplayString,
--               r8LanAliasIPAddr2
--                 DisplayString,
--               r8LanAliasIPAddr3
--                 DisplayString,
--               r8LanAliasIPAddr4
--                 DisplayString,
--               r8LanAliasIPAddr5
--                 DisplayString,
            r8LanRoutingProtocol        INTEGER,
            r8LanLayer2Protocol         INTEGER,
            r8LanSpeed                  INTEGER,
            r8LanInterfaceMode          INTEGER,
            r8LanInboundPolicy          DisplayString,
            r8LanOutboundPolicy         DisplayString,
            r8LanStatus                 DisplayString
        }

        r8LCSlotIndex  OBJECT-TYPE
            SYNTAX  LSSlotID
            ACCESS  read-only
            STATUS  mandatory
            DESCRIPTION
                "R8 slot"
            ::= { r8LanCFGEntry 1 }

        r8LanIndex  OBJECT-TYPE
            SYNTAX  INTEGER {
                    lan1(1),
                    lan2(2),
                    lan3(3),
                    lan4(4),
                    lan5(5),
                    lan6(6),
                    lan7(7),
                    lan8(8)

                }
            ACCESS  read-only
            STATUS  mandatory
            DESCRIPTION
                "Lan Index"
            ::= { r8LanCFGEntry 2 }

        r8LanIPAddr  OBJECT-TYPE
            SYNTAX  DisplayString (SIZE (0..20))
            ACCESS  read-write
            STATUS  mandatory
            DESCRIPTION
                "Lan IP Address(xxx.xxx.xxx.xxx/xx)"
            ::= { r8LanCFGEntry 3 }

--         r8LanAliasIPAddr1  OBJECT-TYPE
--             SYNTAX  DisplayString (SIZE (0..20))
--             ACCESS  read-only
--             STATUS  mandatory
--             DESCRIPTION
--                "Lan alias IP Address(xxx.xxx.xxx.xxx/xx)"
--             ::= { r8LanCFGEntry 4 }
--
--         r8LanAliasIPAddr2  OBJECT-TYPE
--             SYNTAX  DisplayString (SIZE (0..20))
--             ACCESS  read-only
--             STATUS  mandatory
--             DESCRIPTION
--                "Lan alias IP Address(xxx.xxx.xxx.xxx/xx)"
--             ::= { r8LanCFGEntry 5 }
--
--         r8LanAliasIPAddr3  OBJECT-TYPE
--             SYNTAX  DisplayString (SIZE (0..20))
--             ACCESS  read-only
--             STATUS  mandatory
--             DESCRIPTION
--                "Lan alias IP Address(xxx.xxx.xxx.xxx/xx)"
--             ::= { r8LanCFGEntry 6 }
--
--         r8LanAliasIPAddr4  OBJECT-TYPE
--             SYNTAX  DisplayString (SIZE (0..20))
--             ACCESS  read-only
--             STATUS  mandatory
--             DESCRIPTION
--                "Lan alias IP Address(xxx.xxx.xxx.xxx/xx)"
--             ::= { r8LanCFGEntry 7 }

--        r8LanAliasIPAddr5  OBJECT-TYPE
--            SYNTAX  DisplayString (SIZE (0..20))
--            ACCESS  read-only
--            STATUS  mandatory
--            DESCRIPTION
--                "Lan alias IP Address(xxx.xxx.xxx.xxx/xx)"
--            ::= { r8LanCFGEntry 8 }

        r8LanRoutingProtocol  OBJECT-TYPE
            SYNTAX  INTEGER {
                    rip1(1),
                    rip2(2),
                    ospf(3),
                    none(4)
                }
            ACCESS  read-write
            STATUS  mandatory
            DESCRIPTION
                "Lan Routing Protocol(OSPF enable/disable in r2OspfIntfAdminSetup Table"
            ::= { r8LanCFGEntry 9 }

        r8LanLayer2Protocol  OBJECT-TYPE
            SYNTAX  INTEGER {
                    ethernet(1),
                    fast-ethernet(2)
                }
            ACCESS  read-only
            STATUS  mandatory
            DESCRIPTION
                "Lan Layer2 Protocol"
            ::= { r8LanCFGEntry 10 }

        r8LanSpeed  OBJECT-TYPE
            SYNTAX  INTEGER {
                    half-duplex-10M(1),
                    full-duplex-10M(2),
                    half-duplex-100M(3),
                    full-duplex-100M(4),
                    auto-negotiation(5)
                }
            ACCESS  read-write
            STATUS  mandatory
            DESCRIPTION
                "Lan Speed(10/100Mb ; half/full)"
            ::= { r8LanCFGEntry 11 }

        r8LanInterfaceMode  OBJECT-TYPE
            SYNTAX  INTEGER {
                    null(0),
                    router(1),
                    bridge(2)
                }
            ACCESS  read-only
            STATUS  mandatory
            DESCRIPTION
                "Lan Interface Mode"
            ::= { r8LanCFGEntry 12 }

        r8LanInboundPolicy  OBJECT-TYPE
            SYNTAX  DisplayString (SIZE (0..10))
            ACCESS  read-write
            STATUS  mandatory
            DESCRIPTION
                "Lan inbound policy (off to disable access control)"
            ::= { r8LanCFGEntry 13 }

        r8LanOutboundPolicy  OBJECT-TYPE
            SYNTAX  DisplayString (SIZE (0..10))
            ACCESS  read-write
            STATUS  mandatory
            DESCRIPTION
                "Lan outbound policy (off to disable access control)"
            ::= { r8LanCFGEntry 14 }

        r8LanStatus  OBJECT-TYPE
            SYNTAX  DisplayString (SIZE (0..30))
            ACCESS  read-only
            STATUS  mandatory
            DESCRIPTION
                "Lan Status"
            ::= { r8LanCFGEntry 15 }

--
-- OCT-RT-B Add or Delete Lan Alias IP Table
--

--         r8AddDelAliasIP  OBJECT-TYPE
--             SYNTAX  SEQUENCE OF R8AddDelAliasIPEntry
--             ACCESS  not-accessible
--             STATUS  mandatory
--             DESCRIPTION
--                "Add or Delete Lan Alias IP Table."
--             ::= { r8IntfLAN 2 }
--
--         r8AddDelAliasIPEntry  OBJECT-TYPE
--             SYNTAX  R8AddDelAliasIPEntry
--             ACCESS  not-accessible
--             STATUS  mandatory
--             DESCRIPTION
--                "Add or Delete Lan Alias IP Entry"
--             INDEX  { r8ADAISlotIndex }
--             ::= { r8AddDelAliasIP 1 }
--
--         R8AddDelAliasIPEntry ::=
--             SEQUENCE {
--               r8AliasIPLanIndex
--                 INTEGER,
--               r8AliasIPAddr
--                 DisplayString,
--               r8AliasIPAddrCMD
--                 INTEGER
--             }
--
--         r8AliasIPLanIndex  OBJECT-TYPE
--             SYNTAX  INTEGER{
--                        lan1(1),
--                        lan2(2),
--                        lan3(3),
--                        lan4(4),
--                        lan5(5),
--                        lan6(6),
--                        lan7(7),
--                        lan8(8)
--                     }
--             ACCESS  read-write
--             STATUS  mandatory
--             DESCRIPTION
--                "Lan Index"
--             ::= { r8AddDelAliasIPEntry 2 }
--
--         r8AliasIPAddr  OBJECT-TYPE
--             SYNTAX  DisplayString (SIZE (0..20))
--             ACCESS  read-write
--             STATUS  mandatory
--             DESCRIPTION
--                "Alias IP Address(xxx.xxx.xxx.xxx/xx)"
--             ::= { r8AddDelAliasIPEntry 3 }
--
--         r8AliasIPAddrCMD  OBJECT-TYPE
--             SYNTAX  INTEGER{
--                        add(1),
--                        delete(2)
--                     }
--             ACCESS  read-write
--             STATUS  mandatory
--             DESCRIPTION
--                "Add or Delete Alias IP Address"
--             ::= { r8AddDelAliasIPEntry 4 }

--
-- OCT-RT-B WAN
--

    r8IntfWAN                          OBJECT IDENTIFIER ::= { r8Interface 2 }

--
-- OCT-RT-B  WAN Config Table
--

        r8WanCFG  OBJECT-TYPE
            SYNTAX  SEQUENCE OF R8WanCFGEntry
            ACCESS  not-accessible
            STATUS  mandatory
            DESCRIPTION
                "Interface WAN(1-64) Config Table."
            ::= { r8IntfWAN 1 }

        r8WanCFGEntry  OBJECT-TYPE
            SYNTAX  R8WanCFGEntry
            ACCESS  not-accessible
            STATUS  mandatory
            DESCRIPTION
                "Interface WAN(1-64) Config Entry"
            INDEX { r8WCSlotIndex ,
                    r8WanIndex }
            ::= { r8WanCFG 1 }

        R8WanCFGEntry ::= SEQUENCE {
            r8WCSlotIndex               LSSlotID,
            r8WanIndex                  INTEGER,
            r8WanIPAddr                 DisplayString,
            r8WanRoutingProtocol        INTEGER,
            r8WanNatNapt                INTEGER,
            r8WanNumberOfTimeSlots      INTEGER,
            r8WanLayer2Protocol         INTEGER,
            r8WanInterfaceMode          INTEGER,
            r8WanInboundPolicy          DisplayString,
            r8WanOutboundPolicy         DisplayString,
            r8WanStatus                 INTEGER
        }

        r8WCSlotIndex  OBJECT-TYPE
            SYNTAX  LSSlotID
            ACCESS  read-only
            STATUS  mandatory
            DESCRIPTION
                "R8 slot"
            ::= { r8WanCFGEntry 1 }

        r8WanIndex  OBJECT-TYPE
            SYNTAX  INTEGER (1..64)
            ACCESS  read-only
            STATUS  mandatory
            DESCRIPTION
                "Interface WAN1-WAN2"
            ::= { r8WanCFGEntry 2 }

        r8WanIPAddr  OBJECT-TYPE
            SYNTAX  DisplayString (SIZE (0..20))
            ACCESS  read-write
            STATUS  mandatory
            DESCRIPTION
                "WAN IP Address(xxx.xxx.xxx.xxx/xx)"
            ::= { r8WanCFGEntry 3 }

        r8WanRoutingProtocol  OBJECT-TYPE
            SYNTAX  INTEGER {
                    rip1(1),
                    rip2(2),
                    none(4)
                }
            ACCESS  read-write
            STATUS  mandatory
            DESCRIPTION
                "WAN Routing Protocol"
            ::= { r8WanCFGEntry 4 }

        r8WanNatNapt  OBJECT-TYPE
            SYNTAX  INTEGER {
                    disable(1),
                    nat(2),
                    napt(3)
                }
            ACCESS  read-write
            STATUS  mandatory
            DESCRIPTION
                "WAN NAT/NAPT Function"
            ::= { r8WanCFGEntry 5 }

        r8WanNumberOfTimeSlots  OBJECT-TYPE
            SYNTAX  INTEGER
            ACCESS  read-only
            STATUS  mandatory
            DESCRIPTION
                "Number of TimeSlots for this WAN"
            ::= { r8WanCFGEntry 6 }

        r8WanLayer2Protocol  OBJECT-TYPE
            SYNTAX  INTEGER {
                    ppp(3),
                    hdlc(4),
                    frame-relay(5),
                    cisco-hdlc(6)
                }
            ACCESS  read-write
            STATUS  mandatory
            DESCRIPTION
                "Lan Layer2 Protocol"
            ::= { r8WanCFGEntry 7 }

        r8WanInterfaceMode  OBJECT-TYPE
            SYNTAX  INTEGER {
                    null(0),
                    router(1),
                    bridge(2)
                }
            ACCESS  read-only
            STATUS  mandatory
            DESCRIPTION
                "WAN Interface Mode"
            ::= { r8WanCFGEntry 8 }

        r8WanInboundPolicy  OBJECT-TYPE
            SYNTAX  DisplayString (SIZE (0..10))
            ACCESS  read-write
            STATUS  mandatory
            DESCRIPTION
                "Wan inbound policy (off to disable access control)"
            ::= { r8WanCFGEntry 9 }

        r8WanOutboundPolicy  OBJECT-TYPE
            SYNTAX  DisplayString (SIZE (0..10))
            ACCESS  read-write
            STATUS  mandatory
            DESCRIPTION
                "Wan outbound policy (off to disable access control)"
            ::= { r8WanCFGEntry 10 }

        r8WanStatus  OBJECT-TYPE
            SYNTAX  INTEGER {
                    down(1),
                    up(2)
                }
            ACCESS  read-only
            STATUS  mandatory
            DESCRIPTION
                "WAN Status"
            ::= { r8WanCFGEntry 11 }

--
-- OCT-RT-B  WAN Cisco Hdlc Config Table
--

        r8WanCiscoHdlc  OBJECT-TYPE
            SYNTAX  SEQUENCE OF R8WanCiscoHdlcEntry
            ACCESS  not-accessible
            STATUS  mandatory
            DESCRIPTION
                "WAN Cisco Hdlc Config Table."
            ::= { r8IntfWAN 2 }

        r8WanCiscoHdlcEntry  OBJECT-TYPE
            SYNTAX  R8WanCiscoHdlcEntry
            ACCESS  not-accessible
            STATUS  mandatory
            DESCRIPTION
                "WAN Cisco Hdlc Config Entry"
            INDEX { r8WCHSlotIndex ,
                    r8WanCHIndex }
            ::= { r8WanCiscoHdlc 1 }

        R8WanCiscoHdlcEntry ::= SEQUENCE {
            r8WCHSlotIndex              LSSlotID,
            r8WanCHIndex                INTEGER,
            r8WanChdlcInterval          INTEGER,
            r8WanChdlcTimeout           INTEGER,
            r8WanChdlcCMD               INTEGER
        }

        r8WCHSlotIndex  OBJECT-TYPE
            SYNTAX  LSSlotID
            ACCESS  read-only
            STATUS  mandatory
            DESCRIPTION
                "R8 slot"
            ::= { r8WanCiscoHdlcEntry 1 }

        r8WanCHIndex  OBJECT-TYPE
            SYNTAX  INTEGER (1..64)
            ACCESS  read-only
            STATUS  mandatory
            DESCRIPTION
                "Interface WAN1-WAN2"
            ::= { r8WanCiscoHdlcEntry 2 }

        r8WanChdlcInterval  OBJECT-TYPE
            SYNTAX  INTEGER (1..3600)
            ACCESS  read-write
            STATUS  mandatory
            DESCRIPTION
                "Keepalive interval (1-3600, default is 10 secs)"
            ::= { r8WanCiscoHdlcEntry 3 }

        r8WanChdlcTimeout  OBJECT-TYPE
            SYNTAX  INTEGER
            ACCESS  read-write
            STATUS  mandatory
            DESCRIPTION
                "Interface restart timeout(secs, should be multiple of interval)"
            ::= { r8WanCiscoHdlcEntry 4 }

        r8WanChdlcCMD  OBJECT-TYPE
            SYNTAX  INTEGER {
                    set(1)
                }
            ACCESS  read-write
            STATUS  mandatory
            DESCRIPTION
                "Set Cisco Hdlc"
            ::= { r8WanCiscoHdlcEntry 5 }

--
-- OCT-RT-B  WAN Frame Relay Config Table
--

        r8WanFrameRelay  OBJECT-TYPE
            SYNTAX  SEQUENCE OF R8WanFrameRelayEntry
            ACCESS  not-accessible
            STATUS  mandatory
            DESCRIPTION
                "WAN Frame Relay Config Table."
            ::= { r8IntfWAN 3 }

        r8WanFrameRelayEntry  OBJECT-TYPE
            SYNTAX  R8WanFrameRelayEntry
            ACCESS  not-accessible
            STATUS  mandatory
            DESCRIPTION
                "WAN Frame Relay Config Entry"
            INDEX { r8WFRSlotIndex ,
                    r8WanFRIndex }
            ::= { r8WanFrameRelay 1 }

        R8WanFrameRelayEntry ::= SEQUENCE {
            r8WFRSlotIndex              LSSlotID,
            r8WanFRIndex                INTEGER,
            r8WanFRLMIType              INTEGER,
            r8WanFRN391                 INTEGER,
            r8WanFRN392                 INTEGER,
            r8WanFRN393                 INTEGER,
            r8WanFRT391                 INTEGER
        }

        r8WFRSlotIndex  OBJECT-TYPE
            SYNTAX  LSSlotID
            ACCESS  read-only
            STATUS  mandatory
            DESCRIPTION
                "R8 slot"
            ::= { r8WanFrameRelayEntry 1 }

        r8WanFRIndex  OBJECT-TYPE
            SYNTAX  INTEGER (1..64)
            ACCESS  read-only
            STATUS  mandatory
            DESCRIPTION
                "Interface WAN1-WAN2"
            ::= { r8WanFrameRelayEntry 2 }

        r8WanFRLMIType  OBJECT-TYPE
            SYNTAX  INTEGER {
                    q933(1),
                    ansi(2)
                }
            ACCESS  read-write
            STATUS  mandatory
            DESCRIPTION
                "Frame Relay LMI protocol (ansi/q933)"
            ::= { r8WanFrameRelayEntry 3 }

        r8WanFRN391  OBJECT-TYPE
            SYNTAX  INTEGER (1..255)
            ACCESS  read-write
            STATUS  mandatory
            DESCRIPTION
                "LMI full-status polling interval (1~255)"
            ::= { r8WanFrameRelayEntry 4 }

        r8WanFRN392  OBJECT-TYPE
            SYNTAX  INTEGER (1..10)
            ACCESS  read-write
            STATUS  mandatory
            DESCRIPTION
                "LMI error threshold (1~10)"
            ::= { r8WanFrameRelayEntry 5 }

        r8WanFRN393  OBJECT-TYPE
            SYNTAX  INTEGER (1..10)
            ACCESS  read-write
            STATUS  mandatory
            DESCRIPTION
                "LMI monitored event threshold (1~10)"
            ::= { r8WanFrameRelayEntry 6 }

        r8WanFRT391  OBJECT-TYPE
            SYNTAX  INTEGER (5..30)
            ACCESS  read-write
            STATUS  mandatory
            DESCRIPTION
                "LMI link integrity polling interval (5~30)"
            ::= { r8WanFrameRelayEntry 7 }

--
-- OCT-RT-B  WAN PVC
--

    r8WanPVC                       OBJECT IDENTIFIER ::= { r8IntfWAN 4 }

--
-- OCT-RT-B  WAN PVC Function Table
--

        r8WanAddDelPVC  OBJECT-TYPE
            SYNTAX  SEQUENCE OF R8WanAddDelPVCEntry
            ACCESS  not-accessible
            STATUS  mandatory
            DESCRIPTION
                "Add or Delete Frame Relay PVC Table"
            ::= { r8WanPVC 1 }

        r8WanAddDelPVCEntry  OBJECT-TYPE
            SYNTAX  R8WanAddDelPVCEntry
            ACCESS  not-accessible
            STATUS  mandatory
            DESCRIPTION
                "Add or Delete Frame Relay PVC Entry"
            INDEX { r8WADPSlotIndex }
            ::= { r8WanAddDelPVC 1 }

        R8WanAddDelPVCEntry ::= SEQUENCE {
            r8WADPSlotIndex             LSSlotID,
            r8PvcWanIndex               INTEGER,
            r8PvcNum                    INTEGER,
            r8PvcDLCI                   INTEGER,
            r8PvcCIR                    INTEGER,
            r8PvcBc                     INTEGER,
            r8PvcBe                     INTEGER,
            r8PvcQdepth                 INTEGER,
            r8WanPvcCMD                 INTEGER
        }

        r8WADPSlotIndex  OBJECT-TYPE
            SYNTAX  LSSlotID
            ACCESS  read-only
            STATUS  mandatory
            DESCRIPTION
                "R8 slot"
            ::= { r8WanAddDelPVCEntry 1 }

        r8PvcWanIndex  OBJECT-TYPE
            SYNTAX  INTEGER (1..64)
            ACCESS  read-write
            STATUS  mandatory
            DESCRIPTION
                "The Wan number (wan1-wan64)"
            ::= { r8WanAddDelPVCEntry 2 }

        r8PvcNum  OBJECT-TYPE
            SYNTAX  INTEGER (1..16)
            ACCESS  read-write
            STATUS  mandatory
            DESCRIPTION
                "The PVC number (pvc1-pvc16)"
            ::= { r8WanAddDelPVCEntry 3 }

        r8PvcDLCI  OBJECT-TYPE
            SYNTAX  INTEGER
            ACCESS  read-write
            STATUS  mandatory
            DESCRIPTION
                "The PVC's DLCI (16~991)"
            ::= { r8WanAddDelPVCEntry 4 }

        r8PvcCIR  OBJECT-TYPE
            SYNTAX  INTEGER
            ACCESS  read-write
            STATUS  mandatory
            DESCRIPTION
                "Committed Information Rate (kbps)"
            ::= { r8WanAddDelPVCEntry 5 }

        r8PvcBc  OBJECT-TYPE
            SYNTAX  INTEGER
            ACCESS  read-write
            STATUS  mandatory
            DESCRIPTION
                "Committed Burst Size (kbits)"
            ::= { r8WanAddDelPVCEntry 6 }

        r8PvcBe  OBJECT-TYPE
            SYNTAX  INTEGER
            ACCESS  read-write
            STATUS  mandatory
            DESCRIPTION
                "Excess Burst Size (kbits)"
            ::= { r8WanAddDelPVCEntry 7 }

        r8PvcQdepth  OBJECT-TYPE
            SYNTAX  INTEGER
            ACCESS  read-write
            STATUS  mandatory
            DESCRIPTION
                "Max. queue length"
            ::= { r8WanAddDelPVCEntry 8 }

        r8WanPvcCMD  OBJECT-TYPE
            SYNTAX  INTEGER {
                    add-pvc(1),
                    delete-pvc(2)
                }
            ACCESS  read-write
            STATUS  mandatory
            DESCRIPTION
                "Add or Delete Frame Relay PVC for this wan interface"
            ::= { r8WanAddDelPVCEntry 9 }

--
-- OCT-RT-B WAN PVC Config Table
--

        r8WanPvcCFG  OBJECT-TYPE
            SYNTAX  SEQUENCE OF R8WanPvcCFGEntry
            ACCESS  not-accessible
            STATUS  mandatory
            DESCRIPTION
                "WAN PVC Config Table"
            ::= { r8WanPVC 2 }

        r8WanPvcCFGEntry  OBJECT-TYPE
            SYNTAX  R8WanPvcCFGEntry
            ACCESS  not-accessible
            STATUS  mandatory
            DESCRIPTION
                "WAN PVC Config Entry"
            INDEX { r8WPCSlotIndex ,
                    r8WanPCIndex ,
                    r8PvcIndex }
            ::= { r8WanPvcCFG 1 }

        R8WanPvcCFGEntry ::= SEQUENCE {
            r8WPCSlotIndex              LSSlotID,
            r8WanPCIndex                INTEGER,
            r8PvcIndex                  INTEGER,
            r8WanPvcState               INTEGER,
            r8WanPvcIPAddr              DisplayString,
            r8WanPvcRoutingProtocol     INTEGER,
            r8WanPvcNatNapt             INTEGER,
            r8WanPvcInterfaceMode       INTEGER,
            r8WanPvcDLCI                INTEGER,
            r8WanPvcCIR                 INTEGER,
            r8WanPvcBc                  INTEGER,
            r8WanPvcBe                  INTEGER,
            r8WanPvcQdepth              INTEGER,
            r8WanPvcInboundPolicy       DisplayString,
            r8WanPvcOutboundPolicy      DisplayString
        }

        r8WPCSlotIndex  OBJECT-TYPE
            SYNTAX  LSSlotID
            ACCESS  read-only
            STATUS  mandatory
            DESCRIPTION
                "R8 slot"
            ::= { r8WanPvcCFGEntry 1 }

        r8WanPCIndex  OBJECT-TYPE
            SYNTAX  INTEGER (1..64)
            ACCESS  read-only
            STATUS  mandatory
            DESCRIPTION
                "Interface WAN1-WAN2"
            ::= { r8WanPvcCFGEntry 2 }

        r8PvcIndex  OBJECT-TYPE
            SYNTAX  INTEGER (1..16)
            ACCESS  read-only
            STATUS  mandatory
            DESCRIPTION
                "The PVC number (pvc1-pvc16)"
            ::= { r8WanPvcCFGEntry 3 }

        r8WanPvcState  OBJECT-TYPE
            SYNTAX  INTEGER {
                    inactive(1),
                    active(2)
                }
            ACCESS  read-only
            STATUS  mandatory
            DESCRIPTION
                "WAN PVC State"
            ::= { r8WanPvcCFGEntry 4 }

        r8WanPvcIPAddr  OBJECT-TYPE
            SYNTAX  DisplayString (SIZE (0..20))
            ACCESS  read-write
            STATUS  mandatory
            DESCRIPTION
                "WAN PVC IP address (xxx.xxx.xxx.xxx/xx)"
            ::= { r8WanPvcCFGEntry 5 }

        r8WanPvcRoutingProtocol  OBJECT-TYPE
            SYNTAX  INTEGER {
                    rip1(1),
                    rip2(2),
                    ospf(3),
                    none(4)
                }
            ACCESS  read-write
            STATUS  mandatory
            DESCRIPTION
                "WAN PVC Routing Protocol(OSPF enable/disable in r2OspfIntfAdminSetup Table)"
            ::= { r8WanPvcCFGEntry 6 }

        r8WanPvcNatNapt  OBJECT-TYPE
            SYNTAX  INTEGER {
                    disable(1),
                    nat(2),
                    napt(3)
                }
            ACCESS  read-write
            STATUS  mandatory
            DESCRIPTION
                "WAN PVC NAT/NAPT Function"
            ::= { r8WanPvcCFGEntry 7 }

        r8WanPvcInterfaceMode  OBJECT-TYPE
            SYNTAX  INTEGER {
                    null(0),
                    router(1),
                    bridge(2)
                }
            ACCESS  read-only
            STATUS  mandatory
            DESCRIPTION
                "WAN PVC Interface Mode"
            ::= { r8WanPvcCFGEntry 8 }

        r8WanPvcDLCI  OBJECT-TYPE
            SYNTAX  INTEGER (16..991)
            ACCESS  read-write
            STATUS  mandatory
            DESCRIPTION
                "The PVC's DLCI (16~991)"
            ::= { r8WanPvcCFGEntry 9 }

        r8WanPvcCIR  OBJECT-TYPE
            SYNTAX  INTEGER
            ACCESS  read-write
            STATUS  mandatory
            DESCRIPTION
                "Committed Information Rate (kbps)"
            ::= { r8WanPvcCFGEntry 10 }

        r8WanPvcBc  OBJECT-TYPE
            SYNTAX  INTEGER
            ACCESS  read-write
            STATUS  mandatory
            DESCRIPTION
                "Committed Burst Size (kbits)"
            ::= { r8WanPvcCFGEntry 11 }

        r8WanPvcBe  OBJECT-TYPE
            SYNTAX  INTEGER
            ACCESS  read-write
            STATUS  mandatory
            DESCRIPTION
                "Excess Burst Size (kbits)"
            ::= { r8WanPvcCFGEntry 12 }

        r8WanPvcQdepth  OBJECT-TYPE
            SYNTAX  INTEGER
            ACCESS  read-write
            STATUS  mandatory
            DESCRIPTION
                "Max. queue length"
            ::= { r8WanPvcCFGEntry 13 }

        r8WanPvcInboundPolicy  OBJECT-TYPE
            SYNTAX  DisplayString (SIZE (0..10))
            ACCESS  read-write
            STATUS  mandatory
            DESCRIPTION
                "Wan Pvc inbound policy (off to disable access control)"
            ::= { r8WanPvcCFGEntry 14 }

        r8WanPvcOutboundPolicy  OBJECT-TYPE
            SYNTAX  DisplayString (SIZE (0..10))
            ACCESS  read-write
            STATUS  mandatory
            DESCRIPTION
                "Wan Pvc outbound policy (off to disable access control)"
            ::= { r8WanPvcCFGEntry 15 }


--
-- OCT-RT-B WAN Channel Map
--

    r8WanChannelMap                       OBJECT IDENTIFIER ::= { r8IntfWAN 5 }

--
-- OCT-RT-B WAN Set Channel Map Control
--

        r8WanSetMap  OBJECT-TYPE
            SYNTAX  SEQUENCE OF R8WanSetMapEntry
            ACCESS  not-accessible
            STATUS  mandatory
            DESCRIPTION
                "WAN Set Channel Map Table"
            ::= { r8WanChannelMap 1 }

        r8WanSetMapEntry  OBJECT-TYPE
            SYNTAX  R8WanSetMapEntry
            ACCESS  not-accessible
            STATUS  mandatory
            DESCRIPTION
                "WAN Set Channel Map Entry"
            INDEX { r8WSMSlotIndex }
            ::= { r8WanSetMap 1 }

        R8WanSetMapEntry ::= SEQUENCE {
            r8WSMSlotIndex              LSSlotID,
            r8MapWanNumber              INTEGER,
            r8StartTimeSlot             INTEGER,
            r8ChannelNumber             INTEGER,
            r8MapCommand                INTEGER
        }

        r8WSMSlotIndex  OBJECT-TYPE
            SYNTAX  LSSlotID
            ACCESS  read-only
            STATUS  mandatory
            DESCRIPTION
                "R8 slot"
            ::= { r8WanSetMapEntry 1 }

        r8MapWanNumber  OBJECT-TYPE
            SYNTAX  INTEGER (1..64)
            ACCESS  read-write
            STATUS  mandatory
            DESCRIPTION
                "Wan Index(wan1~wan64)"
            ::= { r8WanSetMapEntry 2 }

        r8StartTimeSlot  OBJECT-TYPE
            SYNTAX  INTEGER (1..128)
            ACCESS  read-write
            STATUS  mandatory
            DESCRIPTION
                "Set start time slot number"
            ::= { r8WanSetMapEntry 3 }

        r8ChannelNumber  OBJECT-TYPE
            SYNTAX  INTEGER (1..128)
            ACCESS  read-write
            STATUS  mandatory
            DESCRIPTION
                "Set channel number"
            ::= { r8WanSetMapEntry 4 }

        r8MapCommand  OBJECT-TYPE
            SYNTAX  INTEGER {
                    no(0),
                    clear(1),
                    set(2),
                    clrSet(3)
                }
            ACCESS  read-write
            STATUS  mandatory
            DESCRIPTION
                "Map Command"
            ::= { r8WanSetMapEntry 5 }

--
-- OCT-RT-B WAN Channel Map Info Table
--

        r8ChannelMapTable  OBJECT-TYPE
            SYNTAX  SEQUENCE OF R8ChannelMapEntry
            ACCESS  not-accessible
            STATUS  mandatory
            DESCRIPTION
                "WAN Channel Map Config Table"
            ::= { r8WanChannelMap 2 }

        r8ChannelMapEntry  OBJECT-TYPE
            SYNTAX  R8ChannelMapEntry
            ACCESS  not-accessible
            STATUS  mandatory
            DESCRIPTION
                "WAN Channel Map Config Entry"
            INDEX { r8CMSlotIndex ,
                    r8TimeSlotIndex }
            ::= { r8ChannelMapTable 1 }

        R8ChannelMapEntry ::= SEQUENCE {
            r8CMSlotIndex               LSSlotID,
            r8TimeSlotIndex             INTEGER,
            r8MapToWanNum               WanID
        }

        r8CMSlotIndex  OBJECT-TYPE
            SYNTAX  LSSlotID
            ACCESS  read-only
            STATUS  mandatory
            DESCRIPTION
                "R8 slot"
            ::= { r8ChannelMapEntry 1 }

        r8TimeSlotIndex  OBJECT-TYPE
            SYNTAX  INTEGER (1..128)
            ACCESS  read-only
            STATUS  mandatory
            DESCRIPTION
                "Time slot number"
            ::= { r8ChannelMapEntry 2 }

        r8MapToWanNum  OBJECT-TYPE
            SYNTAX  WanID
            ACCESS  read-only
            STATUS  mandatory
            DESCRIPTION
                "Time slot number"
            ::= { r8ChannelMapEntry 3 }

--
-- OCT-RT-B WAN QoS Table
--

    r8WanQoS                          OBJECT IDENTIFIER ::= { r8IntfWAN 6 }

--
-- R8 WAN Qos Policy Table
--
        r8WanQosPolicyTable  OBJECT-TYPE
            SYNTAX  SEQUENCE OF R8WanQosPolicyEntry
            ACCESS  not-accessible
            STATUS  mandatory
            DESCRIPTION
                "Wan Qos Policy Table."
            ::= { r8WanQoS 1 }

        r8WanQosPolicyEntry  OBJECT-TYPE
            SYNTAX  R8WanQosPolicyEntry
            ACCESS  not-accessible
            STATUS  mandatory
            DESCRIPTION
                "Wan Qos Policy Entry"
            INDEX { r8WQPSlotIndex ,
                    r8WanQPIndex ,
                    r8WanQosPolicyNumber }
            ::= { r8WanQosPolicyTable 1 }

        R8WanQosPolicyEntry ::= SEQUENCE {
            r8WQPSlotIndex              LSSlotID,
            r8WanQPIndex                INTEGER,
            r8WanQosPolicyNumber        INTEGER,
            r8WanQosPolicySrcIP         DisplayString,
            r8WanQosPolicyDstIP         DisplayString,
            r8WanQosPolicyProtocol      DisplayString,
            r8WanQosPolicyRate          DisplayString,
            r8WanQosPolicySrcPort       DisplayString,
            r8WanQosPolicyDstPort       DisplayString,
            r8WanQosPolicyDSCP          DisplayString
        }

        r8WQPSlotIndex  OBJECT-TYPE
            SYNTAX  LSSlotID
            ACCESS  read-only
            STATUS  mandatory
            DESCRIPTION
                "R8 slot"
            ::= { r8WanQosPolicyEntry 1 }

        r8WanQPIndex  OBJECT-TYPE
            SYNTAX  INTEGER (1..64)
            ACCESS  read-only
            STATUS  mandatory
            DESCRIPTION
                "Interface WAN1-WAN2"
            ::= { r8WanQosPolicyEntry 2 }

        r8WanQosPolicyNumber  OBJECT-TYPE
            SYNTAX  INTEGER
            ACCESS  read-only
            STATUS  mandatory
            DESCRIPTION
                "WAN Qos Policy Number"
            ::= { r8WanQosPolicyEntry 3 }

        r8WanQosPolicySrcIP  OBJECT-TYPE
            SYNTAX  DisplayString
            ACCESS  read-only
            STATUS  mandatory
            DESCRIPTION
                "Wan Qos Policy Source IP/Perfix"
            ::= { r8WanQosPolicyEntry 4 }

        r8WanQosPolicyDstIP  OBJECT-TYPE
            SYNTAX  DisplayString
            ACCESS  read-only
            STATUS  mandatory
            DESCRIPTION
                "Wan Qos Policy Destination IP/Perfix"
            ::= { r8WanQosPolicyEntry 5 }

        r8WanQosPolicyProtocol  OBJECT-TYPE
            SYNTAX  DisplayString
            ACCESS  read-only
            STATUS  mandatory
            DESCRIPTION
                "WAN Qos Policy Protocol"
            ::= { r8WanQosPolicyEntry 6 }

        r8WanQosPolicyRate  OBJECT-TYPE
            SYNTAX  DisplayString
            ACCESS  read-only
            STATUS  mandatory
            DESCRIPTION
                "Wan Qos Policy Rate"
            ::= { r8WanQosPolicyEntry 7 }

        r8WanQosPolicySrcPort  OBJECT-TYPE
            SYNTAX  DisplayString
            ACCESS  read-only
            STATUS  mandatory
            DESCRIPTION
                "Wan Qos Policy Source Port"
            ::= { r8WanQosPolicyEntry 8 }

        r8WanQosPolicyDstPort  OBJECT-TYPE
            SYNTAX  DisplayString
            ACCESS  read-only
            STATUS  mandatory
            DESCRIPTION
                "Wan Qos Policy Destination Port"
            ::= { r8WanQosPolicyEntry 9 }

        r8WanQosPolicyDSCP  OBJECT-TYPE
            SYNTAX  DisplayString
            ACCESS  read-only
            STATUS  mandatory
            DESCRIPTION
                "Wan Qos Policy DSCP Information"
            ::= { r8WanQosPolicyEntry 10 }


--
-- R8 WAN Qos Policy Control Table
--

    r8WanQosPolicyControl                        OBJECT IDENTIFIER ::= { r8WanQoS 2 }

--
-- R8 WAN Qos Append and Insert Policy Table
--

        r8WanQosAppAndInsPolicy  OBJECT-TYPE
            SYNTAX  SEQUENCE OF R8WanQosAppAndInsPolicyEntry
            ACCESS  not-accessible
            STATUS  mandatory
            DESCRIPTION
                "Append od Insert a traffic control policy Table."
            ::= { r8WanQosPolicyControl 1 }

        r8WanQosAppAndInsPolicyEntry  OBJECT-TYPE
            SYNTAX  R8WanQosAppAndInsPolicyEntry
            ACCESS  not-accessible
            STATUS  mandatory
            DESCRIPTION
                "Append od Insert a traffic control policy Entry"
            INDEX { r8WQAIPSlotIndex }
            ::= { r8WanQosAppAndInsPolicy 1 }

        R8WanQosAppAndInsPolicyEntry ::= SEQUENCE {
            r8WQAIPSlotIndex                LSSlotID,
            r8WanAppInstPolicyWanNum        INTEGER (1..64),
            r8WanAppInstPolicySrcIP         DisplayString (SIZE (1..20)),
            r8WanAppInstPolicySrcIPPrefix   DisplayString (SIZE (0..2)),
            r8WanAppInstPolicyDstIP         DisplayString (SIZE (1..20)),
            r8WanAppInstPolicyDstIPPrefix   DisplayString (SIZE (0..2)),
            r8WanAppInstPolicySrcPort       DisplayString (SIZE (0..25)),
            r8WanAppInstPolicyDstPort       DisplayString (SIZE (0..25)),
            r8WanAppInstPolicyProtocol      DisplayString (SIZE (1..10)),
            r8WanAppInstPolicyRate          DisplayString (SIZE (1..25)),
            r8WanAppInstPolicyRateType      INTEGER,
            r8WanInstPolicyNum              INTEGER (0..32),
            r8WanAppInstPolicyDSCP          DisplayString (SIZE (0..255)),
            r8WanAppInstPolicyCommand       INTEGER
        }

        r8WQAIPSlotIndex  OBJECT-TYPE
            SYNTAX  LSSlotID
            ACCESS  read-only
            STATUS  mandatory
            DESCRIPTION
                "R8 slot"
            ::= { r8WanQosAppAndInsPolicyEntry 1 }

        r8WanAppInstPolicyWanNum  OBJECT-TYPE
            SYNTAX  INTEGER   (1..64)
            ACCESS  read-write
            STATUS  mandatory
            DESCRIPTION
                "Wan Number(Wan 1~64)"
            ::= { r8WanQosAppAndInsPolicyEntry 2 }

        r8WanAppInstPolicySrcIP  OBJECT-TYPE
            SYNTAX  DisplayString (SIZE (1..20))
            ACCESS  read-write
            STATUS  mandatory
            DESCRIPTION
                "Policy Source IP(xxx.xxx.xxx.xxx)"
            ::= { r8WanQosAppAndInsPolicyEntry 3 }

        r8WanAppInstPolicySrcIPPrefix  OBJECT-TYPE
            SYNTAX  DisplayString (SIZE (0..2))
            ACCESS  read-write
            STATUS  mandatory
            DESCRIPTION
                "Policy Source IP Prefix(skip if src_ip is 'any')"
            ::= { r8WanQosAppAndInsPolicyEntry 4 }

        r8WanAppInstPolicyDstIP  OBJECT-TYPE
            SYNTAX  DisplayString (SIZE (1..20))
            ACCESS  read-write
            STATUS  mandatory
            DESCRIPTION
                "Policy Destination IP(xxx.xxx.xxx.xxx)"
            ::= { r8WanQosAppAndInsPolicyEntry 5 }

        r8WanAppInstPolicyDstIPPrefix  OBJECT-TYPE
            SYNTAX  DisplayString (SIZE (0..2))
            ACCESS  read-write
            STATUS  mandatory
            DESCRIPTION
                "Policy Destination IP Prefix(skip if dst_ip is 'any')"
            ::= { r8WanQosAppAndInsPolicyEntry 6 }

        r8WanAppInstPolicySrcPort  OBJECT-TYPE
            SYNTAX  DisplayString (SIZE (0..25))
            ACCESS  read-write
            STATUS  mandatory
            DESCRIPTION
                "Policy Source Port(any or min[-max] only for TCP/UDP, (no space before and after '-')"
            ::= { r8WanQosAppAndInsPolicyEntry 7 }

        r8WanAppInstPolicyDstPort  OBJECT-TYPE
            SYNTAX  DisplayString (SIZE (0..25))
            ACCESS  read-write
            STATUS  mandatory
            DESCRIPTION
                "Policy Destination Port(any or min[-max] only for TCP/UDP, (no space before and after '-')"
            ::= { r8WanQosAppAndInsPolicyEntry 8 }

        r8WanAppInstPolicyProtocol  OBJECT-TYPE
            SYNTAX  DisplayString (SIZE (1..10))
            ACCESS  read-write
            STATUS  mandatory
            DESCRIPTION
                "Policy Protocol(TCP or UDP or ICMP or Any or 0~255)"
            ::= { r8WanQosAppAndInsPolicyEntry 9 }

        r8WanAppInstPolicyRate  OBJECT-TYPE
            SYNTAX  DisplayString (SIZE (1..25))
            ACCESS  read-write
            STATUS  mandatory
            DESCRIPTION
                "Policy Rate(Committed access rate in min[-max] format, (no space before and after '-') )"
            ::= { r8WanQosAppAndInsPolicyEntry 10 }

        r8WanAppInstPolicyRateType  OBJECT-TYPE
            SYNTAX  INTEGER {
                    kbps(1),
                    mbps(2)
                }
            ACCESS  read-write
            STATUS  mandatory
            DESCRIPTION
                "Policy Rate Type(type of bandwidth for rate in bits per sec)"
            ::= { r8WanQosAppAndInsPolicyEntry 11 }

        r8WanInstPolicyNum  OBJECT-TYPE
            SYNTAX  INTEGER (0..32)
            ACCESS  read-write
            STATUS  mandatory
            DESCRIPTION
                "Policy number before which new policy will be inserted"
            ::= { r8WanQosAppAndInsPolicyEntry 12 }

        r8WanAppInstPolicyDSCP  OBJECT-TYPE
            SYNTAX  DisplayString (SIZE (0..255))
            ACCESS  read-write
            STATUS  mandatory
            DESCRIPTION
                "Policy DSCP"
            ::= { r8WanQosAppAndInsPolicyEntry 13 }

        r8WanAppInstPolicyCommand  OBJECT-TYPE
            SYNTAX  INTEGER {
                    append(1),
                    insert(2)
                }
            ACCESS  read-write
            STATUS  mandatory
            DESCRIPTION
                "Wan Qos Policy Command"
            ::= { r8WanQosAppAndInsPolicyEntry 14 }

--
-- R8 WAN Qos Delete Policy Table
--

        r8WanQosDeletePolicy  OBJECT-TYPE
            SYNTAX  SEQUENCE OF R8WanQosDeletePolicyEntry
            ACCESS  not-accessible
            STATUS  mandatory
            DESCRIPTION
                "Delete a traffic control policy Table."
            ::= { r8WanQosPolicyControl 2 }

        r8WanQosDeletePolicyEntry  OBJECT-TYPE
            SYNTAX  R8WanQosDeletePolicyEntry
            ACCESS  not-accessible
            STATUS  mandatory
            DESCRIPTION
                "Delete a traffic control policy Entry"
            INDEX { r8WQDPSlotIndex }
            ::= { r8WanQosDeletePolicy 1 }

        R8WanQosDeletePolicyEntry ::= SEQUENCE {
            r8WQDPSlotIndex             LSSlotID,
            r8WanDelPolicyWanNum        INTEGER (1..64),
            r8WanDelPolicyNumber        INTEGER (1..32),
            r8WanDelPolicyCommand       INTEGER
        }

        r8WQDPSlotIndex  OBJECT-TYPE
            SYNTAX  LSSlotID
            ACCESS  read-only
            STATUS  mandatory
            DESCRIPTION
                "R8 slot"
            ::= { r8WanQosDeletePolicyEntry 1 }

        r8WanDelPolicyWanNum  OBJECT-TYPE
            SYNTAX  INTEGER (1..64)
            ACCESS  read-write
            STATUS  mandatory
            DESCRIPTION
                "Wan Number(Wan 1~64)"
            ::= { r8WanQosDeletePolicyEntry 2 }

        r8WanDelPolicyNumber  OBJECT-TYPE
            SYNTAX  INTEGER (1..32)
            ACCESS  read-write
            STATUS  mandatory
            DESCRIPTION
                "Policy Number(1~32)"
            ::= { r8WanQosDeletePolicyEntry 3 }

        r8WanDelPolicyCommand  OBJECT-TYPE
            SYNTAX  INTEGER {
                    delete(1)
                }
            ACCESS  read-write
            STATUS  mandatory
            DESCRIPTION
                "Delete Policy Command"
            ::= { r8WanQosDeletePolicyEntry 4 }


--
-- OCT-RT-B Virtual Interface
--

    r8IntfVirtual         OBJECT IDENTIFIER ::= { r8Interface 3 }

--
-- OCT-RT-B Virtual Interface Config
--

        r8VirtualIntfCFG  OBJECT-TYPE
            SYNTAX  SEQUENCE OF R8VirtualIntfCFGEntry
            ACCESS  not-accessible
            STATUS  mandatory
            DESCRIPTION
                "Virtual Interface Configuration Table."
            ::= { r8IntfVirtual 1 }

        r8VirtualIntfCFGEntry  OBJECT-TYPE
            SYNTAX  R8VirtualIntfCFGEntry
            ACCESS  not-accessible
            STATUS  mandatory
            DESCRIPTION
                "Virtual Interface Configuration Entry"
            INDEX { r8VICSlotIndex ,
                    r8VIntfIndex }
            ::= { r8VirtualIntfCFG 1 }

        R8VirtualIntfCFGEntry ::= SEQUENCE {
            r8VICSlotIndex              LSSlotID,
            r8VIntfIndex                INTEGER,
            r8VIntfName                 DisplayString,
            r8VIntfRoutingProtocol      INTEGER,
            r8VIntfLayer2Protocol       INTEGER,
            r8VIntfInterfaceMode        INTEGER,
            r8VIntfInboundPolicy        DisplayString,
            r8VIntfOutboundPolicy       DisplayString,
            r8VIntfStatus               INTEGER
        }

        r8VICSlotIndex  OBJECT-TYPE
            SYNTAX  LSSlotID
            ACCESS  read-only
            STATUS  mandatory
            DESCRIPTION
                "R8 slot"
            ::= { r8VirtualIntfCFGEntry 1 }

        r8VIntfIndex  OBJECT-TYPE
            SYNTAX  INTEGER
            ACCESS  read-only
            STATUS  mandatory
            DESCRIPTION
                "Virtual interface index"
            ::= { r8VirtualIntfCFGEntry 2 }

        r8VIntfName  OBJECT-TYPE
            SYNTAX  DisplayString (SIZE (1..16))
            ACCESS  read-only
            STATUS  mandatory
            DESCRIPTION
                "Virtual interface name"
            ::= { r8VirtualIntfCFGEntry 3 }

        r8VIntfRoutingProtocol  OBJECT-TYPE
            SYNTAX  INTEGER {
                    rip1(1),
                    rip2(2),
                    ospf(3),
                    none(4)
                }
            ACCESS  read-write
            STATUS  mandatory
            DESCRIPTION
                "Virtual Interface Routing Protocol(OSPF enable/disable in r8OspfIntfAdminSetup Table)"
            ::= { r8VirtualIntfCFGEntry 4 }

        r8VIntfLayer2Protocol  OBJECT-TYPE
            SYNTAX  INTEGER {
                    ppp(3)
                }
            ACCESS  read-only
            STATUS  mandatory
            DESCRIPTION
                "Virtual Interface Layer2 Protocol"
            ::= { r8VirtualIntfCFGEntry 5 }

        r8VIntfInterfaceMode  OBJECT-TYPE
            SYNTAX  INTEGER {
                    null(0),
                    router(1),
                    bridge(2)
                }
            ACCESS  read-only
            STATUS  mandatory
            DESCRIPTION
                "Interface Mode of Virtual Interface"
            ::= { r8VirtualIntfCFGEntry 6 }

        r8VIntfInboundPolicy  OBJECT-TYPE
            SYNTAX  DisplayString (SIZE (0..10))
            ACCESS  read-write
            STATUS  mandatory
            DESCRIPTION
                "Virtual Interface inbound policy (off to disable access control)"
            ::= { r8VirtualIntfCFGEntry 7 }

        r8VIntfOutboundPolicy  OBJECT-TYPE
            SYNTAX  DisplayString (SIZE (0..10))
            ACCESS  read-write
            STATUS  mandatory
            DESCRIPTION
                "Virtual Interface outbound policy (off to disable access control)"
            ::= { r8VirtualIntfCFGEntry 8 }

        r8VIntfStatus  OBJECT-TYPE
            SYNTAX  INTEGER {
                    down(1),
                    up(2)
                }
            ACCESS  read-only
            STATUS  mandatory
            DESCRIPTION
                "Virtual Interface Status"
            ::= { r8VirtualIntfCFGEntry 9 }


--
-- OCT-RT-B Policy
--

    r8Policy                      OBJECT IDENTIFIER ::= { oct-rt-b-card 5 }

--
-- R8 Filter Info
--

        r8FilterInfo  OBJECT-TYPE
            SYNTAX  SEQUENCE OF R8FilterInfoEntry
            ACCESS  not-accessible
            STATUS  mandatory
            DESCRIPTION
                "filter information Table"
            ::= { r8Policy 1 }

        r8FilterInfoEntry  OBJECT-TYPE
            SYNTAX  R8FilterInfoEntry
            ACCESS  not-accessible
            STATUS  mandatory
            DESCRIPTION
                "filter information Entry"
            INDEX { r8FISlotIndex ,
                    r8FilterIndex ,
                    r8RuleIndex }
            ::= { r8FilterInfo 1 }

        R8FilterInfoEntry ::= SEQUENCE {
            r8FISlotIndex               LSSlotID,
            r8FilterIndex               INTEGER,
            r8RuleIndex                 INTEGER,
            r8FilterName                DisplayString,
            r8FilterAction              INTEGER,
            r8FilterSrcAddr             DisplayString,
            r8FilterDestAddr            DisplayString,
            r8FilterProtocol            INTEGER,
            r8FilterPortLow             INTEGER,
            r8FilterPortHigh            INTEGER
        }

        r8FISlotIndex  OBJECT-TYPE
            SYNTAX  LSSlotID
            ACCESS  read-only
            STATUS  mandatory
            DESCRIPTION
                "R8 slot"
            ::= { r8FilterInfoEntry 1 }

        r8FilterIndex  OBJECT-TYPE
            SYNTAX  INTEGER
            ACCESS  read-only
            STATUS  mandatory
            DESCRIPTION
                " Filter List Index "
            ::= { r8FilterInfoEntry 2 }

        r8RuleIndex  OBJECT-TYPE
            SYNTAX  INTEGER
            ACCESS  read-only
            STATUS  mandatory
            DESCRIPTION
                "filter rule index"
            ::= { r8FilterInfoEntry 3 }

        r8FilterName  OBJECT-TYPE
            SYNTAX  DisplayString (SIZE (0..10))
            ACCESS  read-only
            STATUS  mandatory
            DESCRIPTION
                "filter list Name"
            ::= { r8FilterInfoEntry 4 }

        r8FilterAction  OBJECT-TYPE
            SYNTAX  INTEGER{
                    deny(1),
                    permit(2)
                }
            ACCESS  read-only
            STATUS  mandatory
            DESCRIPTION
                " Filter action"
            ::= { r8FilterInfoEntry 5 }

        r8FilterSrcAddr  OBJECT-TYPE
            SYNTAX  DisplayString (SIZE (0..20))
            ACCESS  read-only
            STATUS  mandatory
            DESCRIPTION
                "source address of filter action (xx.xx.xx.xx/xx)"
            ::= { r8FilterInfoEntry 6 }

        r8FilterDestAddr  OBJECT-TYPE
            SYNTAX  DisplayString (SIZE (0..20))
            ACCESS  read-only
            STATUS  mandatory
            DESCRIPTION
                "destination address of filter action (xx.xx.xx.xx/xx)"
            ::= { r8FilterInfoEntry 7 }

        r8FilterProtocol  OBJECT-TYPE
            SYNTAX  INTEGER{
                    tcp(1),
                    udp(2),
                    icmp(3),
                    any(4)
                }
            ACCESS  read-only
            STATUS  mandatory
            DESCRIPTION
                "protocol of filter action"
            ::= { r8FilterInfoEntry 8 }

        r8FilterPortLow  OBJECT-TYPE
            SYNTAX  INTEGER
            ACCESS  read-only
            STATUS  mandatory
            DESCRIPTION
                "Low port of the port range for TCP/UDP"
            ::= { r8FilterInfoEntry 9 }

        r8FilterPortHigh  OBJECT-TYPE
            SYNTAX  INTEGER
            ACCESS  read-only
            STATUS  mandatory
            DESCRIPTION
                "High port of the port range for TCP/UDP"
            ::= { r8FilterInfoEntry 10 }

--
-- OCT-RT-B Mac Filter Info
--

        r8MacFilterInfo  OBJECT-TYPE
            SYNTAX  SEQUENCE OF R8MacFilterInfoEntry
            ACCESS  not-accessible
            STATUS  mandatory
            DESCRIPTION
                "Mac filter information Table"
            ::= { r8Policy 2 }

        r8MacFilterInfoEntry  OBJECT-TYPE
            SYNTAX  R8MacFilterInfoEntry
            ACCESS  not-accessible
            STATUS  mandatory
            DESCRIPTION
                "Mac filter information Entry"
            INDEX { r8MFISlotIndex ,
                    r8MacFilterIndex ,
                    r8MacFilterRuleIndex }
            ::= { r8MacFilterInfo 1 }

        R8MacFilterInfoEntry ::= SEQUENCE {
            r8MFISlotIndex              LSSlotID,
            r8MacFilterIndex            INTEGER,
            r8MacFilterRuleIndex        INTEGER,
            r8MacFilterName             DisplayString,
            r8MacFilterMacAddress       DisplayString
        }

        r8MFISlotIndex  OBJECT-TYPE
            SYNTAX  LSSlotID
            ACCESS  read-only
            STATUS  mandatory
            DESCRIPTION
                "R8 slot"
            ::= { r8MacFilterInfoEntry 1 }

        r8MacFilterIndex  OBJECT-TYPE
            SYNTAX  INTEGER
            ACCESS  read-only
            STATUS  mandatory
            DESCRIPTION
                "Mac Filter List Index "
            ::= { r8MacFilterInfoEntry 2 }

        r8MacFilterRuleIndex  OBJECT-TYPE
            SYNTAX  INTEGER
            ACCESS  read-only
            STATUS  mandatory
            DESCRIPTION
                "MAc Filter rule index"
            ::= { r8MacFilterInfoEntry 3 }

        r8MacFilterName  OBJECT-TYPE
            SYNTAX  DisplayString (SIZE (0..10))
            ACCESS  read-only
            STATUS  mandatory
            DESCRIPTION
                "Mac Filter list Name"
            ::= { r8MacFilterInfoEntry 4 }

        r8MacFilterMacAddress  OBJECT-TYPE
            SYNTAX  DisplayString (SIZE (0..20))
            ACCESS  read-only
            STATUS  mandatory
            DESCRIPTION
                "Mac Filter Mac Address"
            ::= { r8MacFilterInfoEntry 5 }


-- OCT-RT-B Filter Control
--

    r8FilterControl                      OBJECT IDENTIFIER ::= { r8Policy 3 }

--
-- OCT-RT-B Create & Destroy Filter list Table
--

        r8CreateDestroyFilter  OBJECT-TYPE
            SYNTAX  SEQUENCE OF R8CreateDestroyFilterEntry
            ACCESS  not-accessible
            STATUS  mandatory
            DESCRIPTION
                "Create and Destroy Filter List Table"
            ::= { r8FilterControl 1 }

        r8CreateDestroyFilterEntry  OBJECT-TYPE
            SYNTAX  R8CreateDestroyFilterEntry
            ACCESS  not-accessible
            STATUS  mandatory
            DESCRIPTION
                "Create and Destroy Filter List Entry"
            INDEX { r8CDFSlotIndex }
            ::= { r8CreateDestroyFilter 1 }

        R8CreateDestroyFilterEntry ::= SEQUENCE {
            r8CDFSlotIndex              LSSlotID,
            r8CreDesFilterName          DisplayString,
            r8CreDesFilterCMD           INTEGER
        }

        r8CDFSlotIndex  OBJECT-TYPE
            SYNTAX  LSSlotID
            ACCESS  read-only
            STATUS  mandatory
            DESCRIPTION
                "R8 slot"
            ::= { r8CreateDestroyFilterEntry 1 }

        r8CreDesFilterName  OBJECT-TYPE
            SYNTAX  DisplayString (SIZE (0..10))
            ACCESS  read-write
            STATUS  mandatory
            DESCRIPTION
                "Filter List Name"
            ::= { r8CreateDestroyFilterEntry 2 }

        r8CreDesFilterCMD  OBJECT-TYPE
            SYNTAX  INTEGER{
                    create-filter(1),
                    destroy-filter(2),
                    create-mac-filter(3),
                    destroy-mac-filter(4)
                }
            ACCESS  read-write
            STATUS  mandatory
            DESCRIPTION
                " Filter List Command"
            ::= { r8CreateDestroyFilterEntry 3 }

--
-- OCT-RT-B Add Filter Rule
--

        r8AddFilterRule  OBJECT-TYPE
            SYNTAX  SEQUENCE OF R8AddFilterRuleEntry
            ACCESS  not-accessible
            STATUS  mandatory
            DESCRIPTION
                "Append filter rule Table"
            ::= { r8FilterControl 2 }

        r8AddFilterRuleEntry  OBJECT-TYPE
            SYNTAX  R8AddFilterRuleEntry
            ACCESS  not-accessible
            STATUS  mandatory
            DESCRIPTION
                "Append filter rule Entry"
            INDEX { r8AFRSlotIndex }
            ::= { r8AddFilterRule 1 }

        R8AddFilterRuleEntry ::= SEQUENCE {
            r8AFRSlotIndex              LSSlotID,
            r8AddFilterName             DisplayString,
            r8AddFilterAction           INTEGER,
            r8AddFilterSrcAddr          DisplayString,
            r8AddFilterDestAddr         DisplayString,
            r8AddFilterProtocol         INTEGER,
            r8AddFilterPortLow          INTEGER,
            r8AddFilterPortHigh         INTEGER,
            r8AddFilterRuleCMD          INTEGER
        }

        r8AFRSlotIndex  OBJECT-TYPE
            SYNTAX  LSSlotID
            ACCESS  read-only
            STATUS  mandatory
            DESCRIPTION
                "R8 slot"
            ::= { r8AddFilterRuleEntry 1 }

        r8AddFilterName  OBJECT-TYPE
            SYNTAX  DisplayString (SIZE (0..10))
            ACCESS  read-write
            STATUS  mandatory
            DESCRIPTION
                "Filter List Name"
            ::= { r8AddFilterRuleEntry 2 }

        r8AddFilterAction  OBJECT-TYPE
            SYNTAX  INTEGER{
                    deny(1),
                    permit(2)
                }
            ACCESS  read-write
            STATUS  mandatory
            DESCRIPTION
                " Filter action"
            ::= { r8AddFilterRuleEntry 3 }

        r8AddFilterSrcAddr  OBJECT-TYPE
            SYNTAX  DisplayString (SIZE (0..20))
            ACCESS  read-write
            STATUS  mandatory
            DESCRIPTION
                "source address of filter action (xx.xx.xx.xx/xx)"
            ::= { r8AddFilterRuleEntry 4 }

        r8AddFilterDestAddr  OBJECT-TYPE
            SYNTAX  DisplayString (SIZE (0..20))
            ACCESS  read-write
            STATUS  mandatory
            DESCRIPTION
                "destination address of filter action (xx.xx.xx.xx/xx)"
            ::= { r8AddFilterRuleEntry 5 }

        r8AddFilterProtocol  OBJECT-TYPE
            SYNTAX  INTEGER{
                    tcp(1),
                    udp(2),
                    icmp(3),
                    any(4)
                }
            ACCESS  read-write
            STATUS  mandatory
            DESCRIPTION
                "protocol of filter action"
            ::= { r8AddFilterRuleEntry 6 }

        r8AddFilterPortLow  OBJECT-TYPE
            SYNTAX  INTEGER
            ACCESS  read-write
            STATUS  mandatory
            DESCRIPTION
                "Low port of the port range for TCP/UDP"
            ::= { r8AddFilterRuleEntry 7 }

        r8AddFilterPortHigh  OBJECT-TYPE
            SYNTAX  INTEGER
            ACCESS  read-write
            STATUS  mandatory
            DESCRIPTION
                "High port of the port range for TCP/UDP"
            ::= { r8AddFilterRuleEntry 8 }

        r8AddFilterRuleCMD  OBJECT-TYPE
            SYNTAX  INTEGER{
                    append(1)
                }
            ACCESS  read-write
            STATUS  mandatory
            DESCRIPTION
                " Append Filter rule"
            ::= { r8AddFilterRuleEntry 9 }



 --
-- OCT-RT-B Add Mac Filter Rule
--

        r8AddMacFilterRule  OBJECT-TYPE
            SYNTAX  SEQUENCE OF R8AddMacFilterRuleEntry
            ACCESS  not-accessible
            STATUS  mandatory
            DESCRIPTION
                "Append Mac filter rule Table"
            ::= { r8FilterControl 3 }

        r8AddMacFilterRuleEntry  OBJECT-TYPE
            SYNTAX  R8AddMacFilterRuleEntry
            ACCESS  not-accessible
            STATUS  mandatory
            DESCRIPTION
                "Append Mac filter rule Entry"
            INDEX { r8AMFRSlotIndex }
            ::= { r8AddMacFilterRule 1 }

        R8AddMacFilterRuleEntry ::= SEQUENCE {
            r8AMFRSlotIndex             LSSlotID,
            r8AddMacFilterName          DisplayString,
            r8AddMacFilterMacAddr       DisplayString,
            r8AddMacFilterRuleCMD       INTEGER
        }

        r8AMFRSlotIndex  OBJECT-TYPE
            SYNTAX  LSSlotID
            ACCESS  read-only
            STATUS  mandatory
            DESCRIPTION
                "R8 slot"
            ::= { r8AddMacFilterRuleEntry 1 }

        r8AddMacFilterName  OBJECT-TYPE
            SYNTAX  DisplayString (SIZE (0..10))
            ACCESS  read-write
            STATUS  mandatory
            DESCRIPTION
                "Mac Filter List Name"
            ::= { r8AddMacFilterRuleEntry 2 }

        r8AddMacFilterMacAddr  OBJECT-TYPE
            SYNTAX  DisplayString (SIZE (0..20))
            ACCESS  read-write
            STATUS  mandatory
            DESCRIPTION
                "Mac Filter Mac address"
            ::= { r8AddMacFilterRuleEntry 3 }

        r8AddMacFilterRuleCMD  OBJECT-TYPE
            SYNTAX  INTEGER{
                    append(1)
                }
            ACCESS  read-write
            STATUS  mandatory
            DESCRIPTION
                " Append Mac Filter rule"
            ::= { r8AddMacFilterRuleEntry 4 }

--
-- OCT-RT-B Delete Filter Rule
--

        r8DelFilterRule  OBJECT-TYPE
            SYNTAX  SEQUENCE OF R8DelFilterRuleEntry
            ACCESS  not-accessible
            STATUS  mandatory
            DESCRIPTION
                "Delete filter rule Table"
            ::= { r8FilterControl 4 }

        r8DelFilterRuleEntry  OBJECT-TYPE
            SYNTAX  R8DelFilterRuleEntry
            ACCESS  not-accessible
            STATUS  mandatory
            DESCRIPTION
                "Delete filter rule Entry"
            INDEX { r8DFRSlotIndex }
            ::= { r8DelFilterRule 1 }

        R8DelFilterRuleEntry ::= SEQUENCE {
            r8DFRSlotIndex              LSSlotID,
            r8DelFilterName             DisplayString,
            r8DelStartIndex             INTEGER,
            r8DelEndIndex               INTEGER,
            r8DelFilterRuleCMD          INTEGER
        }

        r8DFRSlotIndex  OBJECT-TYPE
            SYNTAX  LSSlotID
            ACCESS  read-only
            STATUS  mandatory
            DESCRIPTION
                "R8 slot"
            ::= { r8DelFilterRuleEntry 1 }

        r8DelFilterName  OBJECT-TYPE
            SYNTAX  DisplayString (SIZE (0..10))
            ACCESS  read-write
            STATUS  mandatory
            DESCRIPTION
                "filter list Name"
            ::= { r8DelFilterRuleEntry 2 }

        r8DelStartIndex  OBJECT-TYPE
            SYNTAX  INTEGER
            ACCESS  read-write
            STATUS  mandatory
            DESCRIPTION
                "start index of list which will be deleted"
            ::= { r8DelFilterRuleEntry 3 }

        r8DelEndIndex  OBJECT-TYPE
            SYNTAX  INTEGER
            ACCESS  read-write
            STATUS  mandatory
            DESCRIPTION
                "end index of list which will be deleted"
            ::= { r8DelFilterRuleEntry 4 }

        r8DelFilterRuleCMD  OBJECT-TYPE
            SYNTAX  INTEGER{
                    delete(1)
                }
            ACCESS  read-write
            STATUS  mandatory
            DESCRIPTION
                "delete filter rule command"
            ::= { r8DelFilterRuleEntry 5 }


--
-- OCT-RT-B Delete Mac Filter Rule
--

        r8DelMacFilterRule  OBJECT-TYPE
            SYNTAX  SEQUENCE OF R8DelMacFilterRuleEntry
            ACCESS  not-accessible
            STATUS  mandatory
            DESCRIPTION
                "Delete Mac filter rule Table"
            ::= { r8FilterControl 5 }

        r8DelMacFilterRuleEntry  OBJECT-TYPE
            SYNTAX  R8DelMacFilterRuleEntry
            ACCESS  not-accessible
            STATUS  mandatory
            DESCRIPTION
                "Delete Mac filter rule Entry"
            INDEX { r8DMFRSlotIndex }
            ::= { r8DelMacFilterRule 1 }

        R8DelMacFilterRuleEntry ::= SEQUENCE {
            r8DMFRSlotIndex             LSSlotID,
            r8DelMacFilterName          DisplayString,
            r8DelMacFilterMacAddr       DisplayString,
            r8DelMacFilterRuleCMD       INTEGER
        }

        r8DMFRSlotIndex  OBJECT-TYPE
            SYNTAX  LSSlotID
            ACCESS  read-only
            STATUS  mandatory
            DESCRIPTION
                "R8 slot"
            ::= { r8DelMacFilterRuleEntry 1 }

        r8DelMacFilterName  OBJECT-TYPE
            SYNTAX  DisplayString (SIZE (0..10))
            ACCESS  read-write
            STATUS  mandatory
            DESCRIPTION
                "mac filter list Name"
            ::= { r8DelMacFilterRuleEntry 2 }

        r8DelMacFilterMacAddr  OBJECT-TYPE
            SYNTAX  DisplayString (SIZE (0..20))
            ACCESS  read-write
            STATUS  mandatory
            DESCRIPTION
                "mac address"
            ::= { r8DelMacFilterRuleEntry 3 }

        r8DelMacFilterRuleCMD  OBJECT-TYPE
            SYNTAX  INTEGER{
                    delete(1)
                }
            ACCESS  read-write
            STATUS  mandatory
            DESCRIPTION
                "delete mac filter rule command"
            ::= { r8DelMacFilterRuleEntry 4 }

--
-- OCT-RT-B Route
--

    r8Route                      OBJECT IDENTIFIER ::= { oct-rt-b-card 6 }

--
-- OCT-RT-B Static Route Table
--

        r8StaticRouteTable  OBJECT-TYPE
            SYNTAX  SEQUENCE OF R8StaticRouteEntry
            ACCESS  not-accessible
            STATUS  mandatory
            DESCRIPTION
                "Static Route Table"
            ::= { r8Route 1 }

        r8StaticRouteEntry  OBJECT-TYPE
            SYNTAX  R8StaticRouteEntry
            ACCESS  not-accessible
            STATUS  mandatory
            DESCRIPTION
                "Static Route Entry"
            INDEX { r8SRSlotIndex ,
                    r8RouteIndex }
            ::= { r8StaticRouteTable 1 }

        R8StaticRouteEntry ::= SEQUENCE {
            r8SRSlotIndex               LSSlotID,
            r8RouteIndex                INTEGER,
            r8StaticRouteNetAddr        DisplayString,
            r8StaticRouteNetMask        DisplayString,
            r8StaticRouteGatewayAddr    DisplayString,
            r8StaticRouteInterface      DisplayString
        }

        r8SRSlotIndex  OBJECT-TYPE
            SYNTAX  LSSlotID
            ACCESS  read-only
            STATUS  mandatory
            DESCRIPTION
                "R8 slot"
            ::= { r8StaticRouteEntry 1 }

        r8RouteIndex  OBJECT-TYPE
            SYNTAX  INTEGER
            ACCESS  read-only
            STATUS  mandatory
            DESCRIPTION
                "routing table entry index"
            ::= { r8StaticRouteEntry 2 }

        r8StaticRouteNetAddr  OBJECT-TYPE
            SYNTAX  DisplayString (SIZE (0..20))
            ACCESS  read-only
            STATUS  mandatory
            DESCRIPTION
                "Static route net Address"
            ::= { r8StaticRouteEntry 3 }

        r8StaticRouteNetMask  OBJECT-TYPE
            SYNTAX  DisplayString (SIZE (0..20))
            ACCESS  read-only
            STATUS  mandatory
            DESCRIPTION
                "Static route net mask"
            ::= { r8StaticRouteEntry 4 }

        r8StaticRouteGatewayAddr  OBJECT-TYPE
            SYNTAX  DisplayString (SIZE (0..20))
            ACCESS  read-only
            STATUS  mandatory
            DESCRIPTION
                "Static route gateway Address"
            ::= { r8StaticRouteEntry 5 }

        r8StaticRouteInterface  OBJECT-TYPE
            SYNTAX  DisplayString (SIZE (0..30))
            ACCESS  read-only
            STATUS  mandatory
            DESCRIPTION
                "Static route output interface"
            ::= { r8StaticRouteEntry 6 }

--
-- OCT-RT-B Add Static Route
--

        r8AddStaticRoute  OBJECT-TYPE
            SYNTAX  SEQUENCE OF R8AddStaticRouteEntry
            ACCESS  not-accessible
            STATUS  mandatory
            DESCRIPTION
                "Add static route Table"
            ::= { r8Route 2 }

        r8AddStaticRouteEntry  OBJECT-TYPE
            SYNTAX  R8AddStaticRouteEntry
            ACCESS  not-accessible
            STATUS  mandatory
            DESCRIPTION
                "Add static route Entry"
            INDEX { r8ASRSlotIndex }
            ::= { r8AddStaticRoute 1 }

        R8AddStaticRouteEntry ::= SEQUENCE {
            r8ASRSlotIndex              LSSlotID,
            r8AddRouteNetAddr           DisplayString,
            r8AddRouteGatewayAddr       DisplayString,
            r8AddRouteInterface         DisplayString,
            r8AddSataicRouteCMD         INTEGER
        }

        r8ASRSlotIndex  OBJECT-TYPE
            SYNTAX  LSSlotID
            ACCESS  read-only
            STATUS  mandatory
            DESCRIPTION
                "R8 slot"
            ::= { r8AddStaticRouteEntry 1 }

        r8AddRouteNetAddr  OBJECT-TYPE
            SYNTAX  DisplayString (SIZE (0..20))
            ACCESS  read-write
            STATUS  mandatory
            DESCRIPTION
                "Static route net Address(xxx.xxx.xxx.xxx/xx)"
            ::= { r8AddStaticRouteEntry 2 }

        r8AddRouteGatewayAddr  OBJECT-TYPE
            SYNTAX  DisplayString (SIZE (0..20))
            ACCESS  read-write
            STATUS  mandatory
            DESCRIPTION
                "Static route gateway Address(xxx.xxx.xxx.xxx)"
            ::= { r8AddStaticRouteEntry 3 }

        r8AddRouteInterface  OBJECT-TYPE
            SYNTAX  DisplayString (SIZE (0..20))
            ACCESS  read-write
            STATUS  mandatory
            DESCRIPTION
                "Static route output interface(lan1~2/wan1~wan64/wanX pvc1-16/brg_group)"
            ::= { r8AddStaticRouteEntry 4 }

        r8AddSataicRouteCMD  OBJECT-TYPE
            SYNTAX  INTEGER{
                    add(1)
                }
            ACCESS  read-write
            STATUS  mandatory
            DESCRIPTION
                " add static route "
            ::= { r8AddStaticRouteEntry 5 }

--
-- OCT-RT-B Delete Static Route
--

        r8DelStaticRoute  OBJECT-TYPE
            SYNTAX  SEQUENCE OF R8DelStaticRouteEntry
            ACCESS  not-accessible
            STATUS  mandatory
            DESCRIPTION
                "Delete static route Table"
            ::= { r8Route 3 }

        r8DelStaticRouteEntry  OBJECT-TYPE
            SYNTAX  R8DelStaticRouteEntry
            ACCESS  not-accessible
            STATUS  mandatory
            DESCRIPTION
                "Delete static route Entry"
            INDEX { r8DSRSlotIndex }
            ::= { r8DelStaticRoute 1 }

        R8DelStaticRouteEntry ::= SEQUENCE {
            r8DSRSlotIndex              LSSlotID,
            r8DelRouteNetAddr           DisplayString,
            r8DelSataicRouteCMD         INTEGER
        }

        r8DSRSlotIndex  OBJECT-TYPE
            SYNTAX  LSSlotID
            ACCESS  read-only
            STATUS  mandatory
            DESCRIPTION
                "R8 slot"
            ::= { r8DelStaticRouteEntry 1 }

        r8DelRouteNetAddr  OBJECT-TYPE
            SYNTAX  DisplayString (SIZE (0..20))
            ACCESS  read-write
            STATUS  mandatory
            DESCRIPTION
                "Static route net Address(xxx.xxx.xxx.xxx/xx)"
            ::= { r8DelStaticRouteEntry 2 }

        r8DelSataicRouteCMD  OBJECT-TYPE
            SYNTAX  INTEGER{
                    delete(1)
                }
            ACCESS  read-write
            STATUS  mandatory
            DESCRIPTION
                "Delete static route"
            ::= { r8DelStaticRouteEntry 3 }


--
-- OCT-RT-B OSPF
--

    r8OSPF                      OBJECT IDENTIFIER ::= { r8Route 4 }

--
-- OCT-RT-B OSPF General Table
--

        r8OspfGereralTable  OBJECT-TYPE
            SYNTAX  SEQUENCE OF R8OspfGereralEntry
            ACCESS  not-accessible
            STATUS  mandatory
            DESCRIPTION
                "Route OSPF General Config Table"
            ::= { r8OSPF 1 }

        r8OspfGereralEntry  OBJECT-TYPE
            SYNTAX  R8OspfGereralEntry
            ACCESS  not-accessible
            STATUS  mandatory
            DESCRIPTION
                "Route OSPF General Config Entry"
            INDEX { r8OGSlotIndex }
            ::= { r8OspfGereralTable 1 }

        R8OspfGereralEntry ::= SEQUENCE {
            r8OGSlotIndex               LSSlotID,
            r8OspfRedistribute          DisplayString (SIZE (1..50)),
            r8OspfRouterID              DisplayString (SIZE (1..20))
        }

        r8OGSlotIndex  OBJECT-TYPE
            SYNTAX  LSSlotID
            ACCESS  read-only
            STATUS  mandatory
            DESCRIPTION
                "R8 slot"
            ::= { r8OspfGereralEntry 1 }

        r8OspfRedistribute  OBJECT-TYPE
            SYNTAX  DisplayString (SIZE (1..50))
            ACCESS  read-write
            STATUS  mandatory
            DESCRIPTION
                "Redistributes (kernel | static | connected | rip | none)"
            ::= { r8OspfGereralEntry 2 }

        r8OspfRouterID  OBJECT-TYPE
            SYNTAX  DisplayString (SIZE (1..20))
            ACCESS  read-write
            STATUS  mandatory
            DESCRIPTION
                "IP address(xxx.xxx.xxx.xxx) that identifies this OSPF router"
            ::= { r8OspfGereralEntry 3 }

--
-- OCT-RT-B OSPF Area
--

    r8OspfArea                      OBJECT IDENTIFIER ::= { r8OSPF 2 }

--
-- R8 OSPF Area Config
--

        r8OspfAreaCFG  OBJECT-TYPE
            SYNTAX  SEQUENCE OF R8OspfAreaCFGEntry
            ACCESS  not-accessible
            STATUS  mandatory
            DESCRIPTION
                "OSPF Area Config"
            ::= { r8OspfArea 1 }

        r8OspfAreaCFGEntry  OBJECT-TYPE
            SYNTAX  R8OspfAreaCFGEntry
            ACCESS  not-accessible
            STATUS  mandatory
            DESCRIPTION
                "OSPF Area Config Entry"
            INDEX { r8OACSlotIndex ,
                    r8OspfAreaCfgIndex }
            ::= { r8OspfAreaCFG 1 }

        R8OspfAreaCFGEntry ::= SEQUENCE {
            r8OACSlotIndex              LSSlotID,
            r8OspfAreaCfgIndex          INTEGER,
            r8OspfAreaCfgAreaID         INTEGER,
            r8OspfAreaCfgAuthType       INTEGER,
            r8OspfAreaCfgAreaType       INTEGER,
            r8OspfAreaCfgCost           INTEGER (0..16777215)
        }

        r8OACSlotIndex  OBJECT-TYPE
            SYNTAX  LSSlotID
            ACCESS  read-only
            STATUS  mandatory
            DESCRIPTION
                "R8 slot"
            ::= { r8OspfAreaCFGEntry 1 }

        r8OspfAreaCfgIndex  OBJECT-TYPE
            SYNTAX  INTEGER
            ACCESS  read-only
            STATUS  mandatory
            DESCRIPTION
                "OSPF Area Config Index"
            ::= { r8OspfAreaCFGEntry 2 }

        r8OspfAreaCfgAreaID  OBJECT-TYPE
            SYNTAX  INTEGER
            ACCESS  read-only
            STATUS  mandatory
            DESCRIPTION
                "OSPF Area Config Area ID"
            ::= { r8OspfAreaCFGEntry 3 }

        r8OspfAreaCfgAuthType  OBJECT-TYPE
            SYNTAX  INTEGER {
                    none(1),
                    password(2),
                    md5(3)
                }
            ACCESS  read-write
            STATUS  mandatory
            DESCRIPTION
                "Authentication for an OSPF area"
            ::= { r8OspfAreaCFGEntry 4 }

        r8OspfAreaCfgAreaType  OBJECT-TYPE
            SYNTAX  INTEGER {
                    normal(1),
                    stub(2),
                    stub-no-summary(3)
                }
            ACCESS  read-write
            STATUS  mandatory
            DESCRIPTION
                "Designates an area as a stub area"
            ::= { r8OspfAreaCFGEntry 5 }

        r8OspfAreaCfgCost  OBJECT-TYPE
            SYNTAX  INTEGER (0..16777215)
            ACCESS  read-write
            STATUS  mandatory
            DESCRIPTION
                "Assign a specific cost to the default summary route used"
            ::= { r8OspfAreaCFGEntry 6 }

--
-- OCT-RT-B OSPF Add & Delete Area
--

        r8OspfAddDelArea  OBJECT-TYPE
            SYNTAX  SEQUENCE OF R8OspfAddDelAreaEntry
            ACCESS  not-accessible
            STATUS  mandatory
            DESCRIPTION
                "Add and Delete OSPF Area"
            ::= { r8OspfArea 2 }

        r8OspfAddDelAreaEntry  OBJECT-TYPE
            SYNTAX  R8OspfAddDelAreaEntry
            ACCESS  not-accessible
            STATUS  mandatory
            DESCRIPTION
                "Add and Delete OSPF Area Entry"
            INDEX { r8OADASlotIndex }
            ::= { r8OspfAddDelArea 1 }

        R8OspfAddDelAreaEntry ::= SEQUENCE {
            r8OADASlotIndex             LSSlotID,
            r8OspfAddDelAreaID          INTEGER,
            r8OspfAddDelAreaCommand     INTEGER
        }

        r8OADASlotIndex  OBJECT-TYPE
            SYNTAX  LSSlotID
            ACCESS  read-only
            STATUS  mandatory
            DESCRIPTION
                "R8 slot"
            ::= { r8OspfAddDelAreaEntry 1 }

        r8OspfAddDelAreaID  OBJECT-TYPE
            SYNTAX  INTEGER
            ACCESS  read-write
            STATUS  mandatory
            DESCRIPTION
                "Add and Delete OSPF Area ID"
            ::= { r8OspfAddDelAreaEntry 2 }

        r8OspfAddDelAreaCommand  OBJECT-TYPE
            SYNTAX  INTEGER {
                    add(1),
                    delete(2)
                }
            ACCESS  read-write
            STATUS  mandatory
            DESCRIPTION
                "Add and Delete OSPF Area ID Command"
            ::= { r8OspfAddDelAreaEntry 3 }


--
-- OCT-RT-B OSPF Interface Table
--

    r8OspfInterface                      OBJECT IDENTIFIER ::= { r8OSPF 3 }

--
-- OCT-RT-B OSPF Interface Config Table
--

        r8OspfIntfCFG  OBJECT-TYPE
            SYNTAX  SEQUENCE OF R8OspfIntfCFGEntry
            ACCESS  not-accessible
            STATUS  mandatory
            DESCRIPTION
                "OSPF Interface Config"
            ::= { r8OspfInterface 1 }

        r8OspfIntfCFGEntry  OBJECT-TYPE
            SYNTAX  R8OspfIntfCFGEntry
            ACCESS  not-accessible
            STATUS  mandatory
            DESCRIPTION
                "OSPF Interface Config Entry"
            INDEX { r8OICSlotIndex ,
                    r8OspfIntfIndex }
            ::= { r8OspfIntfCFG 1 }

        R8OspfIntfCFGEntry ::= SEQUENCE {
            r8OICSlotIndex              LSSlotID,
            r8OspfIntfIndex             INTEGER,
            r8OspfIntfName              DisplayString (SIZE (0..20)),
            r8OspfIntfAdminStatus       INTEGER,
            r8OspfIntfAreaID            INTEGER,
            r8OspfIntfNetworkType       INTEGER,
            r8OspfIntfLinkCost          INTEGER (1..65535),
            r8OspfIntfTransmitDelay     INTEGER (1..65535),
            r8OspfIntfRouterPriority    INTEGER (0..255),
            r8OspfIntfHelloInterval     INTEGER (1..65535),
            r8OspfIntfRouterDeadInterval    INTEGER (1..65535),
            r8OspfIntfRetransmitInterval    INTEGER (1..65535),
            r8OspfIntfAuthMD5KeyID-Key      DisplayString (SIZE (1..20)),
            r8OspfIntfAuthPasswordTextKey   DisplayString (SIZE (1..8))
        }

        r8OICSlotIndex  OBJECT-TYPE
            SYNTAX  LSSlotID
            ACCESS  read-only
            STATUS  mandatory
            DESCRIPTION
                "R8 slot"
            ::= { r8OspfIntfCFGEntry 1 }

        r8OspfIntfIndex  OBJECT-TYPE
            SYNTAX  INTEGER
            ACCESS  read-only
            STATUS  mandatory
            DESCRIPTION
                "Interface Index"
            ::= { r8OspfIntfCFGEntry 2 }

        r8OspfIntfName  OBJECT-TYPE
            SYNTAX  DisplayString (SIZE (0..20))
            ACCESS  read-only
            STATUS  mandatory
            DESCRIPTION
                "Interface Name(Lan1~2/Wan1~64/Wanxx Pvc1~16)"
            ::= { r8OspfIntfCFGEntry 3 }

        r8OspfIntfAdminStatus  OBJECT-TYPE
            SYNTAX  INTEGER {
                    dsiable(1),
                    enable(2)
                }
            ACCESS  read-only
            STATUS  mandatory
            DESCRIPTION
                "The OSPF interface's administrative status"
            ::= { r8OspfIntfCFGEntry 4 }

        r8OspfIntfAreaID  OBJECT-TYPE
            SYNTAX  INTEGER
            ACCESS  read-only
            STATUS  mandatory
            DESCRIPTION
                "A 32-bit integer uniquely identifying the area to which the interface connects."
            ::= { r8OspfIntfCFGEntry 5 }

        r8OspfIntfNetworkType  OBJECT-TYPE
            SYNTAX  INTEGER {
                    broadcast(1),
                    point-to-point(2)
                }
            ACCESS  read-write
            STATUS  mandatory
            DESCRIPTION
                "The OSPF interface type."
            ::= { r8OspfIntfCFGEntry 6 }

        r8OspfIntfLinkCost  OBJECT-TYPE
            SYNTAX  INTEGER (1..65535)
            ACCESS  read-write
            STATUS  mandatory
            DESCRIPTION
                "Explicitly specify the link cost of sending a packet"
            ::= { r8OspfIntfCFGEntry 7 }

        r8OspfIntfTransmitDelay  OBJECT-TYPE
            SYNTAX  INTEGER (1..65535)
            ACCESS  read-write
            STATUS  mandatory
            DESCRIPTION
                "Number of seconds for InfTransDelay value."
            ::= { r8OspfIntfCFGEntry 8 }

        r8OspfIntfRouterPriority  OBJECT-TYPE
            SYNTAX  INTEGER (0..255)
            ACCESS  read-write
            STATUS  mandatory
            DESCRIPTION
                "RouterPriority integer value."
            ::= { r8OspfIntfCFGEntry 9 }

        r8OspfIntfHelloInterval  OBJECT-TYPE
            SYNTAX  INTEGER (1..65535)
            ACCESS  read-write
            STATUS  mandatory
            DESCRIPTION
                "Number of seconds between hello packets sent."
            ::= { r8OspfIntfCFGEntry 10 }

        r8OspfIntfRouterDeadInterval  OBJECT-TYPE
            SYNTAX  INTEGER (1..65535)
            ACCESS  read-write
            STATUS  mandatory
            DESCRIPTION
                "Number of seconds for RouterDeadInterval timer."
            ::= { r8OspfIntfCFGEntry 11 }

        r8OspfIntfRetransmitInterval  OBJECT-TYPE
            SYNTAX  INTEGER (1..65535)
            ACCESS  read-write
            STATUS  mandatory
            DESCRIPTION
                "Number of seconds for RxmtInterval timer value."
            ::= { r8OspfIntfCFGEntry 12 }

        r8OspfIntfAuthMD5KeyID-Key  OBJECT-TYPE
            SYNTAX  DisplayString (SIZE (1..20))
            ACCESS  read-write
            STATUS  mandatory
            DESCRIPTION
                "Interface MD5 Authentication KeyID/Key(KeyID:1~255, Key:up to 16 chars)"
            ::= { r8OspfIntfCFGEntry 13 }

        r8OspfIntfAuthPasswordTextKey  OBJECT-TYPE
            SYNTAX  DisplayString (SIZE (1..8))
            ACCESS  read-write
            STATUS  mandatory
            DESCRIPTION
                "Interface Password Authentication Key"
            ::= { r8OspfIntfCFGEntry 14 }

--
-- OCT-RT-B OSPF Interface Admin Setup Table
--

        r8OspfIntfAdminSetup  OBJECT-TYPE
            SYNTAX  SEQUENCE OF R8OspfIntfAdminSetupEntry
            ACCESS  not-accessible
            STATUS  mandatory
            DESCRIPTION
                "OSPF Interface Admin Setup Table"
            ::= { r8OspfInterface 2 }

        r8OspfIntfAdminSetupEntry  OBJECT-TYPE
            SYNTAX  R8OspfIntfAdminSetupEntry
            ACCESS  not-accessible
            STATUS  mandatory
            DESCRIPTION
                "OSPF Interface Admin Setup Entry"
            INDEX { r8OIASSlotIndex }
            ::= { r8OspfIntfAdminSetup 1 }

        R8OspfIntfAdminSetupEntry ::= SEQUENCE {
            r8OIASSlotIndex             LSSlotID,
            r8OspfIntfAdminSetupIntfName    DisplayString (SIZE (1..20)),
            r8OspfIntfAdminSetupAreaID      INTEGER,
            r8OspfIntfAdminSetupCMD         INTEGER
        }

        r8OIASSlotIndex  OBJECT-TYPE
            SYNTAX  LSSlotID
            ACCESS  read-only
            STATUS  mandatory
            DESCRIPTION
                "R8 slot"
            ::= { r8OspfIntfAdminSetupEntry 1 }

        r8OspfIntfAdminSetupIntfName  OBJECT-TYPE
            SYNTAX  DisplayString (SIZE (1..20))
            ACCESS  read-write
            STATUS  mandatory
            DESCRIPTION
                "Interface Name(lan1~2/wan1~64/wanXX pvcXX)"
            ::= { r8OspfIntfAdminSetupEntry 2 }

        r8OspfIntfAdminSetupAreaID  OBJECT-TYPE
            SYNTAX  INTEGER
            ACCESS  read-write
            STATUS  mandatory
            DESCRIPTION
                "Interface OSPF Area ID"
            ::= { r8OspfIntfAdminSetupEntry 3 }

        r8OspfIntfAdminSetupCMD  OBJECT-TYPE
            SYNTAX  INTEGER {
                    disable-intf-ospf(1),
                    enable-intf-ospf(2)
                }
            ACCESS  read-write
            STATUS  mandatory
            DESCRIPTION
                "Interface OSPF Admin Setup Command(Disable/Enable)"
            ::= { r8OspfIntfAdminSetupEntry 4 }



--
-- OCT-RT-B NAT
--

    r8NAT                      OBJECT IDENTIFIER ::= { oct-rt-b-card 7 }

--
-- R8 NAT Interface Mode
--

        r8NatIFMode  OBJECT-TYPE
            SYNTAX  SEQUENCE OF R8NatIFModeEntry
            ACCESS  not-accessible
            STATUS  mandatory
            DESCRIPTION
                "NAT interface mode status Table"
            ::= { r8NAT 1 }

        r8NatIFModeEntry  OBJECT-TYPE
            SYNTAX  R8NatIFModeEntry
            ACCESS  not-accessible
            STATUS  mandatory
            DESCRIPTION
                "NAT interface mode status Entry"
            INDEX { r8NIMSlotIndex ,
                    r8NatIFIndex }
            ::= { r8NatIFMode 1 }

        R8NatIFModeEntry ::= SEQUENCE {
            r8NIMSlotIndex              LSSlotID,
            r8NatIFIndex                INTEGER,
            r8NatIFName                 DisplayString,
            r8NatMode                   INTEGER
        }

        r8NIMSlotIndex  OBJECT-TYPE
            SYNTAX  LSSlotID
            ACCESS  read-only
            STATUS  mandatory
            DESCRIPTION
                "R8 slot"
            ::= { r8NatIFModeEntry 1 }

        r8NatIFIndex  OBJECT-TYPE
            SYNTAX  INTEGER
            ACCESS  read-only
            STATUS  mandatory
            DESCRIPTION
                "NAT index"
            ::= { r8NatIFModeEntry 2 }

        r8NatIFName  OBJECT-TYPE
            SYNTAX  DisplayString (SIZE (0..20))
            ACCESS  read-only
            STATUS  mandatory
            DESCRIPTION
                "Interface Name"
            ::= { r8NatIFModeEntry 3 }

        r8NatMode  OBJECT-TYPE
            SYNTAX  INTEGER{
                    disable(1),
                    nat(2),
                    napt(3)
                }
            ACCESS  read-only
            STATUS  mandatory
            DESCRIPTION
                "NAT mode of interface"
            ::= { r8NatIFModeEntry 4 }

--
-- OCT-RT-B NAT IP Pool
--

        r8NatIPPool  OBJECT-TYPE
            SYNTAX  SEQUENCE OF R8NatIPPoolEntry
            ACCESS  not-accessible
            STATUS  mandatory
            DESCRIPTION
                "NAT IP Pool Table"
            ::= { r8NAT 2 }

        r8NatIPPoolEntry  OBJECT-TYPE
            SYNTAX  R8NatIPPoolEntry
            ACCESS  not-accessible
            STATUS  mandatory
            DESCRIPTION
                "NAT IP Pool Entry"
            INDEX { r8NIPSlotIndex ,
                    r8NatIPIndex ,
                    r8NatPoolIndex }
            ::= { r8NatIPPool 1 }

        R8NatIPPoolEntry ::= SEQUENCE {
            r8NIPSlotIndex              LSSlotID,
            r8NatIPIndex                INTEGER,
            r8NatPoolIndex              INTEGER,
            r8NatPoolIFName             DisplayString,
            r8NatStartAddress           DisplayString,
            r8NatEndAddress             DisplayString
        }

        r8NIPSlotIndex  OBJECT-TYPE
            SYNTAX  LSSlotID
            ACCESS  read-only
            STATUS  mandatory
            DESCRIPTION
                "R8 slot"
            ::= { r8NatIPPoolEntry 1 }

        r8NatIPIndex  OBJECT-TYPE
            SYNTAX  INTEGER
            ACCESS  read-only
            STATUS  mandatory
            DESCRIPTION
                "NAT index"
            ::= { r8NatIPPoolEntry 2 }

        r8NatPoolIndex  OBJECT-TYPE
            SYNTAX  INTEGER (1..8)
            ACCESS  read-only
            STATUS  mandatory
            DESCRIPTION
                "IP Pool index"
            ::= { r8NatIPPoolEntry 3 }

        r8NatPoolIFName  OBJECT-TYPE
            SYNTAX  DisplayString (SIZE (0..20))
            ACCESS  read-only
            STATUS  mandatory
            DESCRIPTION
                "Interface Name(wan1-64/wanX pvc1-16)"
            ::= { r8NatIPPoolEntry 4 }

        r8NatStartAddress  OBJECT-TYPE
            SYNTAX  DisplayString (SIZE (0..20))
            ACCESS  read-only
            STATUS  mandatory
            DESCRIPTION
                "NAT start address"
            ::= { r8NatIPPoolEntry 5 }

        r8NatEndAddress  OBJECT-TYPE
            SYNTAX  DisplayString (SIZE (0..20))
            ACCESS  read-only
            STATUS  mandatory
            DESCRIPTION
                "NAT end address"
            ::= { r8NatIPPoolEntry 6 }

--
-- R8 NAT Add or Delete IP Pool
--

        r8NatAddDelIPPool  OBJECT-TYPE
            SYNTAX  SEQUENCE OF R8NatAddDelIPPoolEntry
            ACCESS  not-accessible
            STATUS  mandatory
            DESCRIPTION
                "Add or Delete NAT IP Pool Table"
            ::= { r8NAT 3 }

        r8NatAddDelIPPoolEntry  OBJECT-TYPE
            SYNTAX  R8NatAddDelIPPoolEntry
            ACCESS  not-accessible
            STATUS  mandatory
            DESCRIPTION
                "Add or Delete NAT IP Pool Entry"
            INDEX { r8NADIPSlotIndex }
            ::= { r8NatAddDelIPPool 1 }

        R8NatAddDelIPPoolEntry ::= SEQUENCE {
            r8NADIPSlotIndex            LSSlotID,
            r8NatAddDelPoolIFName       DisplayString,
            r8NatAddDelPoolIndex        INTEGER,
            r8NatAddDelStartAddr        DisplayString,
            r8NatAddDelEndAddr          DisplayString,
            r8NatAddDelIPPoolCMD        INTEGER
        }

        r8NADIPSlotIndex  OBJECT-TYPE
            SYNTAX  LSSlotID
            ACCESS  read-only
            STATUS  mandatory
            DESCRIPTION
                "R8 slot"
            ::= { r8NatAddDelIPPoolEntry 1 }

        r8NatAddDelPoolIFName  OBJECT-TYPE
            SYNTAX  DisplayString (SIZE (0..20))
            ACCESS  read-write
            STATUS  mandatory
            DESCRIPTION
                "Interface Name(wan1-64/wanx pvc1-16)"
            ::= { r8NatAddDelIPPoolEntry 2 }

        r8NatAddDelPoolIndex  OBJECT-TYPE
            SYNTAX  INTEGER (1..8)
            ACCESS  read-write
            STATUS  mandatory
            DESCRIPTION
                "Add or delete IP Pool index"
            ::= { r8NatAddDelIPPoolEntry 3 }

        r8NatAddDelStartAddr  OBJECT-TYPE
            SYNTAX  DisplayString (SIZE (0..20))
            ACCESS  read-write
            STATUS  mandatory
            DESCRIPTION
                "NAT start address(xxx.xxx.xxx.xxx)"
            ::= { r8NatAddDelIPPoolEntry 4 }

        r8NatAddDelEndAddr  OBJECT-TYPE
            SYNTAX  DisplayString (SIZE (0..20))
            ACCESS  read-write
            STATUS  mandatory
            DESCRIPTION
                "NAT end address(xxx.xxx.xxx.xxx)"
            ::= { r8NatAddDelIPPoolEntry 5 }

        r8NatAddDelIPPoolCMD  OBJECT-TYPE
            SYNTAX  INTEGER{
                    add(1),
                    delete(2)
                }
            ACCESS  read-write
            STATUS  mandatory
            DESCRIPTION
                "Add or delete IP Pool command"
            ::= { r8NatAddDelIPPoolEntry 6 }

--
-- OCT-RT-B NAT IP Static
--

        r8NatIPStatic  OBJECT-TYPE
            SYNTAX  SEQUENCE OF R8NatIPStaticEntry
            ACCESS  not-accessible
            STATUS  mandatory
            DESCRIPTION
                "NAT IP static status Table"
            ::= { r8NAT 4 }

        r8NatIPStaticEntry  OBJECT-TYPE
            SYNTAX  R8NatIPStaticEntry
            ACCESS  not-accessible
            STATUS  mandatory
            DESCRIPTION
                "NAT IP static status Entry"
            INDEX { r8NISSlotIndex ,
                    r8NatISIndex ,
                    r8NatIPStaticIndex }
            ::= { r8NatIPStatic 1 }

        R8NatIPStaticEntry ::= SEQUENCE {
            r8NISSlotIndex              LSSlotID,
            r8NatISIndex                INTEGER,
            r8NatIPStaticIndex          INTEGER,
            r8NatIPStaticIFName         DisplayString,
            r8NatIPStaticPublicAddr     DisplayString,
            r8NatIPStaticPrivateAddr    DisplayString
        }

        r8NISSlotIndex  OBJECT-TYPE
            SYNTAX  LSSlotID
            ACCESS  read-only
            STATUS  mandatory
            DESCRIPTION
                "R8 slot"
            ::= { r8NatIPStaticEntry 1 }

        r8NatISIndex  OBJECT-TYPE
            SYNTAX  INTEGER
            ACCESS  read-only
            STATUS  mandatory
            DESCRIPTION
                "NAT index"
            ::= { r8NatIPStaticEntry 2 }

        r8NatIPStaticIndex  OBJECT-TYPE
            SYNTAX  INTEGER (1..8)
            ACCESS  read-only
            STATUS  mandatory
            DESCRIPTION
                "NAT IP static index"
            ::= { r8NatIPStaticEntry 3 }

        r8NatIPStaticIFName  OBJECT-TYPE
            SYNTAX  DisplayString (SIZE (0..20))
            ACCESS  read-only
            STATUS  mandatory
            DESCRIPTION
                "Interface name(wan1-64/wanx pvc1-16)"
            ::= { r8NatIPStaticEntry 4 }

        r8NatIPStaticPublicAddr  OBJECT-TYPE
            SYNTAX  DisplayString (SIZE (0..20))
            ACCESS  read-only
            STATUS  mandatory
            DESCRIPTION
                "NAT IP static public Address"
            ::= { r8NatIPStaticEntry 5 }

        r8NatIPStaticPrivateAddr  OBJECT-TYPE
            SYNTAX  DisplayString (SIZE (0..20))
            ACCESS  read-only
            STATUS  mandatory
            DESCRIPTION
                "NAT IP static private Address"
            ::= { r8NatIPStaticEntry 6 }

--
-- OCT-RT-B NAT Add or Delete IP Static
--

        r8NatAddDelIPStatic  OBJECT-TYPE
            SYNTAX  SEQUENCE OF R8NatAddDelIPStaticEntry
            ACCESS  not-accessible
            STATUS  mandatory
            DESCRIPTION
                "NAT add or delete IP static Table"
            ::= { r8NAT 5 }

        r8NatAddDelIPStaticEntry  OBJECT-TYPE
            SYNTAX  R8NatAddDelIPStaticEntry
            ACCESS  not-accessible
            STATUS  mandatory
            DESCRIPTION
                "NAT add or delete IP static Entry"
            INDEX { r8NADISSlotIndex }
            ::= { r8NatAddDelIPStatic 1 }

        R8NatAddDelIPStaticEntry ::= SEQUENCE {
            r8NADISSlotIndex            LSSlotID,
            r8NatAddDelIPStaticIFName   DisplayString,
            r8NatAddDelPublicAddr       DisplayString,
            r8NatAddDelPrivateAddr      DisplayString,
            r8NatAddDelIPStaticCMD      INTEGER
        }

        r8NADISSlotIndex  OBJECT-TYPE
            SYNTAX  LSSlotID
            ACCESS  read-only
            STATUS  mandatory
            DESCRIPTION
                "R8 slot"
            ::= { r8NatAddDelIPStaticEntry 1 }

        r8NatAddDelIPStaticIFName  OBJECT-TYPE
            SYNTAX  DisplayString (SIZE (0..20))
            ACCESS  read-write
            STATUS  mandatory
            DESCRIPTION
                "Interface Name(wan1-64/wanx pvc1-16)"
            ::= { r8NatAddDelIPStaticEntry 2 }

        r8NatAddDelPublicAddr  OBJECT-TYPE
            SYNTAX  DisplayString (SIZE (0..20))
            ACCESS  read-write
            STATUS  mandatory
            DESCRIPTION
                "NAT IP static public Address(xxx.xxx.xxx.xxx)"
            ::= { r8NatAddDelIPStaticEntry 3 }

        r8NatAddDelPrivateAddr  OBJECT-TYPE
            SYNTAX  DisplayString (SIZE (0..20))
            ACCESS  read-write
            STATUS  mandatory
            DESCRIPTION
                "NAT IP static private Address(xxx.xxx.xxx.xxx)"
            ::= { r8NatAddDelIPStaticEntry 4 }

        r8NatAddDelIPStaticCMD  OBJECT-TYPE
            SYNTAX  INTEGER{
                    add(1),
                    delete(2)
                }
            ACCESS  read-write
            STATUS  mandatory
            DESCRIPTION
                "NAT add or delete IP static command"
            ::= { r8NatAddDelIPStaticEntry 5 }

--
-- OCT-RT-B NAPT Port Forwarding
--

        r8NaptPortForwarding  OBJECT-TYPE
            SYNTAX  SEQUENCE OF R8NaptPortForwardingEntry
            ACCESS  not-accessible
            STATUS  mandatory
            DESCRIPTION
                "NAPT Port Forwarding Table"
            ::= { r8NAT 6 }

        r8NaptPortForwardingEntry  OBJECT-TYPE
            SYNTAX  R8NaptPortForwardingEntry
            ACCESS  not-accessible
            STATUS  mandatory
            DESCRIPTION
                "NAPT Port Forwarding Entry"
            INDEX { r8NPFSlotIndex ,
                    r8NaptIFIndex ,
                    r8NaptPortFwdIndex }
            ::= { r8NaptPortForwarding 1 }

        R8NaptPortForwardingEntry ::= SEQUENCE {
            r8NPFSlotIndex              LSSlotID,
            r8NaptIFIndex               INTEGER,
            r8NaptPortFwdIndex          INTEGER,
            r8NaptIFName                DisplayString,
            r8NaptPortFwdName           DisplayString,
            r8NaptPortFwdStartPort      INTEGER,
            r8NaptPortFwdEndPort        INTEGER,
            r8NaptPortFwdServerIP       DisplayString
        }

        r8NPFSlotIndex  OBJECT-TYPE
            SYNTAX  LSSlotID
            ACCESS  read-only
            STATUS  mandatory
            DESCRIPTION
                "R8 slot"
            ::= { r8NaptPortForwardingEntry 1 }

        r8NaptIFIndex  OBJECT-TYPE
            SYNTAX  INTEGER
            ACCESS  read-only
            STATUS  mandatory
            DESCRIPTION
                "Interface index"
            ::= { r8NaptPortForwardingEntry 2 }

        r8NaptPortFwdIndex  OBJECT-TYPE
            SYNTAX  INTEGER (1..32)
            ACCESS  read-only
            STATUS  mandatory
            DESCRIPTION
                "NAPT Port Forwarding entry index"
            ::= { r8NaptPortForwardingEntry 3 }

        r8NaptIFName  OBJECT-TYPE
            SYNTAX  DisplayString (SIZE (0..20))
            ACCESS  read-only
            STATUS  mandatory
            DESCRIPTION
                "Interface Name"
            ::= { r8NaptPortForwardingEntry 4 }

        r8NaptPortFwdName  OBJECT-TYPE
            SYNTAX  DisplayString (SIZE (0..8))
            ACCESS  read-only
            STATUS  mandatory
            DESCRIPTION
                "The NAPT entry name"
            ::= { r8NaptPortForwardingEntry 5 }

        r8NaptPortFwdStartPort  OBJECT-TYPE
            SYNTAX  INTEGER (1..1024)
            ACCESS  read-only
            STATUS  mandatory
            DESCRIPTION
                "Start Port number"
            ::= { r8NaptPortForwardingEntry 6 }

        r8NaptPortFwdEndPort  OBJECT-TYPE
            SYNTAX  INTEGER (1..1024)
            ACCESS  read-only
            STATUS  mandatory
            DESCRIPTION
                "End Port number"
            ::= { r8NaptPortForwardingEntry 7 }

        r8NaptPortFwdServerIP  OBJECT-TYPE
            SYNTAX  DisplayString (SIZE (0..20))
            ACCESS  read-only
            STATUS  mandatory
            DESCRIPTION
                "The IP address of the service(xxx.xxx.xxx.xxx)"
            ::= { r8NaptPortForwardingEntry 8 }

--
-- OCT-RT-B NAPT Add or Delete Port Forwarding
--

        r8NaptAddDelPortForward  OBJECT-TYPE
            SYNTAX  SEQUENCE OF R8NaptADPForwardEntry
            ACCESS  not-accessible
            STATUS  mandatory
            DESCRIPTION
                "NAPT Add or Delete Port Forwarding Table"
            ::= { r8NAT 7 }

        r8NaptADPForwardEntry  OBJECT-TYPE
            SYNTAX  R8NaptADPForwardEntry
            ACCESS  not-accessible
            STATUS  mandatory
            DESCRIPTION
                "NAPT Add or Delete Port Forwarding Entry"
            INDEX { r8NAFSlotIndex }
            ::= { r8NaptAddDelPortForward 1 }

        R8NaptADPForwardEntry ::= SEQUENCE {
            r8NAFSlotIndex              LSSlotID,
            r8NaptAddDelIFName          DisplayString,
            r8NaptAddDelName            DisplayString,
            r8NaptAddDelStartPort       INTEGER,
            r8NaptAddDelEndPort         INTEGER,
            r8NaptAddDelServerIP        DisplayString,
            r8NaptAddDelPortFwdCMD      INTEGER
        }

        r8NAFSlotIndex  OBJECT-TYPE
            SYNTAX  LSSlotID
            ACCESS  read-only
            STATUS  mandatory
            DESCRIPTION
                "R8 slot"
            ::= { r8NaptADPForwardEntry 1 }

        r8NaptAddDelIFName  OBJECT-TYPE
            SYNTAX  DisplayString (SIZE (0..20))
            ACCESS  read-write
            STATUS  mandatory
            DESCRIPTION
                "Interface Name"
            ::= { r8NaptADPForwardEntry 2 }

        r8NaptAddDelName  OBJECT-TYPE
            SYNTAX  DisplayString (SIZE (0..8))
            ACCESS  read-write
            STATUS  mandatory
            DESCRIPTION
                "The NAPT entry name"
            ::= { r8NaptADPForwardEntry 3 }

        r8NaptAddDelStartPort  OBJECT-TYPE
            SYNTAX  INTEGER (1..1024)
            ACCESS  read-write
            STATUS  mandatory
            DESCRIPTION
                "Start Port number"
            ::= { r8NaptADPForwardEntry 4 }

        r8NaptAddDelEndPort  OBJECT-TYPE
            SYNTAX  INTEGER (1..1024)
            ACCESS  read-write
            STATUS  mandatory
            DESCRIPTION
                "End Port number"
            ::= { r8NaptADPForwardEntry 5 }

        r8NaptAddDelServerIP  OBJECT-TYPE
            SYNTAX  DisplayString (SIZE (0..20))
            ACCESS  read-write
            STATUS  mandatory
            DESCRIPTION
                "The IP address of the service(xxx.xxx.xxx.xxx)"
            ::= { r8NaptADPForwardEntry 6 }

        r8NaptAddDelPortFwdCMD  OBJECT-TYPE
            SYNTAX  INTEGER{
                    add(1),
                    delete(2)
                }
            ACCESS  read-write
            STATUS  mandatory
            DESCRIPTION
                "NAPT add or delete port forwarding command"
            ::= { r8NaptADPForwardEntry 7 }


--
-- OCT-RT-B VLAN
--

    r8VLAN                      OBJECT IDENTIFIER ::= { oct-rt-b-card 8 }

--
-- R8 VLAN State
--

        r8VlanState  OBJECT-TYPE
            SYNTAX  SEQUENCE OF R8VlanStateEntry
            ACCESS  not-accessible
            STATUS  mandatory
            DESCRIPTION
                "Vlan state Table"
            ::= { r8VLAN 1 }

        r8VlanStateEntry  OBJECT-TYPE
            SYNTAX  R8VlanStateEntry
            ACCESS  not-accessible
            STATUS  mandatory
            DESCRIPTION
                "Vlan state Entry"
            INDEX { r8VSSlotIndex ,
                    r8BrgVSID }
            ::= { r8VlanState 1 }

        R8VlanStateEntry ::= SEQUENCE {
            r8VSSlotIndex               LSSlotID,
            r8BrgVSID                   INTEGER,
            r8VlanBrgName               DisplayString,
            r8VlanEnable                INTEGER,
            r8VlanMgmtVID               INTEGER,
            r8VlanRegenCRC              INTEGER
        }

        r8VSSlotIndex  OBJECT-TYPE
            SYNTAX  LSSlotID
            ACCESS  read-only
            STATUS  mandatory
            DESCRIPTION
                "R8 slot"
            ::= { r8VlanStateEntry 1 }

        r8BrgVSID  OBJECT-TYPE
            SYNTAX  INTEGER
            ACCESS  read-only
            STATUS  mandatory
            DESCRIPTION
                "Bridge Group ID"
            ::= { r8VlanStateEntry 2 }

        r8VlanBrgName  OBJECT-TYPE
            SYNTAX  DisplayString (SIZE (0..8))
            ACCESS  read-only
            STATUS  mandatory
            DESCRIPTION
                "Bridge group name"
            ::= { r8VlanStateEntry 3 }

        r8VlanEnable  OBJECT-TYPE
            SYNTAX  INTEGER{
                    disable(1),
                    enable(2)
                }
            ACCESS  read-write
            STATUS  mandatory
            DESCRIPTION
                "Vlan state enable/disable"
            ::= { r8VlanStateEntry 4 }

        r8VlanMgmtVID  OBJECT-TYPE
            SYNTAX  INTEGER (1..4094)
            ACCESS  read-write
            STATUS  mandatory
            DESCRIPTION
                "VLAN ID for the bridge management interface"
            ::= { r8VlanStateEntry 5 }

        r8VlanRegenCRC  OBJECT-TYPE
            SYNTAX  INTEGER{
                    disable(1),
                    enable(2)
                }
            ACCESS  read-write
            STATUS  mandatory
            DESCRIPTION
                "Enable/disable CRC regenerating on WAN interfaces for VLAN frames"
            ::= { r8VlanStateEntry 6 }

--
-- OCT-RT-B VLAN Table
--


        r8VlanTable  OBJECT-TYPE
            SYNTAX  SEQUENCE OF R8VlanTableEntry
            ACCESS  not-accessible
            STATUS  mandatory
            DESCRIPTION
                "Vlan Table"
            ::= { r8VLAN 2 }

        r8VlanTableEntry  OBJECT-TYPE
            SYNTAX  R8VlanTableEntry
            ACCESS  not-accessible
            STATUS  mandatory
            DESCRIPTION
                "Vlan Table Tag Member Entry"
            INDEX { r8VTSlotIndex ,
                    r8BrgVTID ,
                    r8VlanID ,
                    r8VlanTableIndex }
            ::= { r8VlanTable 1 }

        R8VlanTableEntry ::= SEQUENCE {
            r8VTSlotIndex               LSSlotID,
            r8BrgVTID                   INTEGER,
            r8VlanID                    INTEGER,
            r8VlanTableIndex            INTEGER,
            r8VlanTagMember             DisplayString,
            r8VlanUnTagMember           DisplayString
        }

        r8VTSlotIndex  OBJECT-TYPE
            SYNTAX  LSSlotID
            ACCESS  read-only
            STATUS  mandatory
            DESCRIPTION
                "R8 slot"
            ::= { r8VlanTableEntry 1 }

        r8BrgVTID  OBJECT-TYPE
            SYNTAX  INTEGER
            ACCESS  read-only
            STATUS  mandatory
            DESCRIPTION
                "Bridge Group ID"
            ::= { r8VlanTableEntry 2 }

        r8VlanID  OBJECT-TYPE
            SYNTAX  INTEGER (1..4094)
            ACCESS  read-only
            STATUS  mandatory
            DESCRIPTION
                "Vlan Index"
            ::= { r8VlanTableEntry 3 }

        r8VlanTableIndex  OBJECT-TYPE
            SYNTAX  INTEGER
            ACCESS  read-only
            STATUS  mandatory
            DESCRIPTION
                "Vlan Tag Index"
            ::= { r8VlanTableEntry 4 }

        r8VlanTagMember  OBJECT-TYPE
            SYNTAX  DisplayString (SIZE (0..200))
            ACCESS  read-only
            STATUS  mandatory
            DESCRIPTION
                "Vlan member mask"
            ::= { r8VlanTableEntry 5 }

        r8VlanUnTagMember  OBJECT-TYPE
            SYNTAX  DisplayString (SIZE (0..200))
            ACCESS  read-only
            STATUS  mandatory
            DESCRIPTION
                "Vlan member mask"
            ::= { r8VlanTableEntry 6 }

--
-- OCT-RT-B VLAN Table Control
--

    r8VlanTableControl                 OBJECT IDENTIFIER ::= { r8VLAN 3 }

--
-- R8 VLAN Create and Destroy VLAN
--

        r8VlanCreateDestroyVlan  OBJECT-TYPE
            SYNTAX  SEQUENCE OF R8VlanCreateDestroyVlanEntry
            ACCESS  not-accessible
            STATUS  mandatory
            DESCRIPTION
                "Create and destroy vlan Table"
            ::= { r8VlanTableControl 1 }

        r8VlanCreateDestroyVlanEntry  OBJECT-TYPE
            SYNTAX  R8VlanCreateDestroyVlanEntry
            ACCESS  not-accessible
            STATUS  mandatory
            DESCRIPTION
                "Create and destroy vlan Entry"
            INDEX { r8VCDVSlotIndex }
            ::= { r8VlanCreateDestroyVlan 1 }

        R8VlanCreateDestroyVlanEntry ::= SEQUENCE {
            r8VCDVSlotIndex             LSSlotID,
            r8VlanCreateDestroyBrgName  DisplayString,
            r8VlanCreateDestroyVidNum   INTEGER,
            r8ValnCreateDestroyCMD      INTEGER
        }

        r8VCDVSlotIndex  OBJECT-TYPE
            SYNTAX  LSSlotID
            ACCESS  read-only
            STATUS  mandatory
            DESCRIPTION
                "R8 slot"
            ::= { r8VlanCreateDestroyVlanEntry 1 }

        r8VlanCreateDestroyBrgName  OBJECT-TYPE
            SYNTAX  DisplayString (SIZE (0..8))
            ACCESS  read-write
            STATUS  mandatory
            DESCRIPTION
                "Bridge group name"
            ::= { r8VlanCreateDestroyVlanEntry 2 }

        r8VlanCreateDestroyVidNum  OBJECT-TYPE
            SYNTAX  INTEGER (1..4094)
            ACCESS  read-write
            STATUS  mandatory
            DESCRIPTION
                "Vlan VID"
            ::= { r8VlanCreateDestroyVlanEntry 3 }

        r8ValnCreateDestroyCMD  OBJECT-TYPE
            SYNTAX  INTEGER{
                    create-vlan(1),
                    destroy-vlan(2)
                }
            ACCESS  read-write
            STATUS  mandatory
            DESCRIPTION
                "Create and destroy vlan command"
            ::= { r8VlanCreateDestroyVlanEntry 4 }

--
-- R8 VLAN Add and Delete Port
--

        r8VlanAddDelPort  OBJECT-TYPE
            SYNTAX  SEQUENCE OF R8VlanAddDelPortEntry
            ACCESS  not-accessible
            STATUS  mandatory
            DESCRIPTION
                "Vlan add and del port Table"
            ::= { r8VlanTableControl 2 }

        r8VlanAddDelPortEntry  OBJECT-TYPE
            SYNTAX  R8VlanAddDelPortEntry
            ACCESS  not-accessible
            STATUS  mandatory
            DESCRIPTION
                "Vlan add and del port Entry"
            INDEX { r8VADPSlotIndex }
            ::= { r8VlanAddDelPort 1 }

        R8VlanAddDelPortEntry ::= SEQUENCE {
            r8VADPSlotIndex             LSSlotID,
            r8VlanAddDelPortBrgName     DisplayString,
            r8VlanAddDelPortVidNum      INTEGER,
            r8VlanAddDelPortTag         INTEGER,
            r8VlanAddDelPortInterface   DisplayString,
            r8VlanAddDelPortCMD         INTEGER
        }

        r8VADPSlotIndex  OBJECT-TYPE
            SYNTAX  LSSlotID
            ACCESS  read-only
            STATUS  mandatory
            DESCRIPTION
                "R8 slot"
            ::= { r8VlanAddDelPortEntry 1 }

        r8VlanAddDelPortBrgName  OBJECT-TYPE
            SYNTAX  DisplayString (SIZE (0..8))
            ACCESS  read-write
            STATUS  mandatory
            DESCRIPTION
                "Bridge group name"
            ::= { r8VlanAddDelPortEntry 2 }

        r8VlanAddDelPortVidNum  OBJECT-TYPE
            SYNTAX  INTEGER (1..4094)
            ACCESS  read-write
            STATUS  mandatory
            DESCRIPTION
                "Vlan VID"
            ::= { r8VlanAddDelPortEntry 3 }

        r8VlanAddDelPortTag  OBJECT-TYPE
            SYNTAX  INTEGER{
                    untag(1),
                    tag(2)
                }
            ACCESS  read-write
            STATUS  mandatory
            DESCRIPTION
                "Vlan member mask"
            ::= { r8VlanAddDelPortEntry 4 }

        r8VlanAddDelPortInterface  OBJECT-TYPE
            SYNTAX  DisplayString (SIZE (0..20))
            ACCESS  read-write
            STATUS  mandatory
            DESCRIPTION
                "Interface Name (lan1~2/wan1~wan64/wanX pvc1-16)"
            ::= { r8VlanAddDelPortEntry 5 }

        r8VlanAddDelPortCMD  OBJECT-TYPE
            SYNTAX  INTEGER{
                    add-port-to-vlan(1),
                    delete-port-from-vlan(2)
                }
            ACCESS  read-write
            STATUS  mandatory
            DESCRIPTION
                "Vlan add and delete port command"
            ::= { r8VlanAddDelPortEntry 6 }


--
-- OCT-RT-B VLAN Port Table
--

        r8VlanPortTable  OBJECT-TYPE
            SYNTAX  SEQUENCE OF R8VlanPortTableEntry
            ACCESS  not-accessible
            STATUS  mandatory
            DESCRIPTION
                "Vlan port table control Table"
            ::= { r8VLAN 4 }

        r8VlanPortTableEntry  OBJECT-TYPE
            SYNTAX  R8VlanPortTableEntry
            ACCESS  not-accessible
            STATUS  mandatory
            DESCRIPTION
                "Vlan port table control Entry"
            INDEX { r8VPTSlotIndex ,
                    r8VlanPortIndex }
            ::= { r8VlanPortTable 1 }

        R8VlanPortTableEntry ::= SEQUENCE {
            r8VPTSlotIndex              LSSlotID,
            r8VlanPortIndex             INTEGER,
            r8VlanPortIFName            DisplayString,
            r8VlanPortPVID              INTEGER,
            r8VlanPortFrameType         INTEGER,
            r8VlanPortIngressFilter     INTEGER
        }

        r8VPTSlotIndex  OBJECT-TYPE
            SYNTAX  LSSlotID
            ACCESS  read-only
            STATUS  mandatory
            DESCRIPTION
                "R8 slot"
            ::= { r8VlanPortTableEntry 1 }

        r8VlanPortIndex  OBJECT-TYPE
            SYNTAX  INTEGER
            ACCESS  read-only
            STATUS  mandatory
            DESCRIPTION
                "Vlan port index"
            ::= { r8VlanPortTableEntry 2 }

        r8VlanPortIFName  OBJECT-TYPE
            SYNTAX  DisplayString (SIZE (0..20))
            ACCESS  read-only
            STATUS  mandatory
            DESCRIPTION
                "Port type(lan1~2/wan1~wan64/wanX pvc1-16)"
            ::= { r8VlanPortTableEntry 3 }


        r8VlanPortPVID  OBJECT-TYPE
            SYNTAX  INTEGER (1..4094)
            ACCESS  read-write
            STATUS  mandatory
            DESCRIPTION
                "Interface PVID"
            ::= { r8VlanPortTableEntry 4 }

        r8VlanPortFrameType  OBJECT-TYPE
            SYNTAX  INTEGER{
                    all(1),
                    tag-only(2)
                }
            ACCESS  read-write
            STATUS  mandatory
            DESCRIPTION
                "Set the acceptable frame type"
            ::= { r8VlanPortTableEntry 5 }

        r8VlanPortIngressFilter  OBJECT-TYPE
            SYNTAX  INTEGER{
                    disable(1),
                    enable(2)
                }
            ACCESS  read-write
            STATUS  mandatory
            DESCRIPTION
                "Enable/disable ingress filtering"
            ::= { r8VlanPortTableEntry 6 }
--Jass
--
-- OCT-RT-B DHCP
--

    r8DHCP                      OBJECT IDENTIFIER ::= { oct-rt-b-card 9 }

--
-- R8 DHCP Server
--

    r8DHCPServer                OBJECT IDENTIFIER ::= { r8DHCP 1 }

--
-- R8 DHCP Server Config
--

        r8DhcpServerCFG  OBJECT-TYPE
            SYNTAX  SEQUENCE OF R8DhcpServerCFGEntry
            ACCESS  not-accessible
            STATUS  mandatory
            DESCRIPTION
                "DHCP Server Config Table"
            ::= { r8DHCPServer 1 }

        r8DhcpServerCFGEntry  OBJECT-TYPE
            SYNTAX  R8DhcpServerCFGEntry
            ACCESS  not-accessible
            STATUS  mandatory
            DESCRIPTION
                "DHCP Server Config Entry"
            INDEX { r8DSCSlotIndex }
            ::= { r8DhcpServerCFG 1 }

        R8DhcpServerCFGEntry ::= SEQUENCE {
            r8DSCSlotIndex              LSSlotID,
            r8DhcpServer                INTEGER,
            r8DhcpServerInterface       DisplayString,
            r8DhcpServerBridgeMgmt      DisplayString
        }

        r8DSCSlotIndex  OBJECT-TYPE
            SYNTAX  LSSlotID
            ACCESS  read-only
            STATUS  mandatory
            DESCRIPTION
                "R8 slot"
            ::= { r8DhcpServerCFGEntry 1 }

        r8DhcpServer  OBJECT-TYPE
            SYNTAX  INTEGER{
                    disable(1),
                    enable(2)
                }
            ACCESS  read-write
            STATUS  mandatory
            DESCRIPTION
                "DHCP function disable/enable"
            ::= { r8DhcpServerCFGEntry 2 }

        r8DhcpServerInterface  OBJECT-TYPE
            SYNTAX  DisplayString (SIZE (0..20))
            ACCESS  read-only
            STATUS  mandatory
            DESCRIPTION
                "DHCP interface config"
            ::= { r8DhcpServerCFGEntry 3 }

        r8DhcpServerBridgeMgmt  OBJECT-TYPE
            SYNTAX  DisplayString (SIZE (0..20))
            ACCESS  read-only
            STATUS  mandatory
            DESCRIPTION
                "DHCP bridge mgmt"
            ::= { r8DhcpServerCFGEntry 4 }

--
-- R8 Add or Delete DHCP Server Interface
--

        r8DhcpServerAddDelIntf  OBJECT-TYPE
            SYNTAX  SEQUENCE OF R8DhcpSvAddDelIntfEntry
            ACCESS  not-accessible
            STATUS  mandatory
            DESCRIPTION
                "Add or Delete DHCP interface Table"
            ::= { r8DHCPServer 2 }

        r8DhcpSvAddDelIntfEntry  OBJECT-TYPE
            SYNTAX  R8DhcpSvAddDelIntfEntry
            ACCESS  not-accessible
            STATUS  mandatory
            DESCRIPTION
                "Add or Delete DHCP interface Entry"
            INDEX { r8DSADISlotIndex }
            ::= { r8DhcpServerAddDelIntf 1 }

        R8DhcpSvAddDelIntfEntry ::= SEQUENCE {
            r8DSADISlotIndex            LSSlotID,
            r8DhcpServerAddDelIntfName  DisplayString,
            r8DhcpServerAddDelIntfCMD   INTEGER
        }

        r8DSADISlotIndex  OBJECT-TYPE
            SYNTAX  LSSlotID
            ACCESS  read-only
            STATUS  mandatory
            DESCRIPTION
                "R8 slot"
            ::= { r8DhcpSvAddDelIntfEntry 1 }

        r8DhcpServerAddDelIntfName  OBJECT-TYPE
            SYNTAX  DisplayString (SIZE (0..8))
            ACCESS  read-write
            STATUS  mandatory
            DESCRIPTION
                "Interface Name(lan1/lan2/bridge group name)"
            ::= { r8DhcpSvAddDelIntfEntry 2 }

        r8DhcpServerAddDelIntfCMD  OBJECT-TYPE
            SYNTAX  INTEGER{
                    add(1),
                    delete(2)
                }
            ACCESS  read-write
            STATUS  mandatory
            DESCRIPTION
                "Add or delete interface command"
            ::= { r8DhcpSvAddDelIntfEntry 3 }

--
-- R8 DHCP Server Host Table
--

    r8DHCPHost                OBJECT IDENTIFIER ::= { r8DHCPServer 3 }

--
-- R8 DHCP Server Host Config Table
--

        r8DhcpHostCFG  OBJECT-TYPE
            SYNTAX  SEQUENCE OF R8DhcpHostCFGEntry
            ACCESS  not-accessible
            STATUS  mandatory
            DESCRIPTION
                "DHCP host config Table"
            ::= { r8DHCPHost 1 }

        r8DhcpHostCFGEntry OBJECT-TYPE
            SYNTAX  R8DhcpHostCFGEntry
            ACCESS  not-accessible
            STATUS  mandatory
            DESCRIPTION
                "DHCP host config Entry"
            INDEX { r8DHCSlotIndex ,
                    r8DhcpHostIndex }
            ::= { r8DhcpHostCFG 1 }

        R8DhcpHostCFGEntry ::= SEQUENCE {
            r8DHCSlotIndex              LSSlotID,
            r8DhcpHostIndex             INTEGER,
            r8DhcpHostName              DisplayString,
            r8DhcpHostHWType            INTEGER,
            r8DhcpHostHWAddr            DisplayString,
            r8DhcpHostFixedAddr         DisplayString,
            r8DhcpHostBootStrapFile     DisplayString,
            r8DhcpHostNextServer        DisplayString,
            r8DhcpHostClientIdentifier  DisplayString,
            r8DhcpHostDefLeaseTime      INTEGER
        }

        r8DHCSlotIndex  OBJECT-TYPE
            SYNTAX  LSSlotID
            ACCESS  read-only
            STATUS  mandatory
            DESCRIPTION
                "R8 slot"
            ::= { r8DhcpHostCFGEntry 1 }

        r8DhcpHostIndex  OBJECT-TYPE
            SYNTAX  INTEGER (1..8)
            ACCESS  read-only
            STATUS  mandatory
            DESCRIPTION
                "DHCP host configuration index"
            ::= { r8DhcpHostCFGEntry 2 }

        r8DhcpHostName  OBJECT-TYPE
            SYNTAX  DisplayString (SIZE (0..16))
            ACCESS  read-only
            STATUS  mandatory
            DESCRIPTION
                "DHCP host configuration name"
            ::= { r8DhcpHostCFGEntry 3 }

        r8DhcpHostHWType  OBJECT-TYPE
            SYNTAX  INTEGER{
                    null(0),
                    ethernet(1),
                    token-ring(2),
                    fddi(3)
                }
            ACCESS  read-write
            STATUS  mandatory
            DESCRIPTION
                "DHCP host hardware type"
            ::= { r8DhcpHostCFGEntry 4 }

        r8DhcpHostHWAddr  OBJECT-TYPE
            SYNTAX  DisplayString (SIZE (0..32))
            ACCESS  read-write
            STATUS  mandatory
            DESCRIPTION
                "DHCP host hardware address"
            ::= { r8DhcpHostCFGEntry 5 }

        r8DhcpHostFixedAddr  OBJECT-TYPE
            SYNTAX  DisplayString (SIZE (0..20))
            ACCESS  read-write
            STATUS  mandatory
            DESCRIPTION
                "DHCP host address"
            ::= { r8DhcpHostCFGEntry 6 }

        r8DhcpHostBootStrapFile  OBJECT-TYPE
            SYNTAX  DisplayString (SIZE (0..128))
            ACCESS  read-write
            STATUS  mandatory
            DESCRIPTION
                "DHCP host bootstrap file"
            ::= { r8DhcpHostCFGEntry 7 }

        r8DhcpHostNextServer  OBJECT-TYPE
            SYNTAX  DisplayString (SIZE (0..20))
            ACCESS  read-write
            STATUS  mandatory
            DESCRIPTION
                "DHCP next server in boot process"
            ::= { r8DhcpHostCFGEntry 8 }

        r8DhcpHostClientIdentifier  OBJECT-TYPE
            SYNTAX  DisplayString (SIZE (0..9))
            ACCESS  read-write
            STATUS  mandatory
            DESCRIPTION
                "DHCP host client identifier"
            ::= { r8DhcpHostCFGEntry 9 }

        r8DhcpHostDefLeaseTime  OBJECT-TYPE
            SYNTAX  INTEGER
            ACCESS  read-write
            STATUS  mandatory
            DESCRIPTION
                "DHCP host default duration of the lease"
            ::= { r8DhcpHostCFGEntry 10 }

--
-- R8 Add or Delete DHCP Server Host
--

        r8AddDelDhcpHost  OBJECT-TYPE
            SYNTAX  SEQUENCE OF R8AddDelDhcpHostEntry
            ACCESS  not-accessible
            STATUS  mandatory
            DESCRIPTION
                "DHCP host control Table"
            ::= { r8DHCPHost 2 }

        r8AddDelDhcpHostEntry  OBJECT-TYPE
            SYNTAX  R8AddDelDhcpHostEntry
            ACCESS  not-accessible
            STATUS  mandatory
            DESCRIPTION
                "DHCP host control Entry"
            INDEX { r8ADDHSlotIndex }
            ::= { r8AddDelDhcpHost 1 }

        R8AddDelDhcpHostEntry ::= SEQUENCE {
            r8ADDHSlotIndex             LSSlotID,
            r8AddDelDhcpHostName        DisplayString,
            r8DhcpHostCMD               INTEGER
        }

        r8ADDHSlotIndex  OBJECT-TYPE
            SYNTAX  LSSlotID
            ACCESS  read-only
            STATUS  mandatory
            DESCRIPTION
                "R8 slot"
            ::= { r8AddDelDhcpHostEntry 1 }

        r8AddDelDhcpHostName  OBJECT-TYPE
            SYNTAX  DisplayString (SIZE (0..16))
            ACCESS  read-write
            STATUS  mandatory
            DESCRIPTION
                "DHCP host configuration name"
            ::= { r8AddDelDhcpHostEntry 2 }

        r8DhcpHostCMD  OBJECT-TYPE
            SYNTAX  INTEGER{
                    add(1),
                    delete(2)
                }
            ACCESS  read-write
            STATUS  mandatory
            DESCRIPTION
                "Add/Delete a DHCP host configuration"
            ::= { r8AddDelDhcpHostEntry 3 }

--
-- R8 DHCP Host Option
--

        r8DhcpHostOption  OBJECT-TYPE
            SYNTAX  SEQUENCE OF R8DhcpHostOptionEntry
            ACCESS  not-accessible
            STATUS  mandatory
            DESCRIPTION
                "DHCP host option Table"
            ::= { r8DHCPHost 3 }

        r8DhcpHostOptionEntry  OBJECT-TYPE
            SYNTAX  R8DhcpHostOptionEntry
            ACCESS  not-accessible
            STATUS  mandatory
            DESCRIPTION
                "DHCP host option Entry"
            INDEX { r8DHOSlotIndex ,
                    r8DhcpHostOIndex ,
                    r8DhcpHostOptionIndex }
            ::= { r8DhcpHostOption 1 }

        R8DhcpHostOptionEntry ::= SEQUENCE {
            r8DHOSlotIndex              LSSlotID,
            r8DhcpHostOIndex            INTEGER,
            r8DhcpHostOptionIndex       INTEGER,
            r8DhcpHostOptionHostName    DisplayString,
            r8DhcpHostOptionCode        INTEGER,
            r8DhcpHostOptionValue       DisplayString
        }

        r8DHOSlotIndex  OBJECT-TYPE
            SYNTAX  LSSlotID
            ACCESS  read-only
            STATUS  mandatory
            DESCRIPTION
                "R8 slot"
            ::= { r8DhcpHostOptionEntry 1 }

        r8DhcpHostOIndex  OBJECT-TYPE
            SYNTAX  INTEGER (1..8)
            ACCESS  read-only
            STATUS  mandatory
            DESCRIPTION
                "DHCP host configuration index"
            ::= { r8DhcpHostOptionEntry 2 }

        r8DhcpHostOptionIndex  OBJECT-TYPE
            SYNTAX  INTEGER (1..8)
            ACCESS  read-only
            STATUS  mandatory
            DESCRIPTION
                "DHCP host Option index"
            ::= { r8DhcpHostOptionEntry 3 }

        r8DhcpHostOptionHostName  OBJECT-TYPE
            SYNTAX  DisplayString (SIZE (0..16))
            ACCESS  read-only
            STATUS  mandatory
            DESCRIPTION
                "DHCP host name"
            ::= { r8DhcpHostOptionEntry 4 }

        r8DhcpHostOptionCode  OBJECT-TYPE
            SYNTAX  INTEGER (1..255)
            ACCESS  read-only
            STATUS  mandatory
            DESCRIPTION
                "DHCP host option code"
            ::= { r8DhcpHostOptionEntry 5 }

        r8DhcpHostOptionValue  OBJECT-TYPE
            SYNTAX  DisplayString (SIZE (0..64))
            ACCESS  read-only
            STATUS  mandatory
            DESCRIPTION
                "DHCP host option value"
            ::= { r8DhcpHostOptionEntry 6 }

--
-- R8 Add or Delete DHCP Host Option
--

        r8AddDelDhcpHostOption  OBJECT-TYPE
            SYNTAX  SEQUENCE OF R8AddDelDhcpHostOptionEntry
            ACCESS  not-accessible
            STATUS  mandatory
            DESCRIPTION
                "DHCP host option control Table"
            ::= { r8DHCPHost 4 }

        r8AddDelDhcpHostOptionEntry  OBJECT-TYPE
            SYNTAX  R8AddDelDhcpHostOptionEntry
            ACCESS  not-accessible
            STATUS  mandatory
            DESCRIPTION
                "DHCP host option control Entry"
            INDEX { r8ADDHOSlotIndex }
            ::= { r8AddDelDhcpHostOption 1 }

        R8AddDelDhcpHostOptionEntry ::= SEQUENCE {
            r8ADDHOSlotIndex            LSSlotID,
            r8AddDelHostOptionHostName  DisplayString,
            r8AddDelHostOptionCode      INTEGER,
            r8AddDelHostOptionValue     DisplayString,
            r8AddDelHostOptionCMD       INTEGER
        }

        r8ADDHOSlotIndex  OBJECT-TYPE
            SYNTAX  LSSlotID
            ACCESS  read-only
            STATUS  mandatory
            DESCRIPTION
                "R8 slot"
            ::= { r8AddDelDhcpHostOptionEntry 1 }

        r8AddDelHostOptionHostName  OBJECT-TYPE
            SYNTAX  DisplayString (SIZE (0..16))
            ACCESS  read-write
            STATUS  mandatory
            DESCRIPTION
                "DHCP host name"
            ::= { r8AddDelDhcpHostOptionEntry 2 }

        r8AddDelHostOptionCode  OBJECT-TYPE
            SYNTAX  INTEGER (1..255)
            ACCESS  read-write
            STATUS  mandatory
            DESCRIPTION
                "DHCP host option code"
            ::= { r8AddDelDhcpHostOptionEntry 3 }

        r8AddDelHostOptionValue  OBJECT-TYPE
            SYNTAX  DisplayString (SIZE (0..64))
            ACCESS  read-write
            STATUS  mandatory
            DESCRIPTION
                "DHCP host option value"
            ::= { r8AddDelDhcpHostOptionEntry 4 }

        r8AddDelHostOptionCMD  OBJECT-TYPE
            SYNTAX  INTEGER{
                    add(1),
                    delete(2)
                }
            ACCESS  read-write
            STATUS  mandatory
            DESCRIPTION
                "Add/Delete DHCP host option command"
            ::= { r8AddDelDhcpHostOptionEntry 5 }

--
-- R8 DHCP Server Subnet Table
--

    r8DHCPSubnet                OBJECT IDENTIFIER ::= { r8DHCPServer 4 }

--
-- R8 DHCP Server Subnet Config-1 Table
--

        r8DhcpSubnetCFG1  OBJECT-TYPE
            SYNTAX  SEQUENCE OF R8DhcpSubnetCFG1Entry
            ACCESS  not-accessible
            STATUS  mandatory
            DESCRIPTION
                "DHCP subnet config Table"
            ::= { r8DHCPSubnet 1 }

        r8DhcpSubnetCFG1Entry  OBJECT-TYPE
            SYNTAX  R8DhcpSubnetCFG1Entry
            ACCESS  not-accessible
            STATUS  mandatory
            DESCRIPTION
                "DHCP subnet config Entry"
            INDEX { r8DSC1SlotIndex ,
                    r8DhcpSubnetIndex }
            ::= { r8DhcpSubnetCFG1 1 }

        R8DhcpSubnetCFG1Entry ::= SEQUENCE {
            r8DSC1SlotIndex             LSSlotID,
            r8DhcpSubnetIndex           INTEGER,
            r8DhcpCfg1SubnetName        DisplayString,
            r8DhcpSubnetNetworkAddr     DisplayString,
            r8DhcpSubnetStartAddr       DisplayString,
            r8DhcpSubnetEndAddr         DisplayString,
            r8DhcpSubnetBootp           INTEGER,
            r8DhcpSubnetDefLeaseTime    INTEGER,
            r8DhcpSubnetBootStrapFile   DisplayString,
            r8DhcpSubnetNextServer      DisplayString
        }

        r8DSC1SlotIndex  OBJECT-TYPE
            SYNTAX  LSSlotID
            ACCESS  read-only
            STATUS  mandatory
            DESCRIPTION
                "R8 slot"
            ::= { r8DhcpSubnetCFG1Entry 1 }

        r8DhcpSubnetIndex  OBJECT-TYPE
            SYNTAX  INTEGER (1..8)
            ACCESS  read-only
            STATUS  mandatory
            DESCRIPTION
                "DHCP subnet index"
            ::= { r8DhcpSubnetCFG1Entry 2 }

        r8DhcpCfg1SubnetName  OBJECT-TYPE
            SYNTAX  DisplayString (SIZE (0..16))
            ACCESS  read-only
            STATUS  mandatory
            DESCRIPTION
                "DHCP subnet name"
            ::= { r8DhcpSubnetCFG1Entry 3 }

        r8DhcpSubnetNetworkAddr  OBJECT-TYPE
            SYNTAX  DisplayString (SIZE (0..20))
            ACCESS  read-write
            STATUS  mandatory
            DESCRIPTION
                "DHCP subnet address/netmask(xxx.xxx.xxx.xxx/xx)"
            ::= { r8DhcpSubnetCFG1Entry 4 }

        r8DhcpSubnetStartAddr  OBJECT-TYPE
            SYNTAX  DisplayString (SIZE (0..20))
            ACCESS  read-write
            STATUS  mandatory
            DESCRIPTION
                "DHCP subnet ip range(start)"
            ::= { r8DhcpSubnetCFG1Entry 5 }

        r8DhcpSubnetEndAddr  OBJECT-TYPE
            SYNTAX  DisplayString (SIZE (0..20))
            ACCESS  read-write
            STATUS  mandatory
            DESCRIPTION
                "DHCP subnet ip range(end)"
            ::= { r8DhcpSubnetCFG1Entry 6 }

        r8DhcpSubnetBootp  OBJECT-TYPE
            SYNTAX  INTEGER{
                    disable(1),
                    enable(2)
                }
            ACCESS  read-write
            STATUS  mandatory
            DESCRIPTION
                "DHCP subnet bootp support"
            ::= { r8DhcpSubnetCFG1Entry 7 }

        r8DhcpSubnetDefLeaseTime  OBJECT-TYPE
            SYNTAX  INTEGER
            ACCESS  read-write
            STATUS  mandatory
            DESCRIPTION
                "DHCP subnet default duration of the lease"
            ::= { r8DhcpSubnetCFG1Entry 8 }

        r8DhcpSubnetBootStrapFile  OBJECT-TYPE
            SYNTAX  DisplayString (SIZE (0..128))
            ACCESS  read-write
            STATUS  mandatory
            DESCRIPTION
                "DHCP subnet bootstrap file"
            ::= { r8DhcpSubnetCFG1Entry 9 }

        r8DhcpSubnetNextServer  OBJECT-TYPE
            SYNTAX  DisplayString (SIZE (0..20))
            ACCESS  read-write
            STATUS  mandatory
            DESCRIPTION
                "DHCP subnet next server in boot process"
            ::= { r8DhcpSubnetCFG1Entry 10 }

--
-- R8 DHCP Server Subnet Config-2 Table
--

        r8DhcpSubnetCFG2  OBJECT-TYPE
            SYNTAX  SEQUENCE OF R8DhcpSubnetCFG2Entry
            ACCESS  not-accessible
            STATUS  mandatory
            DESCRIPTION
                "DHCP subnet config Table"
            ::= { r8DHCPSubnet 2 }

        r8DhcpSubnetCFG2Entry  OBJECT-TYPE
            SYNTAX  R8DhcpSubnetCFG2Entry
            ACCESS  not-accessible
            STATUS  mandatory
            DESCRIPTION
                "DHCP subnet config Entry"
            INDEX { r8DSC2SlotIndex ,
                    r8DhcpSubnetC2Index }
            ::= { r8DhcpSubnetCFG2 1 }

        R8DhcpSubnetCFG2Entry ::= SEQUENCE {
            r8DSC2SlotIndex             LSSlotID,
            r8DhcpSubnetC2Index         INTEGER,
            r8DhcpCfg2SubnetName        DisplayString,
            r8DhcpSubnetDomainName      DisplayString,
            r8DhcpSubnetDNSServer1      DisplayString,
            r8DhcpSubnetDNSServer2      DisplayString,
            r8DhcpSubnetDNSServer3      DisplayString,
            r8DhcpSubnetDNSServer4      DisplayString,
            r8DhcpSubnetDefRouter1      DisplayString,
            r8DhcpSubnetDefRouter2      DisplayString,
            r8DhcpSubnetDefRouter3      DisplayString,
            r8DhcpSubnetDefRouter4      DisplayString,
            r8DhcpSubnetNetbiosServer1  DisplayString,
            r8DhcpSubnetNetbiosServer2  DisplayString,
            r8DhcpSubnetNetbiosServer3  DisplayString,
            r8DhcpSubnetNetbiosServer4  DisplayString,
            r8DhcpSubnetNetbiosNode     INTEGER
        }

        r8DSC2SlotIndex  OBJECT-TYPE
            SYNTAX  LSSlotID
            ACCESS  read-only
            STATUS  mandatory
            DESCRIPTION
                "R8 slot"
            ::= { r8DhcpSubnetCFG2Entry 1 }

        r8DhcpSubnetC2Index  OBJECT-TYPE
            SYNTAX  INTEGER (1..8)
            ACCESS  read-only
            STATUS  mandatory
            DESCRIPTION
                "DHCP subnet index"
            ::= { r8DhcpSubnetCFG2Entry 2 }

        r8DhcpCfg2SubnetName  OBJECT-TYPE
            SYNTAX  DisplayString (SIZE (0..16))
            ACCESS  read-only
            STATUS  mandatory
            DESCRIPTION
                "DHCP subnet name"
            ::= { r8DhcpSubnetCFG2Entry 3 }

        r8DhcpSubnetDomainName  OBJECT-TYPE
            SYNTAX  DisplayString (SIZE (0..64))
            ACCESS  read-write
            STATUS  mandatory
            DESCRIPTION
                "DHCP subnet domain name"
            ::= { r8DhcpSubnetCFG2Entry 4 }

        r8DhcpSubnetDNSServer1  OBJECT-TYPE
            SYNTAX  DisplayString (SIZE (0..20))
            ACCESS  read-only
            STATUS  mandatory
            DESCRIPTION
                "DHCP subnet domain name server 1"
            ::= { r8DhcpSubnetCFG2Entry 5 }

        r8DhcpSubnetDNSServer2  OBJECT-TYPE
            SYNTAX  DisplayString (SIZE (0..20))
            ACCESS  read-only
            STATUS  mandatory
            DESCRIPTION
                "DHCP subnet domain name server 2"
            ::= { r8DhcpSubnetCFG2Entry 6 }

        r8DhcpSubnetDNSServer3  OBJECT-TYPE
            SYNTAX  DisplayString (SIZE (0..20))
            ACCESS  read-only
            STATUS  mandatory
            DESCRIPTION
                "DHCP subnet domain name server 3"
            ::= { r8DhcpSubnetCFG2Entry 7 }

        r8DhcpSubnetDNSServer4  OBJECT-TYPE
            SYNTAX  DisplayString (SIZE (0..20))
            ACCESS  read-only
            STATUS  mandatory
            DESCRIPTION
                "DHCP subnet domain name server 4"
            ::= { r8DhcpSubnetCFG2Entry 8 }

        r8DhcpSubnetDefRouter1  OBJECT-TYPE
            SYNTAX  DisplayString (SIZE (0..20))
            ACCESS  read-only
            STATUS  mandatory
            DESCRIPTION
                "DHCP subnet default router 1"
            ::= { r8DhcpSubnetCFG2Entry 9 }

        r8DhcpSubnetDefRouter2  OBJECT-TYPE
            SYNTAX  DisplayString (SIZE (0..20))
            ACCESS  read-only
            STATUS  mandatory
            DESCRIPTION
                "DHCP subnet default router 2"
            ::= { r8DhcpSubnetCFG2Entry 10 }

        r8DhcpSubnetDefRouter3  OBJECT-TYPE
            SYNTAX  DisplayString (SIZE (0..20))
            ACCESS  read-only
            STATUS  mandatory
            DESCRIPTION
                "DHCP subnet default router 3"
            ::= { r8DhcpSubnetCFG2Entry 11 }

        r8DhcpSubnetDefRouter4  OBJECT-TYPE
            SYNTAX  DisplayString (SIZE (0..20))
            ACCESS  read-only
            STATUS  mandatory
            DESCRIPTION
                "DHCP subnet default router 4"
            ::= { r8DhcpSubnetCFG2Entry 12 }

        r8DhcpSubnetNetbiosServer1  OBJECT-TYPE
            SYNTAX  DisplayString (SIZE (0..20))
            ACCESS  read-only
            STATUS  mandatory
            DESCRIPTION
                "DHCP subnet NBNS name server 1"
            ::= { r8DhcpSubnetCFG2Entry 13 }

        r8DhcpSubnetNetbiosServer2  OBJECT-TYPE
            SYNTAX  DisplayString (SIZE (0..20))
            ACCESS  read-only
            STATUS  mandatory
            DESCRIPTION
                "DHCP subnet NBNS name server 2"
            ::= { r8DhcpSubnetCFG2Entry 14 }

        r8DhcpSubnetNetbiosServer3  OBJECT-TYPE
            SYNTAX  DisplayString (SIZE (0..20))
            ACCESS  read-only
            STATUS  mandatory
            DESCRIPTION
                "DHCP subnet NBNS name server 3"
            ::= { r8DhcpSubnetCFG2Entry 15 }

        r8DhcpSubnetNetbiosServer4  OBJECT-TYPE
            SYNTAX  DisplayString (SIZE (0..20))
            ACCESS  read-only
            STATUS  mandatory
            DESCRIPTION
                "DHCP subnet NBNS name server 4"
            ::= { r8DhcpSubnetCFG2Entry 16 }

        r8DhcpSubnetNetbiosNode  OBJECT-TYPE
            SYNTAX  INTEGER{
                    null(0),
                    b-node(1),
                    p-node(2),
                    m-node(4),
                    h-node(8)
                }
            ACCESS  read-write
            STATUS  mandatory
            DESCRIPTION
                "DHCP subnet netbios node type"
            ::= { r8DhcpSubnetCFG2Entry 17 }

--
-- R8 Add or Delete DHCP Subnet
--

        r8AddDelDhcpSubnet  OBJECT-TYPE
            SYNTAX  SEQUENCE OF R8AddDelDhcpSubnetEntry
            ACCESS  not-accessible
            STATUS  mandatory
            DESCRIPTION
                "DHCP subnet control Table"
            ::= { r8DHCPSubnet 3 }

        r8AddDelDhcpSubnetEntry  OBJECT-TYPE
            SYNTAX  R8AddDelDhcpSubnetEntry
            ACCESS  not-accessible
            STATUS  mandatory
            DESCRIPTION
                "DHCP subnet control Entry"
            INDEX { r8ADDSSlotIndex }
            ::= { r8AddDelDhcpSubnet 1 }

        R8AddDelDhcpSubnetEntry ::= SEQUENCE {
            r8ADDSSlotIndex             LSSlotID,
            r8AddDelDhcpSubnetName      DisplayString,
            r8DhcpSubnetCMD             INTEGER
        }

        r8ADDSSlotIndex  OBJECT-TYPE
            SYNTAX  LSSlotID
            ACCESS  read-only
            STATUS  mandatory
            DESCRIPTION
                "R8 slot"
            ::= { r8AddDelDhcpSubnetEntry 1 }

        r8AddDelDhcpSubnetName  OBJECT-TYPE
            SYNTAX  DisplayString (SIZE (0..16))
            ACCESS  read-write
            STATUS  mandatory
            DESCRIPTION
                "DHCP subnet domain name"
            ::= { r8AddDelDhcpSubnetEntry 2 }

        r8DhcpSubnetCMD  OBJECT-TYPE
            SYNTAX  INTEGER{
                    add(1),
                    delete(2)
                }
            ACCESS  read-write
            STATUS  mandatory
            DESCRIPTION
                "Add/Delete a DHCP subnet configuration"
            ::= { r8AddDelDhcpSubnetEntry 3 }

--
-- R8 Add or Delete DHCP Subnet DNS Server
--

        r8AddDelSubnetDNSServer  OBJECT-TYPE
            SYNTAX  SEQUENCE OF R8AddDelSubnetDNSServerEntry
            ACCESS  not-accessible
            STATUS  mandatory
            DESCRIPTION
                "DHCP subnet DNS Server control Table"
            ::= { r8DHCPSubnet 4 }

        r8AddDelSubnetDNSServerEntry  OBJECT-TYPE
            SYNTAX  R8AddDelSubnetDNSServerEntry
            ACCESS  not-accessible
            STATUS  mandatory
            DESCRIPTION
                "DHCP subnet DNS Server control Entry"
            INDEX { r8ADSDSSlotIndex }
            ::= { r8AddDelSubnetDNSServer 1 }

        R8AddDelSubnetDNSServerEntry ::= SEQUENCE {
            r8ADSDSSlotIndex            LSSlotID,
            r8AddDelDNSServerSubnetName DisplayString,
            r8AddDelDNSServerAddr       DisplayString,
            r8AddDelDNSSeverCMD         INTEGER
        }

        r8ADSDSSlotIndex  OBJECT-TYPE
            SYNTAX  LSSlotID
            ACCESS  read-only
            STATUS  mandatory
            DESCRIPTION
                "R8 slot"
            ::= { r8AddDelSubnetDNSServerEntry 1 }

        r8AddDelDNSServerSubnetName  OBJECT-TYPE
            SYNTAX  DisplayString (SIZE (0..16))
            ACCESS  read-write
            STATUS  mandatory
            DESCRIPTION
                "DHCP subnet name"
            ::= { r8AddDelSubnetDNSServerEntry 2 }

        r8AddDelDNSServerAddr  OBJECT-TYPE
            SYNTAX  DisplayString (SIZE (0..20))
            ACCESS  read-write
            STATUS  mandatory
            DESCRIPTION
                "DHCP subnet DNS Server Address"
            ::= { r8AddDelSubnetDNSServerEntry 3 }

        r8AddDelDNSSeverCMD  OBJECT-TYPE
            SYNTAX  INTEGER{
                    add(1),
                    delete(2)
                }
            ACCESS  read-write
            STATUS  mandatory
            DESCRIPTION
                "Add/Delete a DHCP subnet DNS Server"
            ::= { r8AddDelSubnetDNSServerEntry 4 }

--
-- R8 Add or Delete DHCP Subnet Default Routers
--

        r8AddDelSubnetDefRouter  OBJECT-TYPE
            SYNTAX  SEQUENCE OF R8AddDelSubnetDefRouterEntry
            ACCESS  not-accessible
            STATUS  mandatory
            DESCRIPTION
                "DHCP subnet default router control Table"
            ::= { r8DHCPSubnet 5 }

        r8AddDelSubnetDefRouterEntry  OBJECT-TYPE
            SYNTAX  R8AddDelSubnetDefRouterEntry
            ACCESS  not-accessible
            STATUS  mandatory
            DESCRIPTION
                "DHCP subnet default router control Entry"
            INDEX { r8ADSDRSlotIndex }
            ::= { r8AddDelSubnetDefRouter 1 }

        R8AddDelSubnetDefRouterEntry ::= SEQUENCE {
            r8ADSDRSlotIndex            LSSlotID,
            r8AddDelDefRTRSubnetName    DisplayString,
            r8AddDelDefRouterAddr       DisplayString,
            r8AddDelDefRouterCMD        INTEGER
        }

        r8ADSDRSlotIndex  OBJECT-TYPE
            SYNTAX  LSSlotID
            ACCESS  read-only
            STATUS  mandatory
            DESCRIPTION
                "R8 slot"
            ::= { r8AddDelSubnetDefRouterEntry 1 }

        r8AddDelDefRTRSubnetName  OBJECT-TYPE
            SYNTAX  DisplayString (SIZE (0..16))
            ACCESS  read-write
            STATUS  mandatory
            DESCRIPTION
                "DHCP subnet name"
            ::= { r8AddDelSubnetDefRouterEntry 2 }

        r8AddDelDefRouterAddr  OBJECT-TYPE
            SYNTAX  DisplayString (SIZE (0..20))
            ACCESS  read-write
            STATUS  mandatory
            DESCRIPTION
                "DHCP subnet default router address"
            ::= { r8AddDelSubnetDefRouterEntry 3 }

        r8AddDelDefRouterCMD  OBJECT-TYPE
            SYNTAX  INTEGER{
                    add(1),
                    delete(2)
                }
            ACCESS  read-write
            STATUS  mandatory
            DESCRIPTION
                "Add/Delete a DHCP subnet default router"
            ::= { r8AddDelSubnetDefRouterEntry 4 }

--
-- R8 Add or Delete DHCP Subnet Netbios Server
--

        r8AddDelSubnetNetbiosSv  OBJECT-TYPE
            SYNTAX  SEQUENCE OF R8ADSNetbiosSvEntry
            ACCESS  not-accessible
            STATUS  mandatory
            DESCRIPTION
                "DHCP subnet netbios server control Table"
            ::= { r8DHCPSubnet 6 }

        r8ADSNetbiosSvEntry  OBJECT-TYPE
            SYNTAX  R8ADSNetbiosSvEntry
            ACCESS  not-accessible
            STATUS  mandatory
            DESCRIPTION
                "DHCP subnet netbios server control Entry"
            INDEX { r8ADSNSlotIndex }
            ::= { r8AddDelSubnetNetbiosSv 1 }

        R8ADSNetbiosSvEntry ::= SEQUENCE {
            r8ADSNSlotIndex             LSSlotID,
            r8AddDelNetbSubnetName      DisplayString,
            r8AddDelNetbServerAddr      DisplayString,
            r8AddDelNetbServerCMD       INTEGER
        }

        r8ADSNSlotIndex  OBJECT-TYPE
            SYNTAX  LSSlotID
            ACCESS  read-only
            STATUS  mandatory
            DESCRIPTION
                "R8 slot"
            ::= { r8ADSNetbiosSvEntry 1 }

        r8AddDelNetbSubnetName  OBJECT-TYPE
            SYNTAX  DisplayString (SIZE (0..16))
            ACCESS  read-write
            STATUS  mandatory
            DESCRIPTION
                "DHCP subnet name"
            ::= { r8ADSNetbiosSvEntry 2 }

        r8AddDelNetbServerAddr  OBJECT-TYPE
            SYNTAX  DisplayString (SIZE (0..20))
            ACCESS  read-write
            STATUS  mandatory
            DESCRIPTION
                "DHCP subnet netbios server address"
            ::= { r8ADSNetbiosSvEntry 3 }

        r8AddDelNetbServerCMD  OBJECT-TYPE
            SYNTAX  INTEGER{
                    add(1),
                    delete(2)
                }
            ACCESS  read-write
            STATUS  mandatory
            DESCRIPTION
                "Add/Delete a DHCP subnet netbios server"
            ::= { r8ADSNetbiosSvEntry 4 }

--
-- R8 DHCP Subnet Option
--

        r8DhcpSubnetOption  OBJECT-TYPE
            SYNTAX  SEQUENCE OF R8DhcpSubnetOptionEntry
            ACCESS  not-accessible
            STATUS  mandatory
            DESCRIPTION
                "DHCP subnet option Table"
            ::= { r8DHCPSubnet 7 }

        r8DhcpSubnetOptionEntry  OBJECT-TYPE
            SYNTAX  R8DhcpSubnetOptionEntry
            ACCESS  not-accessible
            STATUS  mandatory
            DESCRIPTION
                "DHCP subnet option Entry"
            INDEX { r8DSOSlotIndex ,
                    r8DhcpSubnetOIndex ,
                    r8DhcpSubnetOptionIndex }
            ::= { r8DhcpSubnetOption 1 }

        R8DhcpSubnetOptionEntry ::= SEQUENCE {
            r8DSOSlotIndex              LSSlotID,
            r8DhcpSubnetOIndex          INTEGER,
            r8DhcpSubnetOptionIndex     INTEGER,
            r8DhcpSubnetOptSubnetName   DisplayString,
            r8DhcpSubnetOptionCode      INTEGER,
            r8DhcpSubnetOptionValue     DisplayString
        }

        r8DSOSlotIndex  OBJECT-TYPE
            SYNTAX  LSSlotID
            ACCESS  read-only
            STATUS  mandatory
            DESCRIPTION
                "R8 slot"
            ::= { r8DhcpSubnetOptionEntry 1 }

        r8DhcpSubnetOIndex  OBJECT-TYPE
            SYNTAX  INTEGER (1..8)
            ACCESS  read-only
            STATUS  mandatory
            DESCRIPTION
                "DHCP subnet index"
            ::= { r8DhcpSubnetOptionEntry 2 }

        r8DhcpSubnetOptionIndex  OBJECT-TYPE
            SYNTAX  INTEGER (1..8)
            ACCESS  read-only
            STATUS  mandatory
            DESCRIPTION
                "DHCP subnet Option index"
            ::= { r8DhcpSubnetOptionEntry 3 }

        r8DhcpSubnetOptSubnetName  OBJECT-TYPE
            SYNTAX  DisplayString (SIZE (0..16))
            ACCESS  read-only
            STATUS  mandatory
            DESCRIPTION
                "DHCP subnet name"
            ::= { r8DhcpSubnetOptionEntry 4 }

        r8DhcpSubnetOptionCode  OBJECT-TYPE
            SYNTAX  INTEGER (1..255)
            ACCESS  read-only
            STATUS  mandatory
            DESCRIPTION
                "DHCP subnet option code"
            ::= { r8DhcpSubnetOptionEntry 5 }

        r8DhcpSubnetOptionValue  OBJECT-TYPE
            SYNTAX  DisplayString (SIZE (0..64))
            ACCESS  read-only
            STATUS  mandatory
            DESCRIPTION
                "DHCP subnet option value"
            ::= { r8DhcpSubnetOptionEntry 6 }

--
-- R8 Add or Delete DHCP Subnet Option
--

        r8AddDelDhcpSubnetOption  OBJECT-TYPE
            SYNTAX  SEQUENCE OF R8ADHSubnetOptionEntry
            ACCESS  not-accessible
            STATUS  mandatory
            DESCRIPTION
                "DHCP subnet option control Table"
            ::= { r8DHCPSubnet 8 }

        r8ADHSubnetOptionEntry  OBJECT-TYPE
            SYNTAX  R8ADHSubnetOptionEntry
            ACCESS  not-accessible
            STATUS  mandatory
            DESCRIPTION
                "DHCP subnet option control Entry"
            INDEX { r8ADDSOSlotIndex }
            ::= { r8AddDelDhcpSubnetOption 1 }

        R8ADHSubnetOptionEntry ::= SEQUENCE {
            r8ADDSOSlotIndex            LSSlotID,
            r8AddDelSubnetOptSubnetName DisplayString,
            r8AddDelSubnetOptionCode    INTEGER,
            r8AddDelSubnetOptionValue   DisplayString,
            r8AddDelSubnetOptionCMD     INTEGER
        }

        r8ADDSOSlotIndex  OBJECT-TYPE
            SYNTAX  LSSlotID
            ACCESS  read-only
            STATUS  mandatory
            DESCRIPTION
                "R8 slot"
            ::= { r8ADHSubnetOptionEntry 1 }

        r8AddDelSubnetOptSubnetName  OBJECT-TYPE
            SYNTAX  DisplayString (SIZE (0..16))
            ACCESS  read-write
            STATUS  mandatory
            DESCRIPTION
                "DHCP subnet name"
            ::= { r8ADHSubnetOptionEntry 2 }

        r8AddDelSubnetOptionCode  OBJECT-TYPE
            SYNTAX  INTEGER (1..255)
            ACCESS  read-write
            STATUS  mandatory
            DESCRIPTION
                "DHCP subnet option code"
            ::= { r8ADHSubnetOptionEntry 3 }

        r8AddDelSubnetOptionValue  OBJECT-TYPE
            SYNTAX  DisplayString (SIZE (0..64))
            ACCESS  read-write
            STATUS  mandatory
            DESCRIPTION
                "DHCP subnet option value"
            ::= { r8ADHSubnetOptionEntry 4 }

        r8AddDelSubnetOptionCMD  OBJECT-TYPE
            SYNTAX  INTEGER{
                    add(1),
                    delete(2)
                }
            ACCESS  read-write
            STATUS  mandatory
            DESCRIPTION
                "Add/Delete DHCP subnet option"
            ::= { r8ADHSubnetOptionEntry 5 }

--
-- R8 DHCP Relay
--

    r8DHCPRelay                OBJECT IDENTIFIER ::= { r8DHCP 2 }

--
-- R8 DHCP Relay Config
--

        r8DhcpRelayCFG  OBJECT-TYPE
            SYNTAX  SEQUENCE OF R8DhcpRelayCFGEntry
            ACCESS  not-accessible
            STATUS  mandatory
            DESCRIPTION
                "DHCP Relay Config Table"
            ::= { r8DHCPRelay 1 }

        r8DhcpRelayCFGEntry  OBJECT-TYPE
            SYNTAX  R8DhcpRelayCFGEntry
            ACCESS  not-accessible
            STATUS  mandatory
            DESCRIPTION
                "DHCP Relay Config Entry"
            INDEX { r8DRCSlotIndex }
            ::= { r8DhcpRelayCFG 1 }

        R8DhcpRelayCFGEntry ::= SEQUENCE {
            r8DRCSlotIndex              LSSlotID,
            r8DhcpRelay                 INTEGER,
            r8DhcpRelayServerIP         DisplayString,
            r8DhcpRelayInterface        DisplayString,
            r8DhcpRelayBridgeMgmt       DisplayString
        }

        r8DRCSlotIndex  OBJECT-TYPE
            SYNTAX  LSSlotID
            ACCESS  read-only
            STATUS  mandatory
            DESCRIPTION
                "R8 slot"
            ::= { r8DhcpRelayCFGEntry 1 }

        r8DhcpRelay  OBJECT-TYPE
            SYNTAX  INTEGER{
                    disable(1),
                    enable(2)
                }
            ACCESS  read-write
            STATUS  mandatory
            DESCRIPTION
                "DHCP relay function disable/enable"
            ::= { r8DhcpRelayCFGEntry 2 }

        r8DhcpRelayServerIP  OBJECT-TYPE
            SYNTAX  DisplayString (SIZE (0..20))
            ACCESS  read-write
            STATUS  mandatory
            DESCRIPTION
                "DHCP Relay Server IP"
            ::= { r8DhcpRelayCFGEntry 3 }

        r8DhcpRelayInterface  OBJECT-TYPE
            SYNTAX  DisplayString (SIZE (0..20))
            ACCESS  read-only
            STATUS  mandatory
            DESCRIPTION
                "DHCP relay interface"
            ::= { r8DhcpRelayCFGEntry 4 }

        r8DhcpRelayBridgeMgmt  OBJECT-TYPE
            SYNTAX  DisplayString (SIZE (0..20))
            ACCESS  read-only
            STATUS  mandatory
            DESCRIPTION
                "DHCP relay bridge mgmt"
            ::= { r8DhcpRelayCFGEntry 5 }

--
-- R8 Add or Delete DHCP Relay Interface
--

        r8DhcpRelayAddDelIntf  OBJECT-TYPE
            SYNTAX  SEQUENCE OF R8DhcpRelayADIEntry
            ACCESS  not-accessible
            STATUS  mandatory
            DESCRIPTION
                "Add or Delete DHCP Relay interface Table"
            ::= { r8DHCPRelay 2 }

        r8DhcpRelayADIEntry  OBJECT-TYPE
            SYNTAX  R8DhcpRelayADIEntry
            ACCESS  not-accessible
            STATUS  mandatory
            DESCRIPTION
                "Add or Delete DHCP Relay interface Entry"
            INDEX { r8DRADISlotIndex }
            ::= { r8DhcpRelayAddDelIntf 1 }

        R8DhcpRelayADIEntry ::= SEQUENCE {
            r8DRADISlotIndex            LSSlotID,
            r8DhcpRelayAddDelIntfName   DisplayString,
            r8DhcpRelayAddDelIntfCMD    INTEGER
        }

        r8DRADISlotIndex  OBJECT-TYPE
            SYNTAX  LSSlotID
            ACCESS  read-only
            STATUS  mandatory
            DESCRIPTION
                "R8 slot"
            ::= { r8DhcpRelayADIEntry 1 }

        r8DhcpRelayAddDelIntfName  OBJECT-TYPE
            SYNTAX  DisplayString (SIZE (0..8))
            ACCESS  read-write
            STATUS  mandatory
            DESCRIPTION
                "Interface Name"
            ::= { r8DhcpRelayADIEntry 2 }

        r8DhcpRelayAddDelIntfCMD  OBJECT-TYPE
            SYNTAX  INTEGER{
                    add(1),
                    delete(2)
                }
            ACCESS  read-write
            STATUS  mandatory
            DESCRIPTION
                "Add or delete interface command"
            ::= { r8DhcpRelayADIEntry 3 }


--
--  R8 MultiLink
--

    r8MultiLink            OBJECT IDENTIFIER ::= { oct-rt-b-card 10 }

--
-- R8 MultiLink Config Table
--

        r8MultiLinkCFG  OBJECT-TYPE
            SYNTAX  SEQUENCE OF R8MultiLinkCFGEntry
            ACCESS  not-accessible
            STATUS  mandatory
            DESCRIPTION
                "MultiLink Config Table."
            ::= { r8MultiLink 1 }

        r8MultiLinkCFGEntry  OBJECT-TYPE
            SYNTAX  R8MultiLinkCFGEntry
            ACCESS  not-accessible
            STATUS  mandatory
            DESCRIPTION
                "MultiLink Config Entry"
            INDEX { r8MLCSlotIndex ,
                    r8MLinkIndex }
            ::= { r8MultiLinkCFG 1 }

        R8MultiLinkCFGEntry ::= SEQUENCE {
            r8MLCSlotIndex              LSSlotID,
            r8MLinkIndex                INTEGER,
            r8MLinkName                 DisplayString,
            r8MLinkIPAddr               DisplayString,
            r8MLinkBundles              DisplayString,
            r8MLinkInterval             INTEGER,
            r8MLinkTimes                INTEGER
        }

        r8MLCSlotIndex  OBJECT-TYPE
            SYNTAX  LSSlotID
            ACCESS  read-only
            STATUS  mandatory
            DESCRIPTION
                "R8 slot"
            ::= { r8MultiLinkCFGEntry 1 }

        r8MLinkIndex  OBJECT-TYPE
            SYNTAX  INTEGER
            ACCESS  read-only
            STATUS  mandatory
            DESCRIPTION
                "Multilink Index"
            ::= { r8MultiLinkCFGEntry 2 }

        r8MLinkName  OBJECT-TYPE
            SYNTAX  DisplayString (SIZE (0..16))
            ACCESS  read-only
            STATUS  mandatory
            DESCRIPTION
                "Multilink Virtual Name"
            ::= { r8MultiLinkCFGEntry 3 }

        r8MLinkIPAddr  OBJECT-TYPE
            SYNTAX  DisplayString (SIZE (0..20))
            ACCESS  read-write
            STATUS  mandatory
            DESCRIPTION
                "Multilink IP Address(xxx.xxx.xxx.xxx/xx)"
            ::= { r8MultiLinkCFGEntry 4 }

        r8MLinkBundles  OBJECT-TYPE
            SYNTAX  DisplayString (SIZE (0..255))
            ACCESS  read-only
            STATUS  mandatory
            DESCRIPTION
                "Multilink Boundles Interface"
            ::= { r8MultiLinkCFGEntry 5 }

        r8MLinkInterval  OBJECT-TYPE
            SYNTAX  INTEGER (5..255)
            ACCESS  read-write
            STATUS  mandatory
            DESCRIPTION
                "Multilink The Retry Interval"
            ::= { r8MultiLinkCFGEntry 6 }

        r8MLinkTimes  OBJECT-TYPE
            SYNTAX  INTEGER (6..100)
            ACCESS  read-write
            STATUS  mandatory
            DESCRIPTION
                "Multilink The Retry Times"
            ::= { r8MultiLinkCFGEntry 7 }

--
-- R8 Create and Destroy Multilink
--

        r8CreateDestroyMultiLink  OBJECT-TYPE
            SYNTAX  SEQUENCE OF R8CreateDestroyMultiLinkEntry
            ACCESS  not-accessible
            STATUS  mandatory
            DESCRIPTION
                "Create and Destroy MultiLink Table."
            ::= { r8MultiLink 2 }

        r8CreateDestroyMultiLinkEntry  OBJECT-TYPE
            SYNTAX  R8CreateDestroyMultiLinkEntry
            ACCESS  not-accessible
            STATUS  mandatory
            DESCRIPTION
                "Create and Destroy Multilin Entry"
            INDEX { r8CDMLSlotIndex }
            ::= { r8CreateDestroyMultiLink 1 }

        R8CreateDestroyMultiLinkEntry ::= SEQUENCE {
            r8CDMLSlotIndex             LSSlotID,
            r8CreateDestroyMLinkName    DisplayString,
            r8CreateDestroyMLinkCMD     INTEGER
        }

        r8CDMLSlotIndex  OBJECT-TYPE
            SYNTAX  LSSlotID
            ACCESS  read-only
            STATUS  mandatory
            DESCRIPTION
                "R8 slot"
            ::= { r8CreateDestroyMultiLinkEntry 1 }

        r8CreateDestroyMLinkName  OBJECT-TYPE
            SYNTAX  DisplayString (SIZE (1..16))
            ACCESS  read-write
            STATUS  mandatory
            DESCRIPTION
                "Create/Destroy Multilink Name"
            ::= { r8CreateDestroyMultiLinkEntry 2 }

        r8CreateDestroyMLinkCMD  OBJECT-TYPE
            SYNTAX  INTEGER {
                    create(1),
                    destroy(2)
                }
            ACCESS  read-write
            STATUS  mandatory
            DESCRIPTION
                "Create/Destory Multilink Command"
            ::= { r8CreateDestroyMultiLinkEntry 3 }

--
-- R8 MultiLink Add/Delete Interface Table
--

        r8MultiLinkAddDeleteIntf OBJECT-TYPE
            SYNTAX  SEQUENCE OF R8MultiLinkADIEntry
            ACCESS  not-accessible
            STATUS  mandatory
            DESCRIPTION
                "Add/Delete Interfaces To Multilink Bundle Table"
            ::= { r8MultiLink 3 }

        r8MultiLinkADIEntry  OBJECT-TYPE
            SYNTAX  R8MultiLinkADIEntry
            ACCESS  not-accessible
            STATUS  mandatory
            DESCRIPTION
                "Add/Delete Interfaces To Multilink Bundle Entry"
            INDEX { r8MLADISlotIndex }
            ::= { r8MultiLinkAddDeleteIntf 1 }

        R8MultiLinkADIEntry ::= SEQUENCE {
            r8MLADISlotIndex            LSSlotID,
            r8MLinkAddDelMLinkName      DisplayString,
            r8MLinkAddDelIntfName       DisplayString,
            r8MLinkAddDelIntfCMD        INTEGER
        }

        r8MLADISlotIndex  OBJECT-TYPE
            SYNTAX  LSSlotID
            ACCESS  read-only
            STATUS  mandatory
            DESCRIPTION
                "R8 slot"
            ::= { r8MultiLinkADIEntry 1 }

        r8MLinkAddDelMLinkName  OBJECT-TYPE
            SYNTAX  DisplayString (SIZE (1..16))
            ACCESS  read-write
            STATUS  mandatory
            DESCRIPTION
                "Add/Delete Interface MultiLink Name"
            ::= { r8MultiLinkADIEntry 2 }

        r8MLinkAddDelIntfName  OBJECT-TYPE
            SYNTAX  DisplayString(SIZE (1..20))
            ACCESS  read-write
            STATUS  mandatory
            DESCRIPTION
                "Add/Delete Interfaces(wan1~wan64) to Multilink Bundle"
            ::= { r8MultiLinkADIEntry 3 }

        r8MLinkAddDelIntfCMD  OBJECT-TYPE
            SYNTAX  INTEGER {
                    add(1),
                    delete(2)
                }
            ACCESS  read-write
            STATUS  mandatory
            DESCRIPTION
                "Add/Delete interfaces To/From Multilink Bundle"
            ::= { r8MultiLinkADIEntry 4 }

--==================================================
--  R8SVLAN Eddie
--==================================================
    r8svlan         OBJECT IDENTIFIER ::= { oct-rt-b-card 11 }
--==================================================
--  R8SVLAN State
--==================================================

        r8svlanState  OBJECT-TYPE
            SYNTAX  SEQUENCE OF R8SvlanStateEntry
            ACCESS  not-accessible
            STATUS  mandatory
            DESCRIPTION
                "Vlan state Table"
            ::= { r8svlan 1 }

        r8svlanStateEntry  OBJECT-TYPE
            SYNTAX  R8SvlanStateEntry
            ACCESS  not-accessible
            STATUS  mandatory
            DESCRIPTION
                "Svlan state Entry"
            INDEX { r8ssIndex , r8svlanBrgGroupID }
            ::= { r8svlanState 1 }


        R8SvlanStateEntry ::= SEQUENCE {
            r8ssIndex                   LSSlotID,
            r8svlanBrgGroupID           INTEGER,
            r8svlanBrgName              DisplayString,
            r8svlanEnable               INTEGER,
            r8svlanMgmtSVID             INTEGER,
            r8svlanRegenCRC             INTEGER,
            r8svlanTPID                 DisplayString,
            r8svlanPCP                  INTEGER,
            r8svlanDEI                  INTEGER
        }
        r8ssIndex  OBJECT-TYPE
            SYNTAX  LSSlotID
            ACCESS  read-only
            STATUS  mandatory
            DESCRIPTION
                "R8 ssIndex"
            ::= { r8svlanStateEntry 1 }

        r8svlanBrgGroupID  OBJECT-TYPE
            SYNTAX  INTEGER
            ACCESS  read-only
            STATUS  mandatory
            DESCRIPTION
                "Bridge group ID"
            ::= { r8svlanStateEntry 2 }

        r8svlanBrgName  OBJECT-TYPE
            SYNTAX  DisplayString (SIZE (0..8))
            ACCESS  read-only
            STATUS  mandatory
            DESCRIPTION
                "Bridge group name"
            ::= { r8svlanStateEntry 3 }

        r8svlanEnable  OBJECT-TYPE
            SYNTAX  INTEGER{
                    disable(1),
                    enable(2)
                }
            ACCESS  read-write
            STATUS  mandatory
            DESCRIPTION
                "SVlan state enable/disable"
            ::= { r8svlanStateEntry 4 }

        r8svlanMgmtSVID  OBJECT-TYPE
            SYNTAX  INTEGER (1..4094)
            ACCESS  read-write
            STATUS  mandatory
            DESCRIPTION
                "SVLAN ID for the bridge management interface"
            ::= { r8svlanStateEntry 5 }

        r8svlanRegenCRC  OBJECT-TYPE
            SYNTAX  INTEGER{
                    disable(1),
                    enable(2)
                }
            ACCESS  read-write
            STATUS  mandatory
            DESCRIPTION
                "Enable/disable CRC regenerating on WAN interfaces for SVLAN frames"
            ::= { r8svlanStateEntry 6 }

        r8svlanTPID  OBJECT-TYPE
            SYNTAX  DisplayString (SIZE (1..4))
            ACCESS  read-write
            STATUS  mandatory
            DESCRIPTION
                "TPID "
            ::= { r8svlanStateEntry 7 }

        r8svlanPCP  OBJECT-TYPE
            SYNTAX  INTEGER(0..7)
            ACCESS  read-write
            STATUS  mandatory
            DESCRIPTION
                "Priority Code Point"
            ::= { r8svlanStateEntry 8 }

        r8svlanDEI  OBJECT-TYPE
            SYNTAX  INTEGER{
                    disable(1),
                    enable(2)
                }
            ACCESS  read-write
            STATUS  mandatory
            DESCRIPTION
                "Drop Eligible Indicato"
            ::= { r8svlanStateEntry 9 }

--==================================================
-- R8SVLAN Table
--==================================================


        r8svlanTable  OBJECT-TYPE
            SYNTAX  SEQUENCE OF R8SvlanTableEntry
            ACCESS  not-accessible
            STATUS  mandatory
            DESCRIPTION
                "SVlan Table"
            ::= { r8svlan 2 }

        r8svlanTableEntry  OBJECT-TYPE
            SYNTAX  R8SvlanTableEntry
            ACCESS  not-accessible
            STATUS  mandatory
            DESCRIPTION
                "Svlan Table Tag Member Entry"
            INDEX { r8stIndex ,
                    r8svlanTableBrgGroupID ,
                    r8svlanID ,
                    r8svlanTableIndex
                }
            ::= { r8svlanTable 1 }

        R8SvlanTableEntry ::= SEQUENCE {
            r8stIndex                   LSSlotID,
            r8svlanTableBrgGroupID      INTEGER,
            r8svlanID                   INTEGER,
            r8svlanTableIndex           INTEGER,
            r8svlanMember               DisplayString
        }
        r8stIndex  OBJECT-TYPE
            SYNTAX  LSSlotID
            ACCESS  read-only
            STATUS  mandatory
            DESCRIPTION
                "R8 stIndex"
            ::= { r8svlanTableEntry 1 }

        r8svlanTableBrgGroupID OBJECT-TYPE
            SYNTAX  INTEGER
            ACCESS  read-only
            STATUS  mandatory
            DESCRIPTION
                "Bridge Group Index"
            ::= { r8svlanTableEntry 2 }

        r8svlanID  OBJECT-TYPE
            SYNTAX  INTEGER (1..4095)
            ACCESS  read-only
            STATUS  mandatory
            DESCRIPTION
                "SVlan Index"
            ::= { r8svlanTableEntry 3 }

        r8svlanTableIndex  OBJECT-TYPE
            SYNTAX  INTEGER
            ACCESS  read-only
            STATUS  mandatory
            DESCRIPTION
                "SVlan Member Index"
            ::= { r8svlanTableEntry 4 }

        r8svlanMember  OBJECT-TYPE
            SYNTAX  DisplayString (SIZE (0..200))
            ACCESS  read-only
            STATUS  mandatory
            DESCRIPTION
                "Vlan member"
            ::= { r8svlanTableEntry 5 }

--=========================================================
--  SVLAN Table Control
--=========================================================

    r8svlanTableControl  OBJECT IDENTIFIER ::= { r8svlan 3 }

--=========================================================
--  SVLAN Create and Destroy
--=========================================================

        r8svlanCreateDestroyVlan  OBJECT-TYPE
            SYNTAX  SEQUENCE OF R8SvlanCreateDestroyVlanEntry
            ACCESS  not-accessible
            STATUS  mandatory
            DESCRIPTION
                "Create and destroy svlan Table"
            ::= { r8svlanTableControl 1 }

        r8svlanCreateDestroyVlanEntry  OBJECT-TYPE
            SYNTAX  R8SvlanCreateDestroyVlanEntry
            ACCESS  not-accessible
            STATUS  mandatory
            DESCRIPTION
                "Create and destroy svlan Entry"
            INDEX { r8scIndex }
            ::= { r8svlanCreateDestroyVlan 1 }

        R8SvlanCreateDestroyVlanEntry ::= SEQUENCE {
            r8scIndex                    LSSlotID,
            r8svlanCreateDestroyBrgName  DisplayString,
            r8svlanCreateDestroyVidNum   INTEGER,
            r8svlanCreateDestroyCMD      INTEGER
        }
        r8scIndex  OBJECT-TYPE
            SYNTAX  LSSlotID
            ACCESS  read-only
            STATUS  mandatory
            DESCRIPTION
                "R8scIndex"
            ::= { r8svlanCreateDestroyVlanEntry 1 }

        r8svlanCreateDestroyBrgName  OBJECT-TYPE
            SYNTAX  DisplayString (SIZE (0..8))
            ACCESS  read-write
            STATUS  mandatory
            DESCRIPTION
                "Bridge group name"
            ::= { r8svlanCreateDestroyVlanEntry 2 }

        r8svlanCreateDestroyVidNum  OBJECT-TYPE
            SYNTAX  INTEGER (1..4094)
            ACCESS  read-write
            STATUS  mandatory
            DESCRIPTION
                "Vlan VID"
            ::= { r8svlanCreateDestroyVlanEntry 3 }

        r8svlanCreateDestroyCMD  OBJECT-TYPE
            SYNTAX  INTEGER{
                    create-svlan(1),
                    destroy-svlan(2)
                }
            ACCESS  read-write
            STATUS  mandatory
            DESCRIPTION
                "Create and destroy vlan command"
            ::= { r8svlanCreateDestroyVlanEntry 4 }



--=========================================================
--  SVLAN Add and Delete Port
--=========================================================


        r8svlanAddDelPort  OBJECT-TYPE
            SYNTAX  SEQUENCE OF R8SvlanAddDelPortEntry
            ACCESS  not-accessible
            STATUS  mandatory
            DESCRIPTION
                "SVlan add and del port Table"
            ::= { r8svlanTableControl 2 }

        r8svlanAddDelPortEntry  OBJECT-TYPE
            SYNTAX  R8SvlanAddDelPortEntry
            ACCESS  not-accessible
            STATUS  mandatory
            DESCRIPTION
                "SVlan add and del port Entry"
            INDEX { r8saIndex }
            ::= { r8svlanAddDelPort 1 }

        R8SvlanAddDelPortEntry ::= SEQUENCE {
            r8saIndex                    LSSlotID,
            r8svlanAddDelPortBrgName     DisplayString,
            r8svlanAddDelPortVidNum      INTEGER,
            r8svlanAddDelPortInterface   DisplayString,
            r8svlanAddDelPortCMD         INTEGER
        }
        r8saIndex  OBJECT-TYPE
            SYNTAX  LSSlotID
            ACCESS  read-only
            STATUS  mandatory
            DESCRIPTION
                "R8 saIndex"
            ::= { r8svlanAddDelPortEntry 1 }

        r8svlanAddDelPortBrgName  OBJECT-TYPE
            SYNTAX  DisplayString (SIZE (0..8))
            ACCESS  read-write
            STATUS  mandatory
            DESCRIPTION
                "Bridge group name"
            ::= { r8svlanAddDelPortEntry 2 }

        r8svlanAddDelPortVidNum  OBJECT-TYPE
            SYNTAX  INTEGER (1..4094)
            ACCESS  read-write
            STATUS  mandatory
            DESCRIPTION
                "SVlan VID"
            ::= { r8svlanAddDelPortEntry 3 }

        r8svlanAddDelPortInterface  OBJECT-TYPE
            SYNTAX  DisplayString (SIZE (0..16))
            ACCESS  read-write
            STATUS  mandatory
            DESCRIPTION
                "Interface Name"
            ::= { r8svlanAddDelPortEntry 4 }

        r8svlanAddDelPortCMD  OBJECT-TYPE
            SYNTAX  INTEGER{
                    add-port-to-svlan(1),
                    delete-port-from-svlan(2)
                }
            ACCESS  read-write
            STATUS  mandatory
            DESCRIPTION
                "SVlan add and delete port command"
            ::= { r8svlanAddDelPortEntry 5 }

--=========================================================
-- SVLAN Port Table
--=========================================================

        r8svlanPortTable  OBJECT-TYPE
            SYNTAX  SEQUENCE OF R8SvlanPortTableEntry
            ACCESS  not-accessible
            STATUS  mandatory
            DESCRIPTION
                "Vlan port table control Table"
            ::= { r8svlan 4 }

        r8svlanPortTableEntry  OBJECT-TYPE
            SYNTAX  R8SvlanPortTableEntry
            ACCESS  not-accessible
            STATUS  mandatory
            DESCRIPTION
                "Vlan port table control Entry"
            INDEX { r8spIndex , r8svlanPortIndex }
            ::= { r8svlanPortTable 1 }

        R8SvlanPortTableEntry ::= SEQUENCE {
            r8spIndex                   LSSlotID,
            r8svlanPortIndex            INTEGER,
            r8svlanPortIFName           DisplayString,
            r8svlanPortPVID             INTEGER,
            r8svlanPortType             INTEGER,
            r8svlanPortIngressFilter    INTEGER
        }
        r8spIndex  OBJECT-TYPE
            SYNTAX  LSSlotID
            ACCESS  read-only
            STATUS  mandatory
            DESCRIPTION
                "R8 spIndex"
            ::= { r8svlanPortTableEntry 1 }

        r8svlanPortIndex  OBJECT-TYPE
            SYNTAX  INTEGER
            ACCESS  read-only
            STATUS  mandatory
            DESCRIPTION
                "SVlan port index"
            ::= { r8svlanPortTableEntry 2 }

        r8svlanPortIFName  OBJECT-TYPE
            SYNTAX  DisplayString (SIZE (0..20))
            ACCESS  read-only
            STATUS  mandatory
            DESCRIPTION
                "Interface name"
            ::= { r8svlanPortTableEntry 3 }


        r8svlanPortPVID  OBJECT-TYPE
            SYNTAX  INTEGER (1..4094)
            ACCESS  read-write
            STATUS  mandatory
            DESCRIPTION
                "Interface PVID"
            ::= { r8svlanPortTableEntry 4 }

        r8svlanPortType  OBJECT-TYPE
            SYNTAX  INTEGER{
                    provider(1),
                    customer(2)
                }
            ACCESS  read-write
            STATUS  mandatory
            DESCRIPTION
                "the acceptable port type"
            ::= { r8svlanPortTableEntry 5 }

        r8svlanPortIngressFilter  OBJECT-TYPE
            SYNTAX  INTEGER{
                    disable(1),
                    enable(2)
                }
            ACCESS  read-write
            STATUS  mandatory
            DESCRIPTION
                "Enable/disable ingress filtering"
            ::= { r8svlanPortTableEntry 6 }

        rtbTotalCard   OBJECT-TYPE
            SYNTAX  INTEGER
            ACCESS  read-only
            STATUS  mandatory
            DESCRIPTION
                "Total cards of 8RTB"
            ::= { oct-rt-b-card 100 }


--=====================================================================--
--  TDMOE card MIB
--=====================================================================--


    tdmoeConfigTable                  OBJECT IDENTIFIER ::= { tdmoe-card 1 }

        miscellaneousConfig              OBJECT-TYPE
            SYNTAX  SEQUENCE OF   MiscellaneousConfigEntry
            ACCESS  not-accessible
            STATUS  mandatory
            DESCRIPTION
                "TDMoE  Miscellaneous Config Table."
            ::= { tdmoeConfigTable  1 }

        miscellaneousConfigEntry            OBJECT-TYPE
            SYNTAX  MiscellaneousConfigEntry
            ACCESS  not-accessible
            STATUS  mandatory
            DESCRIPTION
                "TDMoE Advanced Config  Entry"
            INDEX { tdmoeActBundleSlotIndex }
            ::= { miscellaneousConfig 1 }

        MiscellaneousConfigEntry ::= SEQUENCE {
            tdmoeActBundleSlotIndex      LSSlotID,
            tdmoeActBundleTimer      INTEGER,
            tdmoeAlarmFilter            INTEGER,
            tdmoeDelaySwitch            INTEGER,
            tdmoeRecoverDelay           INTEGER
        }

        tdmoeActBundleSlotIndex  OBJECT-TYPE
            SYNTAX  LSSlotID
            ACCESS  read-only
            STATUS  mandatory
            DESCRIPTION
                "slot index"
            ::= { miscellaneousConfigEntry 1 }

        tdmoeActBundleTimer     OBJECT-TYPE
            SYNTAX INTEGER (1..99999999)
            ACCESS  read-write
            STATUS  mandatory
            DESCRIPTION
                "arp timer range: 1~9999999 seconds"
            ::= { miscellaneousConfigEntry 2 }

        tdmoeAlarmFilter     OBJECT-TYPE
            SYNTAX INTEGER (0..180)
            ACCESS  read-write
            STATUS  mandatory
            DESCRIPTION
                "Protection: Alarm Filter: 0~180 seconds"
            ::= { miscellaneousConfigEntry 3 }

        tdmoeDelaySwitch     OBJECT-TYPE
            SYNTAX INTEGER (0..180)
            ACCESS  read-write
            STATUS  mandatory
            DESCRIPTION
                "Protection: Delay Switch: 0~180 seconds"
            ::= { miscellaneousConfigEntry 4 }

        tdmoeRecoverDelay     OBJECT-TYPE
            SYNTAX INTEGER (0..180)
            ACCESS  read-write
            STATUS  mandatory
            DESCRIPTION
                "Protection: Recover Delay: 0~180 seconds"
            ::= { miscellaneousConfigEntry 5 }


--
--Qos Table
--

    qosConfig  OBJECT IDENTIFIER ::= {  tdmoeConfigTable 2}

    qosClassOfServiceConfig  OBJECT IDENTIFIER ::= { qosConfig 1 }

        priorityModeConfig  OBJECT-TYPE
            SYNTAX  SEQUENCE OF  PriorityModeEntry
            ACCESS  not-accessible
            STATUS  mandatory
            DESCRIPTION
                "The Ethernet QoS Priority Mode Table."
            ::= { qosClassOfServiceConfig 1 }

        priorityModeEntry  OBJECT-TYPE
            SYNTAX  PriorityModeEntry
            ACCESS  not-accessible
            STATUS  mandatory
            DESCRIPTION
                "An entry in the Ethernet QoS Priority Mode Table."
            INDEX { priorityModeSlotIndex , priorityModePortIndex }
            ::= { priorityModeConfig 1 }

        PriorityModeEntry ::= SEQUENCE {
            priorityModeSlotIndex       LSSlotID,
            priorityModePortIndex       TdmoeEthIndex,
            priorityModeMode            INTEGER
        }
        priorityModeSlotIndex  OBJECT-TYPE
            SYNTAX  LSSlotID
            ACCESS  read-only
            STATUS  mandatory
            DESCRIPTION
                "slot index"
            ::= { priorityModeEntry 1 }

        priorityModePortIndex  OBJECT-TYPE
            SYNTAX  TdmoeEthIndex
            ACCESS  read-only
            STATUS  mandatory
            DESCRIPTION
                "SWPortNum:switch port SNMP, WAN1, WAN2, and LAN."
            ::= { priorityModeEntry 2 }

        priorityModeMode  OBJECT-TYPE
            SYNTAX  INTEGER {
                    fixed(1),
                    cos(2),
                    tos(3)
                }
            ACCESS  read-write
            STATUS  mandatory
            DESCRIPTION
                "WAN1 Priority Mode"
            ::= { priorityModeEntry 3 }

--
--  FixedPriorityTable
--

        fixedPriorityConfig  OBJECT-TYPE
            SYNTAX  SEQUENCE OF  FixedPriorityEntry
            ACCESS  not-accessible
            STATUS  mandatory
            DESCRIPTION
                "The Ethernet QoS Fixed Priority Table."
            ::= { qosClassOfServiceConfig 2 }

        fixedPriorityEntry  OBJECT-TYPE
            SYNTAX  FixedPriorityEntry
            ACCESS  not-accessible
            STATUS  mandatory
            DESCRIPTION
                "An entry in the Ethernet QoS Fixed Priority Table."
            INDEX { fixSlotIndex , fixPortIndex }
            ::= { fixedPriorityConfig 1 }

        FixedPriorityEntry ::= SEQUENCE {
            fixSlotIndex                LSSlotID,
            fixPortIndex                TdmoeEthIndex,
            fixTransmitPriority         INTEGER
        }

        fixSlotIndex  OBJECT-TYPE
            SYNTAX  LSSlotID
            ACCESS  read-only
            STATUS  mandatory
            DESCRIPTION
                "slot index"
            ::= { fixedPriorityEntry 1 }

        fixPortIndex  OBJECT-TYPE
            SYNTAX  TdmoeEthIndex
            ACCESS  read-only
            STATUS  mandatory
            DESCRIPTION
                "priority port."
            ::= { fixedPriorityEntry 2 }

        fixTransmitPriority  OBJECT-TYPE
            SYNTAX  INTEGER {
                    priority-0(1),
                    priority-1(2),
                    priority-2(3),
                    priority-3(4)
                }
            ACCESS  read-write
            STATUS  mandatory
            DESCRIPTION
                "Transmit Priority"
            ::= { fixedPriorityEntry 3 }

--
--  VlanCosPriorityTable
--

        vlanCosPriorityConfig  OBJECT-TYPE
            SYNTAX  SEQUENCE OF  VlanCosPriorityEntry
            ACCESS  not-accessible
            STATUS  mandatory
            DESCRIPTION
                "The Ethernet QoS VLAN Cos Priority Table."
            ::= { qosClassOfServiceConfig 3 }

        vlanCosPriorityEntry  OBJECT-TYPE
            SYNTAX  VlanCosPriorityEntry
            ACCESS  not-accessible
            STATUS  mandatory
            DESCRIPTION
                "An entry in the Ethernet QoS VLAN Cos Priority Table."
            INDEX { cosSlotIndex , cosCosPriority }
            ::= { vlanCosPriorityConfig 1 }

        VlanCosPriorityEntry ::= SEQUENCE {
            cosSlotIndex                LSSlotID,
            cosCosPriority              INTEGER,
            cosTransmitPriority         INTEGER
        }

        cosSlotIndex  OBJECT-TYPE
            SYNTAX  LSSlotID
            ACCESS  read-only
            STATUS  mandatory
            DESCRIPTION
                "slot index"
            ::= { vlanCosPriorityEntry 1 }

        cosCosPriority  OBJECT-TYPE
            SYNTAX  INTEGER {
                    cos-priority-0(1),
                    cos-priority-1(2),
                    cos-priority-2(3),
                    cos-priority-3(4),
                    cos-priority-4(5),
                    cos-priority-5(6),
                    cos-priority-6(7),
                    cos-priority-7(8)
                }
            ACCESS  read-only
            STATUS  mandatory
            DESCRIPTION
                "Vlan Cos Priority 0 to 7"
            ::= { vlanCosPriorityEntry 2 }

        cosTransmitPriority  OBJECT-TYPE
            SYNTAX  INTEGER {
                    priority-0(1),
                    priority-1(2),
                    priority-2(3),
                    priority-3(4)
                }
            ACCESS  read-write
            STATUS  mandatory
            DESCRIPTION
                "Transmit Priority"
            ::= { vlanCosPriorityEntry 3 }


--
--   TosPriorityTable
--

        tosPriorityConfig  OBJECT-TYPE
            SYNTAX  SEQUENCE OF  TosPriorityEntry
            ACCESS  not-accessible
            STATUS  mandatory
            DESCRIPTION
                "The Ethernet QoS Tos Priority Table."
            ::= { qosClassOfServiceConfig 4 }

        tosPriorityEntry  OBJECT-TYPE
            SYNTAX  TosPriorityEntry
            ACCESS  not-accessible
            STATUS  mandatory
            DESCRIPTION
                "An entry in the Ethernet QoS Tos Priority Table."
            INDEX { tosSlotIndex , tosTosPriority }
            ::= { tosPriorityConfig 1 }

        TosPriorityEntry ::= SEQUENCE {
            tosSlotIndex                LSSlotID,
            tosTosPriority              INTEGER,
            tosTransmitPriority         INTEGER
        }
        tosSlotIndex  OBJECT-TYPE
            SYNTAX  LSSlotID
            ACCESS  read-only
            STATUS  mandatory
            DESCRIPTION
                "slot index"
            ::= { tosPriorityEntry 1 }

        tosTosPriority  OBJECT-TYPE
            SYNTAX  INTEGER {
                    tos-priority-0(1),
                    tos-priority-1(2),
                    tos-priority-2(3),
                    tos-priority-3(4),
                    tos-priority-4(5),
                    tos-priority-5(6),
                    tos-priority-6(7),
                    tos-priority-7(8)
                }
            ACCESS  read-only
            STATUS  mandatory
            DESCRIPTION
                "Tos Priority 0 to 7"
            ::= { tosPriorityEntry 2 }

        tosTransmitPriority  OBJECT-TYPE
            SYNTAX  INTEGER {
                    priority-0(1),
                    priority-1(2),
                    priority-2(3),
                    priority-3(4)
                }
            ACCESS  read-write
            STATUS  mandatory
            DESCRIPTION
                "Transmit Priority"
            ::= { tosPriorityEntry 3 }

--=====================
--  Qos Tx Schedule Table
--=====================

    qosTxScheduleConfig  OBJECT IDENTIFIER ::= { qosConfig 2 }

        scheduleAlgorithmConfig  OBJECT-TYPE
            SYNTAX  SEQUENCE OF  ScheduleAlgorithmEntry
            ACCESS  not-accessible
            STATUS  mandatory
            DESCRIPTION
                "The Ethernet QoS Scheduling Algorithm Table."
            ::= { qosTxScheduleConfig 1 }

        scheduleAlgorithmEntry  OBJECT-TYPE
            SYNTAX  ScheduleAlgorithmEntry
            ACCESS  not-accessible
            STATUS  mandatory
            DESCRIPTION
                "An entry in the Ethernet QoS Scheduling Algorithm Table."
            INDEX { scheduleSlotIndex , schedulePortIndex }
            ::= { scheduleAlgorithmConfig 1 }

        ScheduleAlgorithmEntry ::= SEQUENCE {
            scheduleSlotIndex           LSSlotID,
            schedulePortIndex           TdmoeEthIndex,
            scheduleAlgorithm           INTEGER

    }

        scheduleSlotIndex  OBJECT-TYPE
            SYNTAX  LSSlotID
            ACCESS  read-only
            STATUS  mandatory
            DESCRIPTION
                "slot index"
            ::= { scheduleAlgorithmEntry 1 }

        schedulePortIndex  OBJECT-TYPE
            SYNTAX  TdmoeEthIndex
            ACCESS  read-only
            STATUS  mandatory
            DESCRIPTION
                "scheduling algorithm port"
            ::= { scheduleAlgorithmEntry 2 }

        scheduleAlgorithm  OBJECT-TYPE
            SYNTAX  INTEGER {
                    strict-priority(1),
                    weighted-round-robin(2)

                }
            ACCESS  read-write
            STATUS  mandatory
            DESCRIPTION
                "scheduling algorithm"
            ::= { scheduleAlgorithmEntry 3 }

--
--  WRR Weight Table
--




        wrrWeightConfig  OBJECT-TYPE
            SYNTAX  SEQUENCE OF  WrrweightEntry
            ACCESS  not-accessible
            STATUS  mandatory
            DESCRIPTION
                "The Ethernet QoS Scheduling Algorithm Table."
            ::= { qosTxScheduleConfig 2 }

        wrrweightEntry  OBJECT-TYPE
            SYNTAX  WrrweightEntry
            ACCESS  not-accessible
            STATUS  mandatory
            DESCRIPTION
                "An entry in the Ethernet QoS Wrr Table."
            INDEX { wrrSlotIndex }
            ::= { wrrWeightConfig 1 }

        WrrweightEntry ::= SEQUENCE {
            wrrSlotIndex                LSSlotID,
            wrrWeightP0Queue            INTEGER,
            wrrWeightP1Queue            INTEGER,
            wrrWeightP2Queue            INTEGER,
            wrrWeightP3Queue            INTEGER

    }

        wrrSlotIndex  OBJECT-TYPE
            SYNTAX  LSSlotID
            ACCESS  read-only
            STATUS  mandatory
            DESCRIPTION
                "slot index"
            ::= { wrrweightEntry 1 }

        wrrWeightP0Queue  OBJECT-TYPE
            SYNTAX  INTEGER (0..100)
            ACCESS  read-write
            STATUS  mandatory
            DESCRIPTION
                "P0 Queue Percentage, sum of Queue percentage of the four ports must be 100% "
            ::= { wrrweightEntry 2 }

        wrrWeightP1Queue  OBJECT-TYPE
            SYNTAX  INTEGER (0..100)
            ACCESS  read-write
            STATUS  mandatory
            DESCRIPTION
                "P1 Queue Percentage"
            ::= { wrrweightEntry 3}

        wrrWeightP2Queue  OBJECT-TYPE
            SYNTAX  INTEGER (0..100)
            ACCESS  read-write
            STATUS  mandatory
            DESCRIPTION
                "P2 Queue Percentage"
            ::= { wrrweightEntry 4}

        wrrWeightP3Queue  OBJECT-TYPE
            SYNTAX  INTEGER (0..100)
            ACCESS  read-write
            STATUS  mandatory
            DESCRIPTION
                "P3 Queue Percentage"
            ::= { wrrweightEntry 5}


--   flow control

        flowControlConfig  OBJECT-TYPE
            SYNTAX  SEQUENCE OF  FlowControlEntry
            ACCESS  not-accessible
            STATUS  mandatory
            DESCRIPTION
                "The Ethernet QoS flow control Table."
            ::= { qosTxScheduleConfig 3 }

        flowControlEntry  OBJECT-TYPE
            SYNTAX  FlowControlEntry
            ACCESS  not-accessible
            STATUS  mandatory
            DESCRIPTION
                "An entry in the Ethernet QoS flow control Table."
            INDEX { flowSlotIndex , flowPortIndx }
            ::= { flowControlConfig 1 }

        FlowControlEntry ::= SEQUENCE {
            flowSlotIndex               LSSlotID,
            flowPortIndx                TdmoeEthIndex,
            flowFlowControl             INTEGER
        }

        flowSlotIndex  OBJECT-TYPE
            SYNTAX  LSSlotID
            ACCESS  read-only
            STATUS  mandatory
            DESCRIPTION
                "slot index"
            ::= { flowControlEntry 1 }

        flowPortIndx  OBJECT-TYPE
            SYNTAX  TdmoeEthIndex
            ACCESS  read-only
            STATUS  mandatory
            DESCRIPTION
                "TDMoE port 1-4"
            ::= { flowControlEntry 2 }

        flowFlowControl  OBJECT-TYPE
            SYNTAX  INTEGER {
                    enable  (1),
                    disable (2)
                }
            ACCESS  read-write
            STATUS  mandatory
            DESCRIPTION
                "flow control"
            ::= { flowControlEntry 3 }



        qosRateCtrlConfig  OBJECT-TYPE
            SYNTAX  SEQUENCE OF  RateCtrlEntry
            ACCESS  not-accessible
            STATUS  mandatory
            DESCRIPTION
                "The Ethernet QoS Scheduling Algorithm Table."
            ::= { qosConfig 3}

        rateCtrlEntry  OBJECT-TYPE
            SYNTAX  RateCtrlEntry
            ACCESS  not-accessible
            STATUS  mandatory
            DESCRIPTION
                "An entry in the Ethernet QoS Wrr Table."
            INDEX { rateCtrlSlotIndex , rateCtrlPortIndex }
            ::= { qosRateCtrlConfig 1 }


        RateCtrlEntry ::= SEQUENCE {
            rateCtrlSlotIndex           LSSlotID,
            rateCtrlPortIndex           TdmoeEthIndex,
            rateCtrlSpeedRangeValue     INTEGER,
            rateCtrlRateGranularity     INTEGER
        }

        rateCtrlSlotIndex  OBJECT-TYPE
            SYNTAX  LSSlotID
            ACCESS  read-only
            STATUS  mandatory
            DESCRIPTION
                "slot index"
            ::= { rateCtrlEntry 1 }

        rateCtrlPortIndex  OBJECT-TYPE
            SYNTAX  TdmoeEthIndex
            ACCESS  read-only
            STATUS  mandatory
            DESCRIPTION
                "Port Index"
            ::= { rateCtrlEntry 2 }

        rateCtrlSpeedRangeValue  OBJECT-TYPE
            SYNTAX  INTEGER
            ACCESS  read-write
            STATUS  mandatory
            DESCRIPTION
                "64kbps to 1mbps in the ratelimit mode of 64kbps, 1mbps to 100mbps in
                the ratelimit mode of 1 mbp, and 100 mbps to 1000 mbps in the ratelimit mode of 10 mbps. "
            ::= { rateCtrlEntry 3 }


        rateCtrlRateGranularity OBJECT-TYPE
            SYNTAX  INTEGER {
                    kbps-64(1),
                    mbps-1(2),
                    mbps-10(3)
                }
            ACCESS  read-write
            STATUS  mandatory
            DESCRIPTION
                "port rate limit: from 64kbps to 1mbps in increments of of 64kbps, from 1mbps to 100mbps in
                increments of 1 mbp and from 100 mbps to 1000 mbps in increments of 10 mbps."
            ::= { rateCtrlEntry 4 }

--
--   eth phy config table
--
    ethPortConfig    OBJECT IDENTIFIER ::= { tdmoeConfigTable 3}

        ethPortElectricConfig      OBJECT-TYPE
            SYNTAX  SEQUENCE OF EthPortelectricEntry
            ACCESS  not-accessible
            STATUS  mandatory
            DESCRIPTION
                "Eth phy electric Config Table."
            ::= { ethPortConfig 1 }

        ethPortelectricEntry       OBJECT-TYPE
            SYNTAX  EthPortelectricEntry
            ACCESS  not-accessible
            STATUS  mandatory
            DESCRIPTION
                "Eth Phy Config Entry."
            INDEX { ethSlotIndex , ethPortIndex }
            ::= { ethPortElectricConfig 1 }

        EthPortelectricEntry ::= SEQUENCE {
            ethSlotIndex                LSSlotID,
            ethPortIndex                TdmoeEthIndex,
            ethState                    INTEGER,
            ethAutoNegotiation          INTEGER,
            ethSpeed                    INTEGER,
            ethDuplex                   INTEGER
        }

        ethSlotIndex  OBJECT-TYPE
            SYNTAX  LSSlotID
            ACCESS  read-only
            STATUS  mandatory
            DESCRIPTION
                "slot index"
            ::= { ethPortelectricEntry 1 }

        ethPortIndex    OBJECT-TYPE
            SYNTAX  TdmoeEthIndex
            ACCESS  read-only
            STATUS  mandatory
            DESCRIPTION
                "eth port 1-4"
            ::= { ethPortelectricEntry 2 }

        ethState         OBJECT-TYPE
            SYNTAX  INTEGER {
                    enable  (1),
                    disable (2)
                }
            ACCESS  read-write
            STATUS  mandatory
            DESCRIPTION
                "port State"
            ::= { ethPortelectricEntry 3 }

        ethAutoNegotiation    OBJECT-TYPE
            SYNTAX  INTEGER {
                    enable  (1),
                    disable (2)

                }
            ACCESS  read-write
            STATUS  mandatory
            DESCRIPTION
                "auto negotiation state"
            ::= {ethPortelectricEntry 4 }

        ethSpeed    OBJECT-TYPE
            SYNTAX  INTEGER {
                    mbps-10   (1),
                    mbps-100  (2),
                    mbps-1000 (3)
                }
            ACCESS  read-write
            STATUS  mandatory
            DESCRIPTION
                "port speed 10/100/1000 mbps"
            ::= {ethPortelectricEntry 5 }

        ethDuplex      OBJECT-TYPE
            SYNTAX  INTEGER {
                    half   (1),
                    full   (2)
                }
            ACCESS  read-write
            STATUS  mandatory
            DESCRIPTION
                "port duplex mode(half/full)"
            ::= {ethPortelectricEntry 6 }


        ethPortOpticalConfig      OBJECT-TYPE
            SYNTAX  SEQUENCE OF EthPortopticalEntry
            ACCESS  not-accessible
            STATUS  mandatory
            DESCRIPTION
                "Eth phy electric Config Table."
            ::= { ethPortConfig 2 }

        ethPortopticalEntry       OBJECT-TYPE
            SYNTAX  EthPortopticalEntry
            ACCESS  not-accessible
            STATUS  mandatory
            DESCRIPTION
                "Eth Phy Config Entry."
            INDEX { ethopticalSlotIndex , ethopticalPortIndex }
            ::= { ethPortOpticalConfig 1 }

        EthPortopticalEntry ::= SEQUENCE {
            ethopticalSlotIndex         LSSlotID,
            ethopticalPortIndex         INTEGER,
            ethopticalState             INTEGER,
            ethopticalAutolaserShutdown INTEGER,
            ethopticalSpeed             INTEGER,
            ethopticalAutoNegotiation   INTEGER,
            ethopticalDuplex            INTEGER,
            ethopticalPulseRepetitionTime   INTEGER,
            ethopticalManualRestart         INTEGER
        }

        ethopticalSlotIndex  OBJECT-TYPE
            SYNTAX  LSSlotID
            ACCESS  read-only
            STATUS  mandatory
            DESCRIPTION
                "slot index"
            ::= { ethPortopticalEntry 1 }

        ethopticalPortIndex    OBJECT-TYPE
            SYNTAX  INTEGER {
                    eth-1   (1),
                    eth-2   (2)
                }
            ACCESS  read-only
            STATUS  mandatory
            DESCRIPTION
                "eth port 1-2"
            ::= { ethPortopticalEntry 2 }

        ethopticalState         OBJECT-TYPE
            SYNTAX  INTEGER {
                    enable  (1),
                    disable (2)
                }
            ACCESS  read-write
            STATUS  mandatory
            DESCRIPTION
                "port State"
            ::= { ethPortopticalEntry 3 }

        ethopticalAutolaserShutdown    OBJECT-TYPE
            SYNTAX  INTEGER {
                    enable  (1),
                    disable (2)

                }
            ACCESS  read-write
            STATUS  mandatory
            DESCRIPTION
                "autolasershutdown state"
            ::= {ethPortopticalEntry 4 }

        ethopticalSpeed         OBJECT-TYPE
            SYNTAX  INTEGER {
                    mbps-1000 (1),
                    mbps-100  (2)
                }
            ACCESS  read-write
            STATUS  mandatory
            DESCRIPTION
                "port State"
            ::= { ethPortopticalEntry 5 }

        ethopticalAutoNegotiation   OBJECT-TYPE
            SYNTAX  INTEGER {
                    enable  (1),
                    disable (2)
                }
            ACCESS  read-only
            STATUS  mandatory
            DESCRIPTION
                "auto negotiation state"
            ::= {ethPortopticalEntry 6 }

        ethopticalDuplex    OBJECT-TYPE
            SYNTAX  INTEGER {
                    half   (1),
                    full   (2)
                }
            ACCESS  read-only
            STATUS  mandatory
            DESCRIPTION
                "port duplex mode(half/full)"
            ::= {ethPortopticalEntry 7 }

        ethopticalPulseRepetitionTime  OBJECT-TYPE
            SYNTAX  INTEGER (60..300)
            ACCESS  read-write
            STATUS  mandatory
            DESCRIPTION
                "ALS/APSD pulse repetition time for automatic restart(sec)"
            ::= { ethPortopticalEntry 8 }

        ethopticalManualRestart  OBJECT-TYPE
            SYNTAX  INTEGER {
                    off(1),
                    start(2)
                }
            ACCESS  read-write
            STATUS  mandatory
            DESCRIPTION
                "Optical port manual restart"
            ::= { ethPortopticalEntry 9 }

--
-- ethL2 Table
--

    ethSwitchConfig                  OBJECT IDENTIFIER ::= { tdmoeConfigTable 4 }


        agingtimeConfig      OBJECT-TYPE
            SYNTAX  SEQUENCE OF  AgingtimeEntry
            ACCESS  not-accessible
            STATUS  mandatory
            DESCRIPTION
                ""
            ::= {  ethSwitchConfig 1 }

        agingtimeEntry    OBJECT-TYPE
            SYNTAX  AgingtimeEntry
            ACCESS  not-accessible
            STATUS  mandatory
            DESCRIPTION
                "age tme Entry."
            INDEX { tdmoeAgingSlot }
            ::= { agingtimeConfig 1 }

        AgingtimeEntry  ::= SEQUENCE {
            tdmoeAgingSlot        LSSlotID,
            tdmoeAgingtime        INTEGER
        }

        tdmoeAgingSlot  OBJECT-TYPE
            SYNTAX  LSSlotID
            ACCESS  read-only
            STATUS  mandatory
            DESCRIPTION
                "slot index"
            ::= { agingtimeEntry 1 }

        tdmoeAgingtime     OBJECT-TYPE
            SYNTAX   INTEGER (0..3825)
            ACCESS   read-write
            STATUS   mandatory
            DESCRIPTION
                "mac table aging time range: 0~3825 seconds, setting 0 second disables aging process
                aging time must be a multiple of fifteen."
            ::= {agingtimeEntry 2 }


        addMacConfig      OBJECT-TYPE
            SYNTAX  SEQUENCE OF  AddMacEntry
            ACCESS  not-accessible
            STATUS  mandatory
            DESCRIPTION
                "add static mac table"
            ::= {  ethSwitchConfig  2}

        addMacEntry    OBJECT-TYPE
            SYNTAX  AddMacEntry
            ACCESS  not-accessible
            STATUS  mandatory
            DESCRIPTION
                "age static mac Entry."
            INDEX { tdmoeAddSlot }
            ::= { addMacConfig 1 }

        AddMacEntry   ::= SEQUENCE {
            tdmoeAddSlot                LSSlotID,
            tdmoeAddPort                INTEGER,
            tdmoeAddmacAddress          DisplayString
        }

        tdmoeAddSlot  OBJECT-TYPE
            SYNTAX  LSSlotID
            ACCESS  read-only
            STATUS  mandatory
            DESCRIPTION
                "slot index"
            ::= { addMacEntry 1 }

        tdmoeAddPort     OBJECT-TYPE
            SYNTAX   INTEGER {
                    mgt   (1),
                    eth-1 (2),
                    eth-2 (3),
                    eth-3 (4),
                    eth-4 (5)
                }
            ACCESS    read-write
            STATUS    mandatory
            DESCRIPTION
                "determine which port to add mac"
            ::= {addMacEntry  2}

        tdmoeAddmacAddress   OBJECT-TYPE
            SYNTAX   DisplayString (SIZE (0..12))
            ACCESS   read-write
            STATUS    mandatory
            DESCRIPTION
                "add static mac in hex mode(0~F)"
            ::= {addMacEntry  3}



--


        delMacConfig     OBJECT-TYPE
            SYNTAX  SEQUENCE OF  DelMacEntry
            ACCESS  not-accessible
            STATUS  mandatory
            DESCRIPTION
                "delete static mac table"
            ::= {  ethSwitchConfig  3 }

        delMacEntry    OBJECT-TYPE
            SYNTAX  DelMacEntry
            ACCESS  not-accessible
            STATUS  mandatory
            DESCRIPTION
                "delete static mac Entry."
            INDEX { tdmoeDelSlot }
            ::= { delMacConfig 1 }

        DelMacEntry   ::= SEQUENCE {
            tdmoeDelSlot                LSSlotID,
            tdmoeDelPort                INTEGER
        }

        tdmoeDelSlot  OBJECT-TYPE
            SYNTAX  LSSlotID
            ACCESS  read-only
            STATUS  mandatory
            DESCRIPTION
                "slot index"
            ::= { delMacEntry 1 }

        tdmoeDelPort     OBJECT-TYPE
            SYNTAX   INTEGER {
                    mgt   (1),
                    eth-1 (2),
                    eth-2 (3),
                    eth-3 (4),
                    eth-4 (5)
                }
            ACCESS    read-write
            STATUS    mandatory
            DESCRIPTION
                "delete port's mac"
            ::= {delMacEntry  2}




    rstpTable            OBJECT IDENTIFIER ::= {tdmoeConfigTable 5  }

        rstpConfig      OBJECT-TYPE
            SYNTAX  SEQUENCE OF  RstpConfigEntry
            ACCESS  not-accessible
            STATUS  mandatory
            DESCRIPTION
                "rstp config table"
            ::= {rstpTable  1}

        rstpConfigEntry    OBJECT-TYPE
            SYNTAX  RstpConfigEntry
            ACCESS  not-accessible
            STATUS  mandatory
            DESCRIPTION
                "rstp Config Entry."
            INDEX { rstpSlotIndex }
            ::= { rstpConfig 1 }

        RstpConfigEntry  ::= SEQUENCE {
            rstpSlotIndex               LSSlotID,
            rstpState                   INTEGER,
            rstpPriority                INTEGER,
            rstpHellotime               INTEGER,
            rstpMaximumAge              INTEGER,
            rstpForwardDelay            INTEGER
        }

        rstpSlotIndex  OBJECT-TYPE
            SYNTAX  LSSlotID
            ACCESS  read-only
            STATUS  mandatory
            DESCRIPTION
                "slot index"
            ::= { rstpConfigEntry 1 }

        rstpState   OBJECT-TYPE
            SYNTAX  INTEGER {
                    off  (1),
                    --stp  (2),
                    rstp (3)
                }
            ACCESS  read-write
            STATUS  mandatory
            DESCRIPTION
                "rstp state"
            ::= {rstpConfigEntry  2}

        rstpPriority   OBJECT-TYPE
            SYNTAX   INTEGER (0..65534)
            ACCESS  read-write
            STATUS  mandatory
            DESCRIPTION
                "rstp priority 0~65534"
            ::= {rstpConfigEntry  3}

        rstpHellotime   OBJECT-TYPE
            SYNTAX   INTEGER (1..10)
            ACCESS  read-write
            STATUS  mandatory
            DESCRIPTION
                "rstp hello time 1~10 seconds"
            ::= {rstpConfigEntry  4}

        rstpMaximumAge  OBJECT-TYPE
            SYNTAX   INTEGER (6..40)
            ACCESS   read-write
            STATUS   mandatory
            DESCRIPTION
                "rstp maxumun age 6~40 seconds"
            ::= {rstpConfigEntry  5}

        rstpForwardDelay   OBJECT-TYPE
            SYNTAX   INTEGER (4..30)
            ACCESS   read-write
            STATUS   mandatory
            DESCRIPTION
                "rstp forward delay 4~30 seconds"
            ::= {rstpConfigEntry  6}

        rstpPortConfig      OBJECT-TYPE
            SYNTAX  SEQUENCE OF  RstpPortConfigEntry
            ACCESS  not-accessible
            STATUS  mandatory
            DESCRIPTION
                ""
            ::= {rstpTable  2}

        rstpPortConfigEntry     OBJECT-TYPE
            SYNTAX    RstpPortConfigEntry
            ACCESS    not-accessible
            STATUS    mandatory
            DESCRIPTION
                "rstp Port Config Entry."
            INDEX { rstpPortSlot , rstpPortIndex }
            ::= { rstpPortConfig 1 }

        RstpPortConfigEntry ::= SEQUENCE {
            rstpPortSlot                LSSlotID,
            rstpPortIndex               TdmoeEthIndex,
            rstpStpState                INTEGER,
            rstpPortPriority            INTEGER,
            rstpPortCost                INTEGER,
            rstpLinkType                INTEGER,
            rstpEdgePort                INTEGER
        }

        rstpPortSlot  OBJECT-TYPE
            SYNTAX  LSSlotID
            ACCESS  read-only
            STATUS  mandatory
            DESCRIPTION
                "slot index"
            ::= { rstpPortConfigEntry 1 }

        rstpPortIndex    OBJECT-TYPE
            SYNTAX  TdmoeEthIndex
            ACCESS  read-only
            STATUS  mandatory
            DESCRIPTION
                "Eth port 1-4"
            ::= { rstpPortConfigEntry 2}

        rstpStpState    OBJECT-TYPE
            SYNTAX   INTEGER{
                    disable (1),
                    block   (2),
                    listen  (3),
                    learn   (4),
                    forward (5)
                }
            ACCESS  read-only
            STATUS  mandatory
            DESCRIPTION
                "stp port state"
            ::= {rstpPortConfigEntry  3}

        rstpPortPriority    OBJECT-TYPE
            SYNTAX  INTEGER (0..240)
            ACCESS   read-write
            STATUS   mandatory
            DESCRIPTION
                "rstp port priority 0~240"
            ::= {rstpPortConfigEntry 4}

        rstpPortCost       OBJECT-TYPE
            SYNTAX  INTEGER (0..65534)
            ACCESS   read-write
            STATUS   mandatory
            DESCRIPTION
                "rstp port cost 0~32767"
            ::= {rstpPortConfigEntry  5}

        rstpLinkType   OBJECT-TYPE
            SYNTAX    INTEGER {
                    auto   (1),
                    p-to-p (2),
                    shared (3)
                }
            ACCESS   read-write
            STATUS   mandatory
            DESCRIPTION
                "rstp port link type"
            ::= {rstpPortConfigEntry  6}

        rstpEdgePort   OBJECT-TYPE
            SYNTAX    INTEGER {
                    enable  (1),
                    disable (2)
                }
            ACCESS  read-write
            STATUS  mandatory
            DESCRIPTION
                "edge port mode"
            ::= {rstpPortConfigEntry  7}


        linkaggregateConfig     OBJECT-TYPE
            SYNTAX  SEQUENCE OF  AggregateEntry
            ACCESS  not-accessible
            STATUS  mandatory
            DESCRIPTION
                "link aggregate config"
            ::= {tdmoeConfigTable  6}

        aggregateEntry    OBJECT-TYPE
            SYNTAX    AggregateEntry
            ACCESS    not-accessible
            STATUS    mandatory
            DESCRIPTION
                "link aggregate Entry."
            INDEX { aggreSlotIndex }
            ::= { linkaggregateConfig 1 }

        AggregateEntry  ::= SEQUENCE {
            aggreSlotIndex              LSSlotID,
            aggreTrunkGroup1            INTEGER,
            aggreTrunkGroup2            INTEGER
        }

        aggreSlotIndex  OBJECT-TYPE
            SYNTAX  LSSlotID
            ACCESS  read-only
            STATUS  mandatory
            DESCRIPTION
                "slot index"
            ::= { aggregateEntry 1 }

        aggreTrunkGroup1   OBJECT-TYPE
            SYNTAX  INTEGER {
                    disable (1),
                    leader-ETH1 (2),
                    leader-ETH2 (3)
                }
            ACCESS  read-write
            STATUS  mandatory
            DESCRIPTION
                "choose group1 port trunk leader(eth1/eth2)"
            ::= {aggregateEntry  2}

        aggreTrunkGroup2   OBJECT-TYPE
            SYNTAX  INTEGER {
                    disable (1),
                    leader-ETH3 (2),
                    leader-ETH4 (3)
                }
            ACCESS  read-write
            STATUS  mandatory
            DESCRIPTION
                "choose group2 porttrunk leader(eth3/eth4)"
            ::= {aggregateEntry  3}


    tributaryConfig           OBJECT IDENTIFIER ::= { tdmoeConfigTable 7 }

        tributaryModeConfig     OBJECT-TYPE
            SYNTAX  SEQUENCE OF  TributaryModeEntry
            ACCESS  not-accessible
            STATUS  mandatory
            DESCRIPTION
                "tributary config table"
            ::= {tributaryConfig 1 }

        tributaryModeEntry    OBJECT-TYPE
            SYNTAX    TributaryModeEntry
            ACCESS    not-accessible
            STATUS    mandatory
            DESCRIPTION
                "tributary Entry."
            INDEX { tribSlotIndex }
            ::= { tributaryModeConfig 1 }

        TributaryModeEntry ::= SEQUENCE  {
            tribSlotIndex               LSSlotID,
            tribMode                    INTEGER
        }
        tribSlotIndex  OBJECT-TYPE
            SYNTAX  LSSlotID
            ACCESS  read-only
            STATUS  mandatory
            DESCRIPTION
                "slot index"
            ::= { tributaryModeEntry 1 }

        tribMode   OBJECT-TYPE
            SYNTAX  INTEGER{
                    e1(1),
                    t1(2)
                }
            ACCESS    read-write
            STATUS    mandatory
            DESCRIPTION
                "transport mode:E1/T1"
            ::= {tributaryModeEntry  2}


        tributaryPortConfig     OBJECT-TYPE
            SYNTAX  SEQUENCE OF  TributaryPortEntry
            ACCESS  not-accessible
            STATUS  mandatory
            DESCRIPTION
                "tributary config table"
            ::= {tributaryConfig 2 }

        tributaryPortEntry    OBJECT-TYPE
            SYNTAX    TributaryPortEntry
            ACCESS    not-accessible
            STATUS    mandatory
            DESCRIPTION
                "tributary Entry."
            INDEX { tribSlot , tribTribIndex }
            ::= { tributaryPortConfig 1 }

        TributaryPortEntry ::= SEQUENCE  {
            tribSlot                    LSSlotID,
            tribTribIndex               TdmoeTribPort,
            tribFrame                   INTEGER,
            tribCAS                     INTEGER,
            tribRemoteloss              INTEGER
        }

        tribSlot  OBJECT-TYPE
            SYNTAX  LSSlotID
            ACCESS  read-only
            STATUS  mandatory
            DESCRIPTION
                "slot index"
            ::= { tributaryPortEntry 1 }

        tribTribIndex    OBJECT-TYPE
            SYNTAX  TdmoeTribPort
            ACCESS  read-only
            STATUS  mandatory
            DESCRIPTION
                "trib port 1-4"
            ::= { tributaryPortEntry  2}

        tribFrame     OBJECT-TYPE
            SYNTAX  INTEGER{
                    e1-fas  (1),
                    e1-unframe (2),
                    t1-t1403(3),
                    t1-esf  (4),
                    t1-d4   (5),
                    t1-unframe (6)
                }
            ACCESS    read-write
            STATUS    mandatory
            DESCRIPTION
                "e1/t1 line frame"
            ::= {tributaryPortEntry  3}

        tribCAS   OBJECT-TYPE
            SYNTAX  INTEGER{
                    off  (1),
                    on   (2)
                }
            ACCESS    read-write
            STATUS    mandatory
            DESCRIPTION
                "cas state"
            ::= {tributaryPortEntry  4}

        tribRemoteloss    OBJECT-TYPE
            SYNTAX  INTEGER{
                    continue-send-packet (1),
                    stop      (2)
                }
            ACCESS    read-write
            STATUS    mandatory
            DESCRIPTION
                "when remote side are lost, local side stop or continue sending data."
            ::= {tributaryPortEntry  5}


    timeSlotIpAssignTable       OBJECT IDENTIFIER ::= { tdmoe-card 2 }

        bundleAllocationConfig  OBJECT-TYPE
            SYNTAX  SEQUENCE OF BundleAllocationEntry
            ACCESS  not-accessible
            STATUS  mandatory
            DESCRIPTION
                "The Bundle Allocation table."
            ::= {timeSlotIpAssignTable 1 }

        bundleAllocationEntry  OBJECT-TYPE
            SYNTAX  BundleAllocationEntry
            ACCESS  not-accessible
            STATUS  mandatory
            DESCRIPTION
                "An entry in the Bundle Allocation table."
            INDEX { tdmoeBundleAllocationSlot }
            ::= { bundleAllocationConfig 1 }

        BundleAllocationEntry ::= SEQUENCE {
            tdmoeBundleAllocationSlot   LSSlotID,
            tdmoeBundleAllocationMode   INTEGER
        }

        tdmoeBundleAllocationSlot  OBJECT-TYPE
            SYNTAX  LSSlotID
            ACCESS  read-only
            STATUS  mandatory
            DESCRIPTION
                "slot index"
            ::= { bundleAllocationEntry 1 }

        tdmoeBundleAllocationMode    OBJECT-TYPE
            SYNTAX  INTEGER {
                    mode-16 (1),
                    mode-32 (2)

                }
            ACCESS  read-write
            STATUS  mandatory
            DESCRIPTION
                "mode16:trib1-16,trib2-16,trib3-16,trib4-16
                mode32:trib1-32,trib2-disable,trib3-32,trib4-disable"
            ::= { bundleAllocationEntry 2 }




        timeSlotAssignConfig   OBJECT-TYPE
            SYNTAX  SEQUENCE OF  TimeSlotAssignEntry
            ACCESS  not-accessible
            STATUS  mandatory
            DESCRIPTION
                "TDMOE bundle timeslot map table."
            ::= {timeSlotIpAssignTable 2 }

        timeSlotAssignEntry     OBJECT-TYPE
            SYNTAX  TimeSlotAssignEntry
            ACCESS  not-accessible
            STATUS  mandatory
            DESCRIPTION
                "bundletimeSlot map Entry."
            INDEX { timeSlotSlotIndex , timeSlotTribIndex , timeSlotTsIndex }
            ::= { timeSlotAssignConfig 1 }

        TimeSlotAssignEntry ::= SEQUENCE {
            timeSlotSlotIndex           LSSlotID,
            timeSlotTribIndex           TdmoeTribPort,
            timeSlotTsIndex             INTEGER,
            timeSlotBundleID            TdmoeBundleId
        }

        timeSlotSlotIndex  OBJECT-TYPE
            SYNTAX  LSSlotID
            ACCESS  read-only
            STATUS  mandatory
            DESCRIPTION
                "slot index"
            ::= { timeSlotAssignEntry 1 }

        timeSlotTribIndex  OBJECT-TYPE
            SYNTAX  TdmoeTribPort
            ACCESS  read-only
            STATUS  mandatory
            DESCRIPTION
                "port index."
            ::= { timeSlotAssignEntry 2 }

        timeSlotTsIndex  OBJECT-TYPE
            SYNTAX  INTEGER (0..31)
            ACCESS  read-only
            STATUS  mandatory
            DESCRIPTION
                "Time slot index."
            ::= { timeSlotAssignEntry 3 }

        timeSlotBundleID  OBJECT-TYPE
            SYNTAX  TdmoeBundleId
            ACCESS  read-write
            STATUS  mandatory
            DESCRIPTION
                "timeslot bundle index."
            ::= { timeSlotAssignEntry 4 }


        bundleIPConfig      OBJECT-TYPE
            SYNTAX  SEQUENCE OF  BundleIPEntry
            ACCESS  not-accessible
            STATUS  mandatory
            DESCRIPTION
                "TDMOE bundle ip table."
            ::= { timeSlotIpAssignTable 3}

        bundleIPEntry     OBJECT-TYPE
            SYNTAX  BundleIPEntry
            ACCESS  not-accessible
            STATUS  mandatory
            DESCRIPTION
                "timeSlotIP Entry."
            INDEX { tdmoeIpSlotIndex }
            ::= { bundleIPConfig 1 }

        BundleIPEntry ::= SEQUENCE {
            tdmoeIpSlotIndex            LSSlotID,
            tdmoeSrcIpAddress           IpAddress,
            tdmoeSubnetMask             IpAddress,
            tdmoeGatewayIpAddress       IpAddress,
            toePriMacAddress                        DisplayString,
            toeSecSrcIpAddress           IpAddress,
            toeSecSubnetMask             IpAddress,
            toeSecGatewayIpAddress       IpAddress
        }

        tdmoeIpSlotIndex  OBJECT-TYPE
            SYNTAX  LSSlotID
            ACCESS  read-only
            STATUS  mandatory
            DESCRIPTION
                "slot index"
            ::= { bundleIPEntry 1 }

        tdmoeSrcIpAddress  OBJECT-TYPE
            SYNTAX  IpAddress
            ACCESS  read-write
            STATUS  mandatory
            DESCRIPTION
                "bundle Source IP Address"
            ::= { bundleIPEntry 2 }

        tdmoeSubnetMask  OBJECT-TYPE
            SYNTAX  IpAddress
            ACCESS  read-write
            STATUS  mandatory
            DESCRIPTION
                "bundle Subnet Mask"
            ::= { bundleIPEntry 3 }


        tdmoeGatewayIpAddress  OBJECT-TYPE
            SYNTAX  IpAddress
            ACCESS  read-write
            STATUS  mandatory
            DESCRIPTION
                "bundle Gateway IP"
            ::= { bundleIPEntry 4 }

        toePriMacAddress  OBJECT-TYPE
            SYNTAX  DisplayString (SIZE (0..20))
            ACCESS  read-only
            STATUS  mandatory
            DESCRIPTION
                "Primary mac address "
            ::= { bundleIPEntry 5}

        toeSecSrcIpAddress  OBJECT-TYPE
            SYNTAX  IpAddress
            ACCESS  read-write
            STATUS  mandatory
            DESCRIPTION
                "Secondary bundle Source IP Address"
            ::= { bundleIPEntry 6}

        toeSecSubnetMask  OBJECT-TYPE
            SYNTAX  IpAddress
            ACCESS  read-write
            STATUS  mandatory
            DESCRIPTION
                "Secondary bundle Subnet Mask"
            ::= { bundleIPEntry 7 }


        toeSecGatewayIpAddress  OBJECT-TYPE
            SYNTAX  IpAddress
            ACCESS  read-write
            STATUS  mandatory
            DESCRIPTION
                "Secondary bundle Gateway IP"
            ::= { bundleIPEntry 8 }

--  Time Slot Ip Table


        timeSlotIPConfig      OBJECT-TYPE
            SYNTAX  SEQUENCE OF  TimeSlotIPEntry
            ACCESS  not-accessible
            STATUS  mandatory
            DESCRIPTION
                "TDMOE timeslot ip table."
            ::= { timeSlotIpAssignTable 4 }

        timeSlotIPEntry       OBJECT-TYPE
            SYNTAX  TimeSlotIPEntry
            ACCESS  not-accessible
            STATUS  mandatory
            DESCRIPTION
                "timeSlotIP Entry."
            INDEX { tdmoeTimeSolt }
            ::= { timeSlotIPConfig 1 }

        TimeSlotIPEntry ::= SEQUENCE {
            tdmoeTimeSolt               LSSlotID,
            tdmoePort                   INTEGER,
            tdmoeBundleID               TdmoeBundleId2,
            tdmoeSrcUdpPortNumber       INTEGER,

            tdmoeFormat                 INTEGER,
            tdmoeDestIPAddress          IpAddress,
            tdmoeTos                    INTEGER,
            tdmoeStratum                INTEGER,
            tdmoeCellInBundle           INTEGER,
            tdmoeJitterTolerance        INTEGER,
            tdmoeJitterBuffer           INTEGER,
            tdmoeVLAN                   INTEGER,
            tdmoeCVLANId                INTEGER,
            tdmoeCVLANPriority          INTEGER,
            tdmoeSVLANId                INTEGER,
            tdmoeSVLANPriority          INTEGER,
            tdmoeAction                 INTEGER,
            tdmoeConfirm                INTEGER,
            toeBuType                     INTEGER,
            tdmoeSrcEcid                INTEGER,
            toeMacAddress             DisplayString,
            toeBP                              INTEGER,
            toeBPMS                            INTEGER,
            toeBPMode                       INTEGER,
            toeBPSecUdpPW                    INTEGER,
            toeBPPriUdpHB                    INTEGER,
            toeBPSecUdpHB                    INTEGER,
            toeBPSecIP                   IpAddress,
            toeBPCVLANId                     INTEGER,
            toeBPCVLANPriority          INTEGER,
            toeBPSVLANId                     INTEGER,
            toeBPSVLANPriority        INTEGER
        }

        tdmoeTimeSolt  OBJECT-TYPE
            SYNTAX  LSSlotID
            ACCESS  read-only
            STATUS  mandatory
            DESCRIPTION
                "slot index"
            ::= { timeSlotIPEntry 1 }

        tdmoePort  OBJECT-TYPE
            SYNTAX  INTEGER   {
                    trib1(1),
                    trib2(2),
                    trib3(3),
                    trib4(4)
                }
            ACCESS  read-write
            STATUS  mandatory
            DESCRIPTION
                "Port 1 to 4"
            ::= { timeSlotIPEntry 2 }

        tdmoeBundleID  OBJECT-TYPE
            SYNTAX  TdmoeBundleId2
            ACCESS  read-write
            STATUS  mandatory
            DESCRIPTION
                "Bundle ID"
            ::= { timeSlotIPEntry 3 }

        tdmoeSrcUdpPortNumber  OBJECT-TYPE
            SYNTAX  INTEGER (1..65535)
            ACCESS  read-write
            STATUS  mandatory
            DESCRIPTION
                "UDP Number"
            ::= { timeSlotIPEntry 4}



        tdmoeFormat  OBJECT-TYPE
            SYNTAX  INTEGER {
                    aal1(1),
                    cesopsn(2),
                    satop(3)
                }
            ACCESS  read-write
            STATUS  mandatory
            DESCRIPTION
                "format"
            ::= { timeSlotIPEntry 5}

        tdmoeDestIPAddress  OBJECT-TYPE
            SYNTAX  IpAddress
            ACCESS  read-write
            STATUS  mandatory
            DESCRIPTION
                "IP Address"
            ::= { timeSlotIPEntry 6}

        tdmoeTos  OBJECT-TYPE
            SYNTAX  INTEGER (0..255)
            ACCESS  read-write
            STATUS  mandatory
            DESCRIPTION
                "TOS Number"
            ::= { timeSlotIPEntry 7}

        tdmoeStratum  OBJECT-TYPE
            SYNTAX  INTEGER {
                    stratum1(1),
                    stratum2(2),
                    stratum3(3),
                    stratum3e(4),
                    stratum4(5)
                }
            ACCESS  read-write
            STATUS  mandatory
            DESCRIPTION
                "Stratum Setup"
            ::= { timeSlotIPEntry 8}

        tdmoeCellInBundle  OBJECT-TYPE
            SYNTAX  INTEGER (1..1600)
            ACCESS  read-write
            STATUS  mandatory
            DESCRIPTION
                "Cell In Bundle"
            ::= { timeSlotIPEntry 9}

        tdmoeJitterTolerance  OBJECT-TYPE
            SYNTAX  INTEGER (1..512)
            ACCESS  read-write
            STATUS  mandatory
            DESCRIPTION
                "Jitter Delay"
            ::= { timeSlotIPEntry 10}

        tdmoeJitterBuffer  OBJECT-TYPE
            SYNTAX  INTEGER (1..512)
            ACCESS  read-write
            STATUS  mandatory
            DESCRIPTION
                "Jitter Size"
            ::= { timeSlotIPEntry 11}

        tdmoeVLAN  OBJECT-TYPE
            SYNTAX  INTEGER {
                    off(1),
                    cvlan(2),
                    svlan(3)
                }
            ACCESS  read-write
            STATUS  mandatory
            DESCRIPTION
                "VLAN switch"
            ::= { timeSlotIPEntry 12}

        tdmoeCVLANId  OBJECT-TYPE
            SYNTAX  INTEGER (1..4094)
            ACCESS  read-write
            STATUS  mandatory
            DESCRIPTION
                "customer VLAN ID"
            ::= { timeSlotIPEntry 13}

        tdmoeCVLANPriority  OBJECT-TYPE
            SYNTAX  INTEGER {
                    p-0(1),
                    p-1(2),
                    p-2(3),
                    p-3(4),
                    p-4(5),
                    p-5(6),
                    p-6(7),
                    p-7(8)
                }
            ACCESS  read-write
            STATUS  mandatory
            DESCRIPTION
                "customer VLAN Priority"
            ::= { timeSlotIPEntry 14}

        tdmoeSVLANId  OBJECT-TYPE
            SYNTAX  INTEGER (1..4094)
            ACCESS  read-write
            STATUS  mandatory
            DESCRIPTION
                "provider VLAN ID"
            ::= { timeSlotIPEntry 15}

        tdmoeSVLANPriority  OBJECT-TYPE
            SYNTAX  INTEGER {
                    p-0(1),
                    p-1(2),
                    p-2(3),
                    p-3(4),
                    p-4(5),
                    p-5(6),
                    p-6(7),
                    p-7(8)
                }
            ACCESS  read-write
            STATUS  mandatory
            DESCRIPTION
                "provider VLAN Priority"
            ::= { timeSlotIPEntry 16}

        tdmoeAction  OBJECT-TYPE
            SYNTAX  INTEGER {
                    add-bundle(1),
                    delete-bundle(2),
                    delete-all(3),
                    active-all(4),
                    change-bundle(5),
                    stop-Tx-bundle(6)
                }
            ACCESS  read-write
            STATUS  mandatory
            DESCRIPTION
                "bundle action"
            ::= { timeSlotIPEntry 17}

        tdmoeConfirm  OBJECT-TYPE
            SYNTAX  INTEGER {
                    yes(1),
                    no(2)
                }
            ACCESS  read-write
            STATUS  mandatory
            DESCRIPTION
                "Confirm Setup"
            ::= { timeSlotIPEntry 18}

        toeBuType  OBJECT-TYPE
            SYNTAX  INTEGER {
                    ip(1),
                    cesoEth(2)
                }
            ACCESS  read-write
            STATUS  mandatory
            DESCRIPTION
                "bu type"
            ::= { timeSlotIPEntry 19}

        tdmoeSrcEcid  OBJECT-TYPE
            SYNTAX  INTEGER (1..65535)
            ACCESS  read-write
            STATUS  mandatory
            DESCRIPTION
                "ECID"
            ::= { timeSlotIPEntry 20}

        toeMacAddress  OBJECT-TYPE
            SYNTAX  DisplayString (SIZE (0..20))
            ACCESS  read-write
            STATUS  mandatory
            DESCRIPTION
                "mac address "
            ::= { timeSlotIPEntry 21}

        toeBP OBJECT-TYPE
            SYNTAX  INTEGER {
                    disable(1),
                    enable(2)
                }
            ACCESS  read-write
            STATUS  mandatory
            DESCRIPTION
                "bundle protection enable"
            ::= { timeSlotIPEntry 22}

        toeBPMS OBJECT-TYPE
            SYNTAX  INTEGER {
                    master(1),
                    slave(2)
                }
            ACCESS  read-write
            STATUS  mandatory
            DESCRIPTION
                "Master or Slave"
            ::= { timeSlotIPEntry 23}

        toeBPMode OBJECT-TYPE
            SYNTAX  INTEGER {
                    non-Revertible(1),
                    revertible(2)
                }
            ACCESS  read-write
            STATUS  mandatory
            DESCRIPTION
                "Revertible"
            ::= { timeSlotIPEntry 24}

        toeBPSecUdpPW  OBJECT-TYPE
            SYNTAX  INTEGER (1..65535)
            ACCESS  read-write
            STATUS  mandatory
            DESCRIPTION
                "Secondary PW UDP port"
            ::= { timeSlotIPEntry 25}

        toeBPPriUdpHB  OBJECT-TYPE
            SYNTAX  INTEGER (1..65535)
            ACCESS  read-write
            STATUS  mandatory
            DESCRIPTION
                "Primary HB UDP port"
            ::= { timeSlotIPEntry 26}

        toeBPSecUdpHB  OBJECT-TYPE
            SYNTAX  INTEGER (1..65535)
            ACCESS  read-write
            STATUS  mandatory
            DESCRIPTION
                "Secondary HB UDP port"
            ::= { timeSlotIPEntry 27}

        toeBPSecIP  OBJECT-TYPE
            SYNTAX  IpAddress
            ACCESS  read-write
            STATUS  mandatory
            DESCRIPTION
                "Secodary Destination IP"
            ::= { timeSlotIPEntry 28}

        toeBPCVLANId  OBJECT-TYPE
            SYNTAX  INTEGER (1..4094)
            ACCESS  read-write
            STATUS  mandatory
            DESCRIPTION
                "customer VLAN ID"
            ::= { timeSlotIPEntry 29}

        toeBPCVLANPriority  OBJECT-TYPE
            SYNTAX  INTEGER {
                    p-0(1),
                    p-1(2),
                    p-2(3),
                    p-3(4),
                    p-4(5),
                    p-5(6),
                    p-6(7),
                    p-7(8)
                }
            ACCESS  read-write
            STATUS  mandatory
            DESCRIPTION
                "customer VLAN Priority"
            ::= { timeSlotIPEntry 30}

        toeBPSVLANId  OBJECT-TYPE
            SYNTAX  INTEGER (1..4094)
            ACCESS  read-write
            STATUS  mandatory
            DESCRIPTION
                "provider VLAN ID"
            ::= { timeSlotIPEntry 31}

        toeBPSVLANPriority  OBJECT-TYPE
            SYNTAX  INTEGER {
                    p-0(1),
                    p-1(2),
                    p-2(3),
                    p-3(4),
                    p-4(5),
                    p-5(6),
                    p-6(7),
                    p-7(8)
                }
            ACCESS  read-write
            STATUS  mandatory
            DESCRIPTION
                "provider VLAN Priority"
            ::= { timeSlotIPEntry 32}


--
--  Alarm Control Table
--

    tdmoeAlarmTable    OBJECT IDENTIFIER ::= { tdmoe-card   3}

        tdmoeAlarmControlTable  OBJECT-TYPE
            SYNTAX  SEQUENCE OF TdmoeAlarmControlEntry
            ACCESS  not-accessible
            STATUS  mandatory
            DESCRIPTION
                "The alarm control table."
            ::= { tdmoeAlarmTable 1 }

        tdmoeAlarmControlEntry  OBJECT-TYPE
            SYNTAX  TdmoeAlarmControlEntry
            ACCESS  not-accessible
            STATUS  mandatory
            DESCRIPTION
                "An entry in the alarm control table."
            INDEX { tdmoeAlarmSlot }
            ::= { tdmoeAlarmControlTable 1 }

        TdmoeAlarmControlEntry ::= SEQUENCE {
            tdmoeAlarmSlot              LSSlotID,
            tdmoeArp-Lost               LsAlarmSeverity,
            tdmoeRx-Lost                LsAlarmSeverity,
            tdmoeLossOfBundle           LsAlarmSeverity,
            tdmoeJit-Buf-Underrun       LsAlarmSeverity,
            tdmoeJit-Buf-Overrun        LsAlarmSeverity,
            tdmoeEthernet-Link          LsAlarmSeverity,
            tdmoeSFP-Alarm          LsAlarmSeverity,
            tdmoeL-bit-alm               LsAlarmSeverity,
            tdmoeR-bit-alm               LsAlarmSeverity,
            tdmoeBP-alarm               LsAlarmSeverity
        }

        tdmoeAlarmSlot  OBJECT-TYPE
            SYNTAX  LSSlotID
            ACCESS  read-only
            STATUS  mandatory
            DESCRIPTION
                "slot index"
            ::= { tdmoeAlarmControlEntry 1 }

        tdmoeArp-Lost  OBJECT-TYPE
            SYNTAX  LsAlarmSeverity
            ACCESS  read-write
            STATUS  mandatory
            DESCRIPTION
                "arp-bundle alarm severity type"
            ::= { tdmoeAlarmControlEntry 2 }

        tdmoeRx-Lost  OBJECT-TYPE
            SYNTAX  LsAlarmSeverity
            ACCESS  read-write
            STATUS  mandatory
            DESCRIPTION
                "rx-lost means the received packet sequence number is not the same as expected sequence
                number. rx-Lost-bundle alarm severity type"
            ::= { tdmoeAlarmControlEntry 3 }

        tdmoeLossOfBundle    OBJECT-TYPE
            SYNTAX  LsAlarmSeverity
            ACCESS  read-write
            STATUS  mandatory
            DESCRIPTION
                "Loss of bundle"
            ::= { tdmoeAlarmControlEntry 4 }

        tdmoeJit-Buf-Underrun    OBJECT-TYPE
            SYNTAX  LsAlarmSeverity
            ACCESS  read-write
            STATUS  mandatory
            DESCRIPTION
                "Jit-Buf-Underrun means jitter buffer is empty. jitter buffer underrun-bundle alarm severity type"
            ::= { tdmoeAlarmControlEntry 5 }

        tdmoeJit-Buf-Overrun    OBJECT-TYPE
            SYNTAX  LsAlarmSeverity
            ACCESS  read-write
            STATUS  mandatory
            DESCRIPTION
                "Jit-Buf-Overrun means that jitter buffer is full and there is no room for
                new data to enter. jitter buffer overrun-bundle alarm severity type"
            ::= { tdmoeAlarmControlEntry 6 }

        tdmoeEthernet-Link    OBJECT-TYPE
            SYNTAX  LsAlarmSeverity
            ACCESS  read-write
            STATUS  mandatory
            DESCRIPTION
                "jitter buffer overrun-bundle alarm severity type"
            ::= { tdmoeAlarmControlEntry 7 }

        tdmoeSFP-Alarm    OBJECT-TYPE
            SYNTAX  LsAlarmSeverity
            ACCESS  read-write
            STATUS  mandatory
            DESCRIPTION
                "SFP-Alarm"
            ::= { tdmoeAlarmControlEntry 8 }

        tdmoeL-bit-alm OBJECT-TYPE
            SYNTAX  LsAlarmSeverity
            ACCESS  read-write
            STATUS  mandatory
            DESCRIPTION
                "bundle L bit alarm"
            ::= { tdmoeAlarmControlEntry 9 }

        tdmoeR-bit-alm OBJECT-TYPE
            SYNTAX  LsAlarmSeverity
            ACCESS  read-write
            STATUS  mandatory
            DESCRIPTION
                "bundle R bit alarm"
            ::= { tdmoeAlarmControlEntry 10 }

        tdmoeBP-alarm OBJECT-TYPE
            SYNTAX  LsAlarmSeverity
            ACCESS  read-write
            STATUS  mandatory
            DESCRIPTION
                "bundle protection-alarm"
            ::= { tdmoeAlarmControlEntry 11 }
--
--    Alarm Threshold Setup Table
--

        tdmoeThresControlTable  OBJECT-TYPE
            SYNTAX  SEQUENCE OF TdmoeThresControlEntry
            ACCESS  not-accessible
            STATUS  mandatory
            DESCRIPTION
                "The alarm control table."
            ::= { tdmoeAlarmTable 2}

        tdmoeThresControlEntry  OBJECT-TYPE
            SYNTAX  TdmoeThresControlEntry
            ACCESS  not-accessible
            STATUS  mandatory
            DESCRIPTION
                "An entry in the threshold control table."
            INDEX { tdmoeThresSlot }
            ::= { tdmoeThresControlTable 1 }

        TdmoeThresControlEntry ::= SEQUENCE {
            tdmoeThresSlot              LSSlotID,
            tdmoeThresArp-Lost          INTEGER,
            tdmoeThresRx-Lost           INTEGER,
            tdmoeThresJit-Buf-Underrun  INTEGER,
            tdmoeThresJit-Buf-Overrun   INTEGER
        }

        tdmoeThresSlot  OBJECT-TYPE
            SYNTAX  LSSlotID
            ACCESS  read-only
            STATUS  mandatory
            DESCRIPTION
                "slot index"
            ::= { tdmoeThresControlEntry 1 }

        tdmoeThresArp-Lost OBJECT-TYPE
            SYNTAX  INTEGER (1..65535)
            ACCESS  read-write
            STATUS  mandatory
            DESCRIPTION
                "Threshold of arp-bundle. ARP-bundle is count of ARP loss for a boundle."
            ::= { tdmoeThresControlEntry 2 }

        tdmoeThresRx-Lost  OBJECT-TYPE
            SYNTAX  INTEGER (1..65535)
            ACCESS  read-write
            STATUS  mandatory
            DESCRIPTION
                "Threshold of ex-Lost-bundle. Rx-Lost is count for a boundle about ethernet Lost/ jump events Packets."
            ::= { tdmoeThresControlEntry 3 }

        tdmoeThresJit-Buf-Underrun  OBJECT-TYPE
            SYNTAX  INTEGER
            ACCESS  read-only
            STATUS  mandatory
            DESCRIPTION
                "Threshold of underrun-bundle. Underrun is count of underrun events for a boundle."
            ::= { tdmoeThresControlEntry 5 }

        tdmoeThresJit-Buf-Overrun  OBJECT-TYPE
            SYNTAX  INTEGER
            ACCESS  read-only
            STATUS  mandatory
            DESCRIPTION
                "Threshold of overrun-bundle. Overrun is count of overrun events for a boundle."
            ::= { tdmoeThresControlEntry 6 }

--
--  Alarm History Table
--

            AlarmSubChannel ::= INTEGER {
        bundle0(1),
        bundle1(2),
        bundle2(3),
        bundle3(4),
        bundle4(5),
        bundle5(6),
        bundle6(7),
        bundle7(8),
        bundle8(9),
        bundle9(10),
        bundle10(11),
        bundle11(12),
        bundle12(13),
        bundle13(14),
        bundle14(15),
        bundle15(16),
        bundle16(17),
        bundle17(18),
        bundle18(19),
        bundle19(20),
        bundle20(21),
        bundle21(22),
        bundle22(23),
        bundle23(24),
        bundle24(25),
        bundle25(26),
        bundle26(27),
        bundle27(28),
        bundle28(29),
        bundle29(30),
        bundle30(31),
        bundle31(32),
        none(33)
    }

        tdmoeAlarmHistoryTable  OBJECT-TYPE
            SYNTAX  SEQUENCE OF TdmoeAlarmHistoryEntry
            ACCESS  not-accessible
            STATUS  mandatory
            DESCRIPTION
                "Alarm History Table"
            ::= { tdmoe-card 4}

        tdmoeAlarmHistoryEntry  OBJECT-TYPE
            SYNTAX  TdmoeAlarmHistoryEntry
            ACCESS  not-accessible
            STATUS  mandatory
            DESCRIPTION
                "Alarm history entry"
            INDEX { tdmoehisSlotIndex , tdmoehisTribIndex ,
                    tdmoehisAlarmSubchannel , tdmoehisAlarmHistoryIndex }
            ::= { tdmoeAlarmHistoryTable 1 }

        TdmoeAlarmHistoryEntry ::= SEQUENCE {
            tdmoehisSlotIndex           LSSlotID,
            tdmoehisTribIndex           TdmoeAlmTribPort,
            tdmoehisAlarmSubchannel     AlarmSubChannel,
            tdmoehisAlarmHistoryIndex   INTEGER,
            tdmoehisThreshold           INTEGER,
            tdmoehisCurrentState        INTEGER,
            tdmoehisCurrentCount        INTEGER,
            tdmoehisAlarm               LsAlarmSeverity
        }

        tdmoehisSlotIndex  OBJECT-TYPE
            SYNTAX  LSSlotID
            ACCESS  read-only
            STATUS  mandatory
            DESCRIPTION
                "slot index"
            ::= { tdmoeAlarmHistoryEntry 1 }

        tdmoehisTribIndex  OBJECT-TYPE
            SYNTAX  TdmoeAlmTribPort
            ACCESS  read-only
            STATUS  mandatory
            DESCRIPTION
                "TDMoE alarm portIndex"
            ::= { tdmoeAlarmHistoryEntry 2 }


        tdmoehisAlarmSubchannel  OBJECT-TYPE
            SYNTAX  AlarmSubChannel
            ACCESS  read-only
            STATUS  mandatory
            DESCRIPTION
                "TDMoE alarm subchannel"
            ::= { tdmoeAlarmHistoryEntry 3}

        tdmoehisAlarmHistoryIndex  OBJECT-TYPE
            SYNTAX  INTEGER {
                    arp-Lost(1),
                    rx-Lost(2),
                    lossOfBundle(3),
                    jit-buf-underrun(4),
                    jit-buf-overrun(5),
                    eth1-link-down(6),
                    eth2-link-down(7),
                    eth3-link-down(8),
                    eth4-link-down(9),
                    spf1-tx-power-high(10),
                    spf2-tx-power-high(11),
                    spf1-tx-power-low(12),
                    spf2-tx-power-low(13),
                    spf1-rx-power-high(14),
                    spf2-rx-power-high(15),
                    spf1-rx-power-low(16),
                    spf2-rx-power-low(17),
                    spf1-tx-bias-high(18),
                    spf2-tx-bias-high(19),
                    spf1-tx-bias-low(20),
                    spf2-tx-bias-low(21),
                    bp-pri-hb-lost(22),
                    bp-sec-hb-lost(23),
                    bundle-l-bit(26),
                    bundle-r-bit(27)

                }
            ACCESS  read-only
            STATUS  mandatory
            DESCRIPTION
                " Alarm History Index "
            ::= { tdmoeAlarmHistoryEntry 4}




        tdmoehisThreshold  OBJECT-TYPE
            SYNTAX  INTEGER
            ACCESS  read-only
            STATUS  mandatory
            DESCRIPTION
                " Alarm History Threshold value"
            ::= { tdmoeAlarmHistoryEntry 5 }

        tdmoehisCurrentState  OBJECT-TYPE
            SYNTAX  INTEGER {
                    ok(1),
                    alarm(2),
                    disable(3)
                }
            ACCESS  read-only
            STATUS  mandatory
            DESCRIPTION
                " Alarm History Current State"
            ::= { tdmoeAlarmHistoryEntry 6 }

        tdmoehisCurrentCount  OBJECT-TYPE
            SYNTAX  INTEGER
            ACCESS  read-only
            STATUS  mandatory
            DESCRIPTION
                " Alarm History Current Count "
            ::= { tdmoeAlarmHistoryEntry 7 }

        tdmoehisAlarm  OBJECT-TYPE
            SYNTAX  LsAlarmSeverity
            ACCESS  read-only
            STATUS  mandatory
            DESCRIPTION
                "Alarm History Alarm State"
            ::= { tdmoeAlarmHistoryEntry 8 }




--
--  Current Performance Table
--

    tdmoePerformanceTable    OBJECT IDENTIFIER ::= { tdmoe-card   5}

        tdmoeCurrentPerfTable  OBJECT-TYPE
            SYNTAX  SEQUENCE OF TdmoeCurrentPerfEntry
            ACCESS  not-accessible
            STATUS  mandatory
            DESCRIPTION
                "Current Performance Table"
            ::= { tdmoePerformanceTable 1}

        tdmoeCurrentPerfEntry  OBJECT-TYPE
            SYNTAX  TdmoeCurrentPerfEntry
            ACCESS  not-accessible
            STATUS  mandatory
            DESCRIPTION
                "User current performance entry"
            INDEX { tdmoeCurrentPerfSlot , tdmoeCurrentTribIndex , tdmoeCurrentBundleIDIndex }
            ::= { tdmoeCurrentPerfTable 1 }

        TdmoeCurrentPerfEntry ::= SEQUENCE  {
            tdmoeCurrentPerfSlot        LSSlotID,
            tdmoeCurrentTribIndex       TdmoeTribPort,
            tdmoeCurrentBundleIDIndex   TdmoeBundleId2,
            tdmoeCurrentRx-Lost         INTEGER,
            tdmoeCurrentCell-Lost       INTEGER,
            tdmoeCurrentJit-Buf-Underrun    INTEGER,
            tdmoeCurrentJit-Buf-Overrun     INTEGER,
            tdmoeCurr15MinTimeElapsed       INTEGER,
            tdmoeValid15MinInterval         INTEGER
        }

        tdmoeCurrentPerfSlot  OBJECT-TYPE
            SYNTAX  LSSlotID
            ACCESS  read-only
            STATUS  mandatory
            DESCRIPTION
                "slot index"
            ::= { tdmoeCurrentPerfEntry 1 }

        tdmoeCurrentTribIndex  OBJECT-TYPE
            SYNTAX  TdmoeTribPort
            ACCESS  read-only
            STATUS  mandatory
            DESCRIPTION
                "TDMoE perf portIndex"
            ::= { tdmoeCurrentPerfEntry 2 }


        tdmoeCurrentBundleIDIndex   OBJECT-TYPE
            SYNTAX  TdmoeBundleId2
            ACCESS  read-only
            STATUS  mandatory
            DESCRIPTION
                "TDMoE bundle 1-32"
            ::= { tdmoeCurrentPerfEntry 3 }

        tdmoeCurrentRx-Lost  OBJECT-TYPE
            SYNTAX  INTEGER
            ACCESS  read-only
            STATUS  mandatory
            DESCRIPTION
                "Current Rx-Lost Counter. Rx-Lost is count for a boundle about ethernet Lost/ jump events Packets."
            ::= { tdmoeCurrentPerfEntry 4 }

        tdmoeCurrentCell-Lost  OBJECT-TYPE
            SYNTAX  INTEGER
            ACCESS  read-only
            STATUS  mandatory
            DESCRIPTION
                "Current Cell-Lost Counter. Cell-Lost is count for a boundle about Rx AAL1 Lost Cells."
            ::= { tdmoeCurrentPerfEntry 5 }

        tdmoeCurrentJit-Buf-Underrun  OBJECT-TYPE
            SYNTAX  INTEGER
            ACCESS  read-only
            STATUS  mandatory
            DESCRIPTION
                "Current J-UR Counter. Underrun is count of jitter buffer underrun events."
            ::= { tdmoeCurrentPerfEntry 6 }

        tdmoeCurrentJit-Buf-Overrun   OBJECT-TYPE
            SYNTAX  INTEGER
            ACCESS  read-only
            STATUS  mandatory
            DESCRIPTION
                "Current J-OR Counter. Overrun is count of jitter buffer overrun events."
            ::= { tdmoeCurrentPerfEntry 7 }


        tdmoeCurr15MinTimeElapsed  OBJECT-TYPE
            SYNTAX  INTEGER
            ACCESS  read-only
            STATUS  mandatory
            DESCRIPTION
                " Current 15-minute time elapsed"
            ::= { tdmoeCurrentPerfEntry 8 }

        tdmoeValid15MinInterval  OBJECT-TYPE
            SYNTAX  INTEGER
            ACCESS  read-only
            STATUS  mandatory
            DESCRIPTION
                " Current 1-day Valid 15-min interval"
            ::= { tdmoeCurrentPerfEntry 9 }


--
--  Interval Performance Table
--

        tdmoeIntervalPerfTable  OBJECT-TYPE
            SYNTAX  SEQUENCE OF TdmoeIntervalPerfEntry
            ACCESS  not-accessible
            STATUS  mandatory
            DESCRIPTION
                "Interval Performance Table"
            ::= { tdmoePerformanceTable 2 }

        tdmoeIntervalPerfEntry  OBJECT-TYPE
            SYNTAX  TdmoeIntervalPerfEntry
            ACCESS  not-accessible
            STATUS  mandatory
            DESCRIPTION
                "Interval performance entry"
            INDEX { tdmoeIntervalPerfSlot , tdmoeIntervalTribIndex , tdmoeIntervalBundleIDIndex , tdmoeIntervalPerfNum }
            ::= { tdmoeIntervalPerfTable 1 }

        TdmoeIntervalPerfEntry  ::= SEQUENCE  {
            tdmoeIntervalPerfSlot       LSSlotID,
            tdmoeIntervalTribIndex      TdmoeTribPort,
            tdmoeIntervalBundleIDIndex  TdmoeBundleId2,
            tdmoeIntervalPerfNum        INTEGER ,
            tdmoeIntervalRx-Lost        INTEGER,
            tdmoeIntervalCell-Lost      INTEGER,
            tdmoeIntervalJit-Buf-Underrun   INTEGER,
            tdmoeIntervalJit-Buf-Overrun    INTEGER,
            tdmoeIntervalHBPriLost         INTEGER,
            tdmoeIntervalHBSecLost        INTEGER

    }

        tdmoeIntervalPerfSlot  OBJECT-TYPE
            SYNTAX  LSSlotID
            ACCESS  read-only
            STATUS  mandatory
            DESCRIPTION
                "slot index"
            ::= { tdmoeIntervalPerfEntry 1 }

        tdmoeIntervalTribIndex  OBJECT-TYPE
            SYNTAX  TdmoeTribPort
            ACCESS  read-only
            STATUS  mandatory
            DESCRIPTION
                "TDMoE perf portIndex"
            ::= { tdmoeIntervalPerfEntry 2 }


        tdmoeIntervalBundleIDIndex   OBJECT-TYPE
            SYNTAX  TdmoeBundleId2
            ACCESS  read-only
            STATUS  mandatory
            DESCRIPTION
                "TDMoE bundle 1-32"
            ::= { tdmoeIntervalPerfEntry 3 }

        tdmoeIntervalPerfNum  OBJECT-TYPE
            SYNTAX  INTEGER (1..96)
            ACCESS  read-only
            STATUS  mandatory
            DESCRIPTION
                "Interval Index"
            ::= { tdmoeIntervalPerfEntry 4 }

        tdmoeIntervalRx-Lost  OBJECT-TYPE
            SYNTAX  INTEGER
            ACCESS  read-only
            STATUS  mandatory
            DESCRIPTION
                " interval rx-lost counter "
            ::= { tdmoeIntervalPerfEntry 5}

        tdmoeIntervalCell-Lost  OBJECT-TYPE
            SYNTAX  INTEGER
            ACCESS  read-only
            STATUS  mandatory
            DESCRIPTION
                " interval cell-lost counter"
            ::= { tdmoeIntervalPerfEntry 6 }

        tdmoeIntervalJit-Buf-Underrun  OBJECT-TYPE
            SYNTAX  INTEGER
            ACCESS  read-only
            STATUS  mandatory
            DESCRIPTION
                " jitter buffer underrun Counter "
            ::= { tdmoeIntervalPerfEntry 7 }

        tdmoeIntervalJit-Buf-Overrun  OBJECT-TYPE
            SYNTAX  INTEGER
            ACCESS  read-only
            STATUS  mandatory
            DESCRIPTION
                " jitter buffer overrun Counter "
            ::= { tdmoeIntervalPerfEntry 8 }

        tdmoeIntervalHBPriLost  OBJECT-TYPE
            SYNTAX  INTEGER
            ACCESS  read-only
            STATUS  mandatory
            DESCRIPTION
                " Primary Heart Beating lost Counter "
            ::= { tdmoeIntervalPerfEntry 9}

        tdmoeIntervalHBSecLost  OBJECT-TYPE
            SYNTAX  INTEGER
            ACCESS  read-only
            STATUS  mandatory
            DESCRIPTION
                "  Secondary Heart Beating lost Counter "
            ::= { tdmoeIntervalPerfEntry 10}

--
--  Total Performance Table
--
        tdmoeTotalPerfTable  OBJECT-TYPE
            SYNTAX  SEQUENCE OF TdmoeTotalPerfEntry
            ACCESS  not-accessible
            STATUS  mandatory
            DESCRIPTION
                "Total Performance Table"
            ::= {  tdmoePerformanceTable 3 }

        tdmoeTotalPerfEntry  OBJECT-TYPE
            SYNTAX  TdmoeTotalPerfEntry
            ACCESS  not-accessible
            STATUS  mandatory
            DESCRIPTION
                "User total performance entry"
            INDEX { tdmoeTotalPerfSlot , tdmoeTotalTribIndex , tdmoeTotalBundleIDIndex }
            ::= { tdmoeTotalPerfTable 1 }

        TdmoeTotalPerfEntry ::= SEQUENCE  {
            tdmoeTotalPerfSlot        LSSlotID,
            tdmoeTotalTribIndex       TdmoeTribPort,
            tdmoeTotalBundleIDIndex   TdmoeBundleId2,
            tdmoeTotalRx-Lost           INTEGER,
            tdmoeTotalCell-Lost         INTEGER,
            tdmoeTotalJit-Buf-Underrun  INTEGER,
            tdmoeTotalJit-Buf-Overrun   INTEGER,
            tdmoeTotalHBPriLost         INTEGER,
            tdmoeTotalHBSecLost        INTEGER

    }

        tdmoeTotalPerfSlot  OBJECT-TYPE
            SYNTAX  LSSlotID
            ACCESS  read-only
            STATUS  mandatory
            DESCRIPTION
                "slot index"
            ::= { tdmoeTotalPerfEntry 1 }

        tdmoeTotalTribIndex  OBJECT-TYPE
            SYNTAX  TdmoeTribPort
            ACCESS  read-only
            STATUS  mandatory
            DESCRIPTION
                "TDMoE perf portIndex"
            ::= { tdmoeTotalPerfEntry 2 }


        tdmoeTotalBundleIDIndex   OBJECT-TYPE
            SYNTAX  TdmoeBundleId2
            ACCESS  read-only
            STATUS  mandatory
            DESCRIPTION
                "TDMoE bundle 1-32"
            ::= { tdmoeTotalPerfEntry 3 }

        tdmoeTotalRx-Lost  OBJECT-TYPE
            SYNTAX  INTEGER
            ACCESS  read-only
            STATUS  mandatory
            DESCRIPTION
                " Rx-lost Counter in current 24 hours"
            ::= { tdmoeTotalPerfEntry 4 }

        tdmoeTotalCell-Lost  OBJECT-TYPE
            SYNTAX  INTEGER
            ACCESS  read-only
            STATUS  mandatory
            DESCRIPTION
                " Cell-lost Counter in current 24 hours"
            ::= { tdmoeTotalPerfEntry 5 }

        tdmoeTotalJit-Buf-Underrun OBJECT-TYPE
            SYNTAX  INTEGER
            ACCESS  read-only
            STATUS  mandatory
            DESCRIPTION
                " Jitter buffer underrun Counter in current 24 hours"
            ::= { tdmoeTotalPerfEntry 6 }

        tdmoeTotalJit-Buf-Overrun  OBJECT-TYPE
            SYNTAX  INTEGER
            ACCESS  read-only
            STATUS  mandatory
            DESCRIPTION
                " Jitter buffer overrun Counter in current 24 hours"
            ::= { tdmoeTotalPerfEntry 7 }

        tdmoeTotalHBPriLost  OBJECT-TYPE
            SYNTAX  INTEGER
            ACCESS  read-only
            STATUS  mandatory
            DESCRIPTION
                " Heart Beating Primary lost Counter in current 24 hours"
            ::= { tdmoeTotalPerfEntry 8}

        tdmoeTotalHBSecLost  OBJECT-TYPE
            SYNTAX  INTEGER
            ACCESS  read-only
            STATUS  mandatory
            DESCRIPTION
                " Heart Beating Secondary lost Counter in current 24 hours"
            ::= { tdmoeTotalPerfEntry 9}

--
-- Seven Days Performance Table
--
        tdmoeSevenDaysPerfTable  OBJECT-TYPE
            SYNTAX  SEQUENCE OF TdmoeSevenDaysPerfEntry
            ACCESS  not-accessible
            STATUS  mandatory
            DESCRIPTION
                "7 Days Performance Table"
            ::= {  tdmoePerformanceTable 4}

        tdmoeSevenDaysPerfEntry  OBJECT-TYPE
            SYNTAX  TdmoeSevenDaysPerfEntry
            ACCESS  not-accessible
            STATUS  mandatory
            DESCRIPTION
                "7 days performance table"
            INDEX { tdmoeDaysPerfSlot , tdmoeDaysTribIndex , tdmoeDaysBundleIDIndex ,
                    tdmoeDaysIndex }
            ::= { tdmoeSevenDaysPerfTable 1 }

        TdmoeSevenDaysPerfEntry ::= SEQUENCE  {
            tdmoeDaysPerfSlot        LSSlotID,
            tdmoeDaysTribIndex       TdmoeTribPort,
            tdmoeDaysBundleIDIndex   TdmoeBundleId2,
            tdmoeDaysIndex              INTEGER,
            tdmoeDateStrIndex           DisplayString,
            tdmoeSevenDaysRx-Lost       INTEGER,
            tdmoeSevenDaysCell-Lost     INTEGER,
            tdmoeSevenDaysJit-Buf-Underrun  INTEGER,
            tdmoeSevenDaysJit-Buf-Overrun   INTEGER,
            tdmoeSevenDaysHBPriLost        INTEGER,
            tdmoeSevenDaysHBSecLost       INTEGER

    }

        tdmoeDaysPerfSlot  OBJECT-TYPE
            SYNTAX  LSSlotID
            ACCESS  read-only
            STATUS  mandatory
            DESCRIPTION
                "slot index"
            ::= { tdmoeSevenDaysPerfEntry 1 }

        tdmoeDaysTribIndex  OBJECT-TYPE
            SYNTAX  TdmoeTribPort
            ACCESS  read-only
            STATUS  mandatory
            DESCRIPTION
                "TDMoE perf portIndex"
            ::= { tdmoeSevenDaysPerfEntry 2 }


        tdmoeDaysBundleIDIndex   OBJECT-TYPE
            SYNTAX  TdmoeBundleId2
            ACCESS  read-only
            STATUS  mandatory
            DESCRIPTION
                "TDMoE bundle 1-32"
            ::= { tdmoeSevenDaysPerfEntry 3 }

        tdmoeDaysIndex  OBJECT-TYPE
            SYNTAX  INTEGER (1..7)
            ACCESS  read-only
            STATUS  mandatory
            DESCRIPTION
                "Seven Days index "
            ::= { tdmoeSevenDaysPerfEntry 4 }

        tdmoeDateStrIndex  OBJECT-TYPE
            SYNTAX  DisplayString (SIZE (0..255) )
            ACCESS  read-only
            STATUS  mandatory
            DESCRIPTION
                "Seven Days String "
            ::= { tdmoeSevenDaysPerfEntry 5 }

        tdmoeSevenDaysRx-Lost  OBJECT-TYPE
            SYNTAX  INTEGER
            ACCESS  read-only
            STATUS  mandatory
            DESCRIPTION
                " Rx-lost Counter in seven days"
            ::= { tdmoeSevenDaysPerfEntry 6}

        tdmoeSevenDaysCell-Lost  OBJECT-TYPE
            SYNTAX  INTEGER
            ACCESS  read-only
            STATUS  mandatory
            DESCRIPTION
                " Cell-lost Counter in seven days"
            ::= { tdmoeSevenDaysPerfEntry 7 }

        tdmoeSevenDaysJit-Buf-Underrun OBJECT-TYPE
            SYNTAX  INTEGER
            ACCESS  read-only
            STATUS  mandatory
            DESCRIPTION
                " jitter buffer underrun  Counter in seven days"
            ::= { tdmoeSevenDaysPerfEntry 8 }

        tdmoeSevenDaysJit-Buf-Overrun  OBJECT-TYPE
            SYNTAX  INTEGER
            ACCESS  read-only
            STATUS  mandatory
            DESCRIPTION
                " jitter buffer overrun  Counter in seven days"
            ::= { tdmoeSevenDaysPerfEntry 9 }

        tdmoeSevenDaysHBPriLost  OBJECT-TYPE
            SYNTAX  INTEGER
            ACCESS  read-only
            STATUS  mandatory
            DESCRIPTION
                " Heart Beating Primary  lost  Counter in seven days"
            ::= { tdmoeSevenDaysPerfEntry 10}

        tdmoeSevenDaysHBSecLost  OBJECT-TYPE
            SYNTAX  INTEGER
            ACCESS  read-only
            STATUS  mandatory
            DESCRIPTION
                " Heart Beating Secondary lost Counter in seven days"
            ::= { tdmoeSevenDaysPerfEntry 11}




--  Time Slot Ip Map Table

    timeSlotIpMapTable  OBJECT IDENTIFIER ::= { tdmoe-card   6}

        bundleAllocationInfo  OBJECT-TYPE
            SYNTAX  SEQUENCE OF BundleAllocationInfoEntry
            ACCESS  not-accessible
            STATUS  mandatory
            DESCRIPTION
                "Time Slot Ip Map table."
            ::= { timeSlotIpMapTable 1 }

        bundleAllocationInfoEntry  OBJECT-TYPE
            SYNTAX  BundleAllocationInfoEntry
            ACCESS  not-accessible
            STATUS  mandatory
            DESCRIPTION
                "An entry in Time Slot Ip Map table."
            INDEX { tdmoeMapSlotIndex }
            ::= { bundleAllocationInfo 1 }

        BundleAllocationInfoEntry ::= SEQUENCE  {
            tdmoeMapSlotIndex           LSSlotID,
            tdmoeMapBundleAllocationMode    INTEGER
        }

        tdmoeMapSlotIndex  OBJECT-TYPE
            SYNTAX  LSSlotID
            ACCESS  read-only
            STATUS  mandatory
            DESCRIPTION
                "slot index"
            ::= { bundleAllocationInfoEntry 1 }

        tdmoeMapBundleAllocationMode  OBJECT-TYPE
            SYNTAX  INTEGER  {
                    mode-16 (1),
                    mode-32 (2)
                }
            ACCESS  read-only
            STATUS  mandatory
            DESCRIPTION
                "slot index"
            ::= { bundleAllocationInfoEntry 2 }


        timeSlotAssignInfo  OBJECT-TYPE
            SYNTAX  SEQUENCE OF TimeSlotAssignInfoEntry
            ACCESS  not-accessible
            STATUS  mandatory
            DESCRIPTION
                "Time Slot Ip Map table."
            ::= { timeSlotIpMapTable 2 }

        timeSlotAssignInfoEntry  OBJECT-TYPE
            SYNTAX  TimeSlotAssignInfoEntry
            ACCESS  not-accessible
            STATUS  mandatory
            DESCRIPTION
                "An entry in Time Slot Ip Map table."
            INDEX { tdmoeMapSlot , tdmoeMapTribIndex ,
                    tdmoeMapTsIndex }
            ::= { timeSlotAssignInfo 1 }

        TimeSlotAssignInfoEntry ::= SEQUENCE  {
            tdmoeMapSlot                LSSlotID,
            tdmoeMapTribIndex           TdmoeTribPort,
            tdmoeMapTsIndex             INTEGER,
            tdmoeMapBundleID            TdmoeBundleId
        }

        tdmoeMapSlot  OBJECT-TYPE
            SYNTAX  LSSlotID
            ACCESS  read-only
            STATUS  mandatory
            DESCRIPTION
                "slot index"
            ::= { timeSlotAssignInfoEntry 1 }

        tdmoeMapTribIndex  OBJECT-TYPE
            SYNTAX  TdmoeTribPort
            ACCESS  read-only
            STATUS  mandatory
            DESCRIPTION
                "TDMoE  portIndex"
            ::= { timeSlotAssignInfoEntry 2 }

        tdmoeMapTsIndex  OBJECT-TYPE
            SYNTAX  INTEGER (0..31)
            ACCESS  read-only
            STATUS  mandatory
            DESCRIPTION
                "Time slot index."
            ::= { timeSlotAssignInfoEntry 3 }


        tdmoeMapBundleID   OBJECT-TYPE
            SYNTAX   TdmoeBundleId
            ACCESS  read-only
            STATUS  mandatory
            DESCRIPTION
                "TDMoE bundle 0-31"
            ::= { timeSlotAssignInfoEntry 4 }



        bundleIpinfo   OBJECT-TYPE
            SYNTAX  SEQUENCE OF BundleIPInfoEntry
            ACCESS  not-accessible
            STATUS  mandatory
            DESCRIPTION
                "Time Slot Ip Map table."
            ::= { timeSlotIpMapTable 3 }

        bundleIPInfoEntry     OBJECT-TYPE
            SYNTAX  BundleIPInfoEntry
            ACCESS  not-accessible
            STATUS  mandatory
            DESCRIPTION
                "timeSlotIP Entry."
            INDEX { tdmoeBundleInfoSlotIndex }
            ::= { bundleIpinfo 1 }

        BundleIPInfoEntry ::= SEQUENCE {
            tdmoeBundleInfoSlotIndex    LSSlotID,
            tdmoeBundleInfoSrcIpAddress IpAddress,
            tdmoeBundleInfoSubnetMask   IpAddress,
            tdmoeBundleInfoGatewayIpAddr IpAddress,
            toeInfoPriMacAddr            DisplayString,
            toeInfoSecSrcIpAddr IpAddress,
            toeInfoSecSubnetMask   IpAddress,
            toeInfoSecGatewayIpAddr IpAddress
        }

        tdmoeBundleInfoSlotIndex    OBJECT-TYPE
            SYNTAX  LSSlotID
            ACCESS  read-only
            STATUS  mandatory
            DESCRIPTION
                "slot index"
            ::= { bundleIPInfoEntry 1 }

        tdmoeBundleInfoSrcIpAddress  OBJECT-TYPE
            SYNTAX  IpAddress
            ACCESS  read-only
            STATUS  mandatory
            DESCRIPTION
                "bundle Source IP Address"
            ::= { bundleIPInfoEntry 2 }

        tdmoeBundleInfoSubnetMask  OBJECT-TYPE
            SYNTAX  IpAddress
            ACCESS  read-only
            STATUS  mandatory
            DESCRIPTION
                "bundle Subnet Mask"
            ::= { bundleIPInfoEntry 3 }


        tdmoeBundleInfoGatewayIpAddr  OBJECT-TYPE
            SYNTAX  IpAddress
            ACCESS  read-only
            STATUS  mandatory
            DESCRIPTION
                "bundle Gateway IP"
            ::= { bundleIPInfoEntry 4 }

        toeInfoPriMacAddr  OBJECT-TYPE
            SYNTAX  DisplayString (SIZE (0..20))
            ACCESS  read-only
            STATUS  mandatory
            DESCRIPTION
                "Primary mac address "
            ::= { bundleIPInfoEntry 5}

        toeInfoSecSrcIpAddr OBJECT-TYPE
            SYNTAX  IpAddress
            ACCESS  read-only
            STATUS  mandatory
            DESCRIPTION
                "bundle Source IP Address"
            ::= { bundleIPInfoEntry 6}

        toeInfoSecSubnetMask  OBJECT-TYPE
            SYNTAX  IpAddress
            ACCESS  read-only
            STATUS  mandatory
            DESCRIPTION
                "bundle Subnet Mask"
            ::= { bundleIPInfoEntry 7 }


        toeInfoSecGatewayIpAddr  OBJECT-TYPE
            SYNTAX  IpAddress
            ACCESS  read-only
            STATUS  mandatory
            DESCRIPTION
                "bundle Gateway IP"
            ::= { bundleIPInfoEntry 8 }


        timeSlotIpInfo  OBJECT-TYPE
            SYNTAX  SEQUENCE OF TimeSlotIpInfoEntry
            ACCESS  not-accessible
            STATUS  mandatory
            DESCRIPTION
                "Time Slot Ip Map table."
            ::= { timeSlotIpMapTable 4 }

        timeSlotIpInfoEntry  OBJECT-TYPE
            SYNTAX  TimeSlotIpInfoEntry
            ACCESS  not-accessible
            STATUS  mandatory
            DESCRIPTION
                "An entry in Time Slot Ip Map table."
            INDEX { tdmoeMapTimeSlot , tdmoeMapTimeTrib ,
                    tdmoeMapBundleIDIndex }
            ::= { timeSlotIpInfo 1 }

        TimeSlotIpInfoEntry ::= SEQUENCE  {
            tdmoeMapTimeSlot            LSSlotID,
            tdmoeMapTimeTrib            TdmoeTribPort,
            tdmoeMapBundleIDIndex       TdmoeBundleId2,
            tdmoeMapSrcUdpPortNumber    INTEGER,
            tdmoeMapFormat              INTEGER,
            tdmoeMapCellInBundle        INTEGER,
            tdmoeMapJit-Tolerance       INTEGER,
            tdmoeMapJit-Buffer          INTEGER,
            tdmoeMapDestIPAddress       DisplayString,
            tdmoeMapTos                 INTEGER,
            tdmoeMapStratum             INTEGER,
            tdmoeMapVLAN                INTEGER,
            tdmoeMapCVLANId             INTEGER,
            tdmoeMapCVLANPriority       INTEGER,
            tdmoeMapSVLANId             INTEGER,
            tdmoeMapSVLANPriority       INTEGER,
            tdmoeMapBuType        INTEGER,
            tdmoeMapEcid        INTEGER,
            tdmoeMapDestMACAddr       DisplayString,
            toeMapBP                              INTEGER,
            toeMapBPMS                       INTEGER,
            toeMapBPMode                       INTEGER,
            toeMapBPSecUdpPW                    INTEGER,
            toeMapBPPriUdpHB                    INTEGER,
            toeMapBPSecUdpHB                    INTEGER,
            toeMapBPSecIP                   IpAddress,
            toeMapBPCVLANId                     INTEGER,
            toeMapBPCVLANPriority          INTEGER,
            toeMapBPSVLANId                     INTEGER,
            toeMapBPSVLANPriority        INTEGER
        }

        tdmoeMapTimeSlot  OBJECT-TYPE
            SYNTAX  LSSlotID
            ACCESS  read-only
            STATUS  mandatory
            DESCRIPTION
                "slot index"
            ::= { timeSlotIpInfoEntry 1 }

        tdmoeMapTimeTrib  OBJECT-TYPE
            SYNTAX  TdmoeTribPort
            ACCESS  read-only
            STATUS  mandatory
            DESCRIPTION
                "TDMoE  portIndex"
            ::= { timeSlotIpInfoEntry 2 }

        tdmoeMapBundleIDIndex  OBJECT-TYPE
            SYNTAX  TdmoeBundleId2
            ACCESS  read-only
            STATUS  mandatory
            DESCRIPTION
                "Bundle ID"
            ::= { timeSlotIpInfoEntry 3 }

        tdmoeMapSrcUdpPortNumber  OBJECT-TYPE
            SYNTAX  INTEGER
            ACCESS  read-only
            STATUS  mandatory
            DESCRIPTION
                "Ip Map Udp Num"
            ::= { timeSlotIpInfoEntry 4 }

        tdmoeMapFormat  OBJECT-TYPE
            SYNTAX   INTEGER {
                    aal1(1),
                    cesopsn(2),
                    satop(3)
                }
            ACCESS  read-only
            STATUS  mandatory
            DESCRIPTION
                "Ip Map Format"
            ::= { timeSlotIpInfoEntry 5 }

        tdmoeMapCellInBundle  OBJECT-TYPE
            SYNTAX  INTEGER
            ACCESS  read-only
            STATUS  mandatory
            DESCRIPTION
                "Ip Map Cells Num"
            ::= { timeSlotIpInfoEntry 6 }

        tdmoeMapJit-Tolerance  OBJECT-TYPE
            SYNTAX  INTEGER
            ACCESS  read-only
            STATUS  mandatory
            DESCRIPTION
                "Ip Map Jitter Delay"
            ::= { timeSlotIpInfoEntry 7 }

        tdmoeMapJit-Buffer  OBJECT-TYPE
            SYNTAX  INTEGER
            ACCESS  read-only
            STATUS  mandatory
            DESCRIPTION
                "Ip Map Jitter Size"
            ::= { timeSlotIpInfoEntry 8 }

        tdmoeMapDestIPAddress  OBJECT-TYPE
            SYNTAX  DisplayString (SIZE (0..40))
            ACCESS  read-only
            STATUS  mandatory
            DESCRIPTION
                "Ip Map Address"
            ::= { timeSlotIpInfoEntry 9 }

        tdmoeMapTos  OBJECT-TYPE
            SYNTAX  INTEGER
            ACCESS  read-only
            STATUS  mandatory
            DESCRIPTION
                "TOS Number"
            ::= { timeSlotIpInfoEntry 10 }

        tdmoeMapStratum  OBJECT-TYPE
            SYNTAX  INTEGER {
                    stratum1(1),
                    stratum2(2),
                    stratum3(3),
                    stratum3e(4),
                    stratum4(5)
                }
            ACCESS  read-only
            STATUS  mandatory
            DESCRIPTION
                "Stratum Setup"
            ::= { timeSlotIpInfoEntry 11 }

        tdmoeMapVLAN  OBJECT-TYPE
            SYNTAX  INTEGER {
                    off(1),
                    cvlan(2),
                    svlan(3)
                }
            ACCESS  read-only
            STATUS  mandatory
            DESCRIPTION
                "VLAN switch"
            ::= { timeSlotIpInfoEntry 12 }

        tdmoeMapCVLANId  OBJECT-TYPE
            SYNTAX  INTEGER
            ACCESS  read-only
            STATUS  mandatory
            DESCRIPTION
                "customer VLAN ID"
            ::= { timeSlotIpInfoEntry 13 }

        tdmoeMapCVLANPriority  OBJECT-TYPE
            SYNTAX  INTEGER {
                    p-0(1),
                    p-1(2),
                    p-2(3),
                    p-3(4),
                    p-4(5),
                    p-5(6),
                    p-6(7),
                    p-7(8)
                }
            ACCESS  read-only
            STATUS  mandatory
            DESCRIPTION
                "customer VLAN Priority"
            ::= { timeSlotIpInfoEntry 14 }

        tdmoeMapSVLANId  OBJECT-TYPE
            SYNTAX  INTEGER
            ACCESS  read-only
            STATUS  mandatory
            DESCRIPTION
                "provider VLAN ID"
            ::= { timeSlotIpInfoEntry 15 }

        tdmoeMapSVLANPriority  OBJECT-TYPE
            SYNTAX  INTEGER {
                    p-0(1),
                    p-1(2),
                    p-2(3),
                    p-3(4),
                    p-4(5),
                    p-5(6),
                    p-6(7),
                    p-7(8)
                }
            ACCESS  read-only
            STATUS  mandatory
            DESCRIPTION
                "provider VLAN Priority"
            ::= { timeSlotIpInfoEntry 16 }

        tdmoeMapBuType  OBJECT-TYPE
            SYNTAX  INTEGER {
                    ip(1),
                    cesoEth(2)
                }
            ACCESS  read-only
            STATUS  mandatory
            DESCRIPTION
                "BuType"
            ::= { timeSlotIpInfoEntry 17 }

        tdmoeMapEcid  OBJECT-TYPE
            SYNTAX  INTEGER
            ACCESS  read-only
            STATUS  mandatory
            DESCRIPTION
                "ECID"
            ::= { timeSlotIpInfoEntry 18 }

        tdmoeMapDestMACAddr  OBJECT-TYPE
            SYNTAX  DisplayString (SIZE (0..40))
            ACCESS  read-only
            STATUS  mandatory
            DESCRIPTION
                "Ip Map Address"
            ::= { timeSlotIpInfoEntry 19 }

        toeMapBP OBJECT-TYPE
            SYNTAX  INTEGER {
                    disable(1),
                    enable(2)
                }
            ACCESS  read-only
            STATUS  mandatory
            DESCRIPTION
                "bundle protection enable"
            ::= { timeSlotIpInfoEntry 20}

        toeMapBPMS OBJECT-TYPE
            SYNTAX  INTEGER {
                    master(1),
                    slave(2)
                }
            ACCESS read-only
            STATUS  mandatory
            DESCRIPTION
                "Master or Slave"
            ::= { timeSlotIpInfoEntry 21}

        toeMapBPMode OBJECT-TYPE
            SYNTAX  INTEGER {
                    non-Revertible(1),
                    revertible(2)
                }
            ACCESS read-only
            STATUS  mandatory
            DESCRIPTION
                "Revertible"
            ::= { timeSlotIpInfoEntry 22}

        toeMapBPSecUdpPW  OBJECT-TYPE
            SYNTAX  INTEGER (1..65535)
            ACCESS  read-only
            STATUS  mandatory
            DESCRIPTION
                "Secondary PW UDP port"
            ::= { timeSlotIpInfoEntry 23}

        toeMapBPPriUdpHB  OBJECT-TYPE
            SYNTAX  INTEGER (1..65535)
            ACCESS  read-only
            STATUS  mandatory
            DESCRIPTION
                "Primary HB UDP port"
            ::= { timeSlotIpInfoEntry 24}

        toeMapBPSecUdpHB  OBJECT-TYPE
            SYNTAX  INTEGER (1..65535)
            ACCESS read-only
            STATUS  mandatory
            DESCRIPTION
                "Secondary HB UDP port"
            ::= { timeSlotIpInfoEntry 25}

        toeMapBPSecIP  OBJECT-TYPE
            SYNTAX  IpAddress
            ACCESS  read-only
            STATUS  mandatory
            DESCRIPTION
                "Secodary Destination IP"
            ::= { timeSlotIpInfoEntry 26}

        toeMapBPCVLANId  OBJECT-TYPE
            SYNTAX  INTEGER (1..4094)
            ACCESS read-only
            STATUS  mandatory
            DESCRIPTION
                "customer VLAN ID"
            ::= { timeSlotIpInfoEntry 27}

        toeMapBPCVLANPriority  OBJECT-TYPE
            SYNTAX  INTEGER {
                    p-0(1),
                    p-1(2),
                    p-2(3),
                    p-3(4),
                    p-4(5),
                    p-5(6),
                    p-6(7),
                    p-7(8)
                }
            ACCESS  read-only
            STATUS  mandatory
            DESCRIPTION
                "customer VLAN Priority"
            ::= { timeSlotIpInfoEntry 28}

        toeMapBPSVLANId  OBJECT-TYPE
            SYNTAX  INTEGER (1..4094)
            ACCESS  read-only
            STATUS  mandatory
            DESCRIPTION
                "provider VLAN ID"
            ::= {timeSlotIpInfoEntry 29}

        toeMapBPSVLANPriority  OBJECT-TYPE
            SYNTAX  INTEGER {
                    p-0(1),
                    p-1(2),
                    p-2(3),
                    p-3(4),
                    p-4(5),
                    p-5(6),
                    p-6(7),
                    p-7(8)
                }
            ACCESS  read-only
            STATUS  mandatory
            DESCRIPTION
                "provider VLAN Priority"
            ::= { timeSlotIpInfoEntry 30}


--  Bundle Delay/Size Info

        toeBundleDelayInfoTable     OBJECT-TYPE
            SYNTAX  SEQUENCE OF  ToeBundleDelayInfoEntry
            ACCESS  not-accessible
            STATUS  mandatory
            DESCRIPTION
                "Bundle Delay Info."
            ::= { timeSlotIpMapTable 5 }

        toeBundleDelayInfoEntry       OBJECT-TYPE
            SYNTAX  ToeBundleDelayInfoEntry
            ACCESS  not-accessible
            STATUS  mandatory
            DESCRIPTION
                "Bundle Delay Info Entry"
            INDEX { toeBDInfoSlot , toeBDInfoPort , toeBDInfoBundleID }
            ::= {toeBundleDelayInfoTable 1 }

        ToeBundleDelayInfoEntry ::= SEQUENCE  {
            toeBDInfoSlot       LSSlotID,
            toeBDInfoPort       TdmoeTribPort,
            toeBDInfoBundleID   TdmoeBundleId2,
            toeBDInfoFormat     INTEGER,
            toeBDInfoUdpNumber  INTEGER,
            toeBDInfoPktPerSec  INTEGER,
            toeBDInfoPropDelay  DisplayString,
            toeBDInfoPktSize    DisplayString,
            toeBDInfoOverHead   DisplayString
        }

        toeBDInfoSlot   OBJECT-TYPE
            SYNTAX  LSSlotID
            ACCESS  read-only
            STATUS  mandatory
            DESCRIPTION
                "Slot ID"
            ::= {toeBundleDelayInfoEntry 1 }


        toeBDInfoPort  OBJECT-TYPE
            SYNTAX  TdmoeTribPort
            ACCESS  read-only
            STATUS  mandatory
            DESCRIPTION
                "Bundle ID"
            ::= { toeBundleDelayInfoEntry 2 }

        toeBDInfoBundleID  OBJECT-TYPE
            SYNTAX  TdmoeBundleId2
            ACCESS  read-only
            STATUS  mandatory
            DESCRIPTION
                "Bundle ID"
            ::= { toeBundleDelayInfoEntry 3 }

        toeBDInfoFormat  OBJECT-TYPE
            SYNTAX   INTEGER {
                    aal1(1),
                    cesopsn(2),
                    satop(3)
                }
            ACCESS  read-only
            STATUS  mandatory
            DESCRIPTION
                "Ip Map Format"
            ::= {toeBundleDelayInfoEntry 4 }

        toeBDInfoUdpNumber  OBJECT-TYPE
            SYNTAX  INTEGER
            ACCESS  read-only
            STATUS  mandatory
            DESCRIPTION
                "Ip Map Udp Num"
            ::= { toeBundleDelayInfoEntry 5 }

        toeBDInfoPktPerSec  OBJECT-TYPE
            SYNTAX  INTEGER
            ACCESS  read-only
            STATUS  mandatory
            DESCRIPTION
                "Ip Map Cells Num"
            ::= {toeBundleDelayInfoEntry 6 }

        toeBDInfoPropDelay OBJECT-TYPE
            SYNTAX  DisplayString (SIZE (0..30))
            ACCESS  read-only
            STATUS  mandatory
            DESCRIPTION
                "Propagation Delay"
            ::= { toeBundleDelayInfoEntry  7}

        toeBDInfoPktSize OBJECT-TYPE
            SYNTAX  DisplayString (SIZE (0..30))
            ACCESS  read-only
            STATUS  mandatory
            DESCRIPTION
                "Packet Size"
            ::= { toeBundleDelayInfoEntry  8}

        toeBDInfoOverHead OBJECT-TYPE
            SYNTAX  DisplayString (SIZE (0..30))
            ACCESS  read-only
            STATUS  mandatory
            DESCRIPTION
                "OverHead"
            ::= { toeBundleDelayInfoEntry  9}

--  Bundle Protection Status

        toeProtectInfoTable     OBJECT-TYPE
            SYNTAX  SEQUENCE OF  ToeProtectInfoEntry
            ACCESS  not-accessible
            STATUS  mandatory
            DESCRIPTION
                "Bundle Delay Info."
            ::= { timeSlotIpMapTable 6 }

        toeProtectInfoEntry       OBJECT-TYPE
            SYNTAX  ToeProtectInfoEntry
            ACCESS  not-accessible
            STATUS  mandatory
            DESCRIPTION
                "Bundle Delay Info Entry"
            INDEX { toeBPInfoSlot , toeBPInfoPort , toeBPInfoBundleID }
            ::= {toeProtectInfoTable 1 }

        ToeProtectInfoEntry ::= SEQUENCE  {
            toeBPInfoSlot       LSSlotID,
            toeBPInfoPort       TdmoeTribPort,
            toeBPInfoBundleID   TdmoeBundleId2,
            toeBPInfoPriHB         INTEGER,
            toeBPInfoPriState     INTEGER,
            toeBPInfoSecHB       INTEGER,
            toeBPInfoSecState    INTEGER,
            toeBPInfoBDStatus       INTEGER,
            toeBPInfoPriLost       INTEGER,
            toeBPInfoSecLost       INTEGER

    }

        toeBPInfoSlot   OBJECT-TYPE
            SYNTAX  LSSlotID
            ACCESS  read-only
            STATUS  mandatory
            DESCRIPTION
                "Slot ID"
            ::= {toeProtectInfoEntry 1 }


        toeBPInfoPort  OBJECT-TYPE
            SYNTAX  TdmoeTribPort
            ACCESS  read-only
            STATUS  mandatory
            DESCRIPTION
                "Bundle ID"
            ::= { toeProtectInfoEntry 2 }

        toeBPInfoBundleID  OBJECT-TYPE
            SYNTAX  TdmoeBundleId2
            ACCESS  read-only
            STATUS  mandatory
            DESCRIPTION
                "Bundle ID"
            ::= { toeProtectInfoEntry 3 }

        toeBPInfoPriHB OBJECT-TYPE
            SYNTAX  INTEGER {
                    down(1),
                    ok(2)
                }
            ACCESS  read-only
            STATUS  mandatory
            DESCRIPTION
                "Primary HB status"
            ::= { toeProtectInfoEntry 4 }

        toeBPInfoPriState OBJECT-TYPE
            SYNTAX  INTEGER {
                    working(1),
                    standby(2)
                }
            ACCESS  read-only
            STATUS  mandatory
            DESCRIPTION
                "Primary State"
            ::= { toeProtectInfoEntry 5 }

        toeBPInfoSecHB OBJECT-TYPE
            SYNTAX  INTEGER {
                    down(1),
                    ok(2)
                }
            ACCESS  read-only
            STATUS  mandatory
            DESCRIPTION
                "Secondary HB Status"
            ::= { toeProtectInfoEntry 6 }

        toeBPInfoSecState OBJECT-TYPE
            SYNTAX  INTEGER{
                    working(1),
                    standby(2)
                }
            ACCESS  read-only
            STATUS  mandatory
            DESCRIPTION
                "Secondary State"
            ::= { toeProtectInfoEntry 7 }

        toeBPInfoBDStatus OBJECT-TYPE
            SYNTAX  INTEGER{
                    inactive(1),
                    active(2)
                }
            ACCESS  read-only
            STATUS  mandatory
            DESCRIPTION
                "Bundle Status"
            ::= { toeProtectInfoEntry 8 }

        toeBPInfoPriLost  OBJECT-TYPE
            SYNTAX  INTEGER
            ACCESS  read-only
            STATUS  mandatory
            DESCRIPTION
                "Primary HB lost Counter"
            ::= { toeProtectInfoEntry 9 }

        toeBPInfoSecLost  OBJECT-TYPE
            SYNTAX  INTEGER
            ACCESS  read-only
            STATUS  mandatory
            DESCRIPTION
                "Secondary HB lost Counter"
            ::= { toeProtectInfoEntry 10}

--
-- Loopback table
--
    tdmoeDiagTable          OBJECT IDENTIFIER ::= { tdmoe-card  7}

        tdmoeDiagControlTable  OBJECT-TYPE
            SYNTAX  SEQUENCE OF TdmoeDiagControlEntry
            ACCESS  not-accessible
            STATUS  mandatory
            DESCRIPTION
                "Diagonal Control Table"
            ::= { tdmoeDiagTable 1}

        tdmoeDiagControlEntry  OBJECT-TYPE
            SYNTAX  TdmoeDiagControlEntry
            ACCESS  not-accessible
            STATUS  mandatory
            DESCRIPTION
                "Diagonal Control entry"
            INDEX { tdmoeDiagSlotIndex , tdmoeDiagPort }
            ::= { tdmoeDiagControlTable 1 }

        TdmoeDiagControlEntry ::= SEQUENCE {
            tdmoeDiagSlotIndex          LSSlotID,
            tdmoeDiagPort                  TdmoeTribPort,
            tdmoeLoopBack                INTEGER
        }

        tdmoeDiagSlotIndex  OBJECT-TYPE
            SYNTAX  LSSlotID
            ACCESS  read-only
            STATUS  mandatory
            DESCRIPTION
                "Slot 1~12, total 12 slots."
            ::= { tdmoeDiagControlEntry 1 }

        tdmoeDiagPort   OBJECT-TYPE
            SYNTAX  TdmoeTribPort
            ACCESS  read-only
            STATUS  mandatory
            DESCRIPTION
                "trib port1~4 "
            ::= { tdmoeDiagControlEntry 2 }


        tdmoeLoopBack   OBJECT-TYPE
            SYNTAX  INTEGER {
                    off(1),
                    llb(4),
                    local(5)
                }
            ACCESS  read-write
            STATUS  mandatory
            DESCRIPTION
                "loopback type-plb:payload loopback; llb:line loopback"
            ::= { tdmoeDiagControlEntry 3}


        tdmoeDiagMapTable  OBJECT-TYPE
            SYNTAX  SEQUENCE OF TdmoeDiagMapEntry
            ACCESS  not-accessible
            STATUS  mandatory
            DESCRIPTION
                "Diagonal Map Table"
            ::= { tdmoeDiagTable 2}

        tdmoeDiagMapEntry  OBJECT-TYPE
            SYNTAX  TdmoeDiagMapEntry
            ACCESS  not-accessible
            STATUS  mandatory
            DESCRIPTION
                "Diagonal Control entry"
            INDEX { tdmoeDiagMapSlotIndex , tdmoeDiagPortIndex , tdmoeDiagMapIndex }
            ::= { tdmoeDiagMapTable 1 }

        TdmoeDiagMapEntry ::= SEQUENCE {
            tdmoeDiagMapSlotIndex       LSSlotID,
            tdmoeDiagPortIndex          TdmoeTribPort,
            tdmoeDiagMapIndex           INTEGER,
            tdmoeDiagStatus             INTEGER
        }

        tdmoeDiagMapSlotIndex  OBJECT-TYPE
            SYNTAX  LSSlotID
            ACCESS  read-only
            STATUS  mandatory
            DESCRIPTION
                "Slot 1~12, total 12 slots."
            ::= { tdmoeDiagMapEntry 1 }

        tdmoeDiagPortIndex    OBJECT-TYPE
            SYNTAX  TdmoeTribPort
            ACCESS  read-only
            STATUS  mandatory
            DESCRIPTION
                "trib port1~4 "
            ::= { tdmoeDiagMapEntry 2 }

        tdmoeDiagMapIndex      OBJECT-TYPE
            SYNTAX  INTEGER (1..32)
            ACCESS  read-only
            STATUS  mandatory
            DESCRIPTION
                "map channel 1~32 "
            ::= { tdmoeDiagMapEntry 3}

        tdmoeDiagStatus      OBJECT-TYPE
            SYNTAX  INTEGER {
                    idle(1),
                    used(2)
                }
            ACCESS  read-write
            STATUS  mandatory
            DESCRIPTION
                "map channel status "
            ::= { tdmoeDiagMapEntry 4}

--
-- Transmission delay measurement table
--

        toeRoundTripDelayTable     OBJECT-TYPE
            SYNTAX  SEQUENCE OF  ToeRoundTripDelayEntry
            ACCESS  not-accessible
            STATUS  mandatory
            DESCRIPTION
                "Round Trip Delay"
            ::= {  tdmoeDiagTable 3 }

        toeRoundTripDelayEntry       OBJECT-TYPE
            SYNTAX  ToeRoundTripDelayEntry
            ACCESS  not-accessible
            STATUS  mandatory
            DESCRIPTION
                "Bundle Delay Info Entry"
            INDEX { toeRoundTripSlotIndex , toeRoundTripPortIndex ,
                    toeRoundTripBundleID }
            ::= {toeRoundTripDelayTable 1 }

        ToeRoundTripDelayEntry ::= SEQUENCE  {
            toeRoundTripSlotIndex       LSSlotID,
            toeRoundTripPortIndex                      TdmoeTribPort,
            toeRoundTripBundleID               TdmoeBundleId2,
            toeRoundTripPeriod                    INTEGER,
            toeRoundTripEnable                   INTEGER
        }

        toeRoundTripSlotIndex  OBJECT-TYPE
            SYNTAX  LSSlotID
            ACCESS  read-only
            STATUS  mandatory
            DESCRIPTION
                "Slot 1~12, total 12 slots."
            ::= { toeRoundTripDelayEntry 1 }

        toeRoundTripPortIndex    OBJECT-TYPE
            SYNTAX  TdmoeTribPort
            ACCESS  read-only
            STATUS  mandatory
            DESCRIPTION
                "trib port 1~4 "
            ::= { toeRoundTripDelayEntry 2 }

        toeRoundTripBundleID      OBJECT-TYPE
            SYNTAX  TdmoeBundleId2
            ACCESS  read-only
            STATUS  mandatory
            DESCRIPTION
                "bundle ID "
            ::= { toeRoundTripDelayEntry 3}

        toeRoundTripPeriod  OBJECT-TYPE
--            SYNTAX  INTEGER (1..600)
            SYNTAX  INTEGER (0..600)
            ACCESS  read-write
            STATUS  mandatory
            DESCRIPTION
                "Period time for transmission delay measurement (second) "
            ::= { toeRoundTripDelayEntry 4 }

        toeRoundTripEnable  OBJECT-TYPE
            SYNTAX  INTEGER {
                    enable(1),
                    disable(2)
                }
            ACCESS  read-write
            STATUS  mandatory
            DESCRIPTION
                "Ethernet transmission time delay measurement control "
            ::= { toeRoundTripDelayEntry 5 }

--
--  Bundle Statistics Table
--

    tdmoeStatTable   OBJECT IDENTIFIER ::= { tdmoe-card   8}

        tdmoeBundleStatTable  OBJECT-TYPE
            SYNTAX  SEQUENCE OF TdmoeBundleStatEntry
            ACCESS  not-accessible
            STATUS  mandatory
            DESCRIPTION
                "bundle statistics table"
            ::= {tdmoeStatTable  1}

        tdmoeBundleStatEntry  OBJECT-TYPE
            SYNTAX  TdmoeBundleStatEntry
            ACCESS  not-accessible
            STATUS  mandatory
            DESCRIPTION
                "An entry in bundle statistics table."
            INDEX { bundleSlotIndex , bundleTribIndex ,
                    bundleBundleIDIndex }
            ::= { tdmoeBundleStatTable 1 }

        TdmoeBundleStatEntry ::= SEQUENCE  {
            bundleSlotIndex             LSSlotID,
            bundleTribIndex             TdmoeTribPort,
            bundleBundleIDIndex         TdmoeBundleId2,
            bundleJit-Buf-Underrun      Counter,
            bundleJit-Buf-Overrun       Counter,
            bundleMinJitBuffer          Counter,
            bundleMaxJitBuffer          Counter,
            bundleRx-Lost               Counter,
            bundleRx-Good               Counter,
            bundleTx-Good               Counter,
            bundleJumped                 Counter,
            bundleRe-Oreder           Counter,
            toeBundleClear                   INTEGER
        }

        bundleSlotIndex  OBJECT-TYPE
            SYNTAX  LSSlotID
            ACCESS  read-only
            STATUS  mandatory
            DESCRIPTION
                "slot index"
            ::= { tdmoeBundleStatEntry 1 }

        bundleTribIndex  OBJECT-TYPE
            SYNTAX  TdmoeTribPort
            ACCESS  read-only
            STATUS  mandatory
            DESCRIPTION
                "TDMoE alarm portIndex"
            ::= { tdmoeBundleStatEntry 2 }

        bundleBundleIDIndex   OBJECT-TYPE
            SYNTAX   TdmoeBundleId2
            ACCESS  read-only
            STATUS  mandatory
            DESCRIPTION
                "TDMoE bundle 1-32"
            ::= { tdmoeBundleStatEntry 3 }

        bundleJit-Buf-Underrun  OBJECT-TYPE
            SYNTAX  Counter
            ACCESS  read-only
            STATUS  mandatory
            DESCRIPTION
                "TXC Byte Received"
            ::= { tdmoeBundleStatEntry 4 }

        bundleJit-Buf-Overrun  OBJECT-TYPE
            SYNTAX  Counter
            ACCESS  read-only
            STATUS  mandatory
            DESCRIPTION
                "TXC Byte Transmitted"
            ::= { tdmoeBundleStatEntry 5 }

        bundleMinJitBuffer  OBJECT-TYPE
            SYNTAX  Counter
            ACCESS  read-only
            STATUS  mandatory
            DESCRIPTION
                "TXC Classified Packets Received"
            ::= { tdmoeBundleStatEntry 6 }

        bundleMaxJitBuffer   OBJECT-TYPE
            SYNTAX  Counter
            ACCESS  read-only
            STATUS  mandatory
            DESCRIPTION
                "Wan Byte Received"
            ::= { tdmoeBundleStatEntry 7 }

        bundleRx-Lost  OBJECT-TYPE
            SYNTAX  Counter
            ACCESS  read-only
            STATUS  mandatory
            DESCRIPTION
                "Wan Byte Transmitted"
            ::= { tdmoeBundleStatEntry 8 }

        bundleRx-Good  OBJECT-TYPE
            SYNTAX  Counter
            ACCESS  read-only
            STATUS  mandatory
            DESCRIPTION
                "Wan Packets Received"
            ::= { tdmoeBundleStatEntry 9}

        bundleTx-Good   OBJECT-TYPE
            SYNTAX  Counter
            ACCESS  read-only
            STATUS  mandatory
            DESCRIPTION
                "Wan Packets Tranmitted"
            ::= { tdmoeBundleStatEntry 10 }

        bundleJumped  OBJECT-TYPE
            SYNTAX  Counter
            ACCESS  read-only
            STATUS  mandatory
            DESCRIPTION
                "Jumped packets"
            ::= { tdmoeBundleStatEntry 11 }

        bundleRe-Oreder  OBJECT-TYPE
            SYNTAX  Counter
            ACCESS  read-only
            STATUS  mandatory
            DESCRIPTION
                "Re-Oreder packets"
            ::= { tdmoeBundleStatEntry 12 }

        toeBundleClear  OBJECT-TYPE
            SYNTAX  INTEGER {
                    no(1),
                    clear(2)
                }
            MAX-ACCESS  read-write
            STATUS  mandatory
            DESCRIPTION
                "Clear Bundle Count"
            ::= { tdmoeBundleStatEntry 13 }

--
--  Traffic Statistics Table
--


        tdmoeEthPortStatTable  OBJECT-TYPE
            SYNTAX  SEQUENCE OF   TdmoeEthPortStatEntry
            ACCESS  not-accessible
            STATUS  mandatory
            DESCRIPTION
                "bundle statistics table"
            ::= {tdmoeStatTable  2}

        tdmoeEthPortStatEntry  OBJECT-TYPE
            SYNTAX  TdmoeEthPortStatEntry
            ACCESS  not-accessible
            STATUS  mandatory
            DESCRIPTION
                "An entry in bundle statistics table."
            INDEX { trafficSlotIndex , trafficPortIndex }
            ::= { tdmoeEthPortStatTable 1 }

        TdmoeEthPortStatEntry ::= SEQUENCE  {
            trafficSlotIndex            LSSlotID,
            trafficPortIndex            TdmoeEthIndex,
            trafficTx-Packets           Counter,
            trafficTx-Bytes             Counter,
            trafficTx-UnicastPackets    Counter,
            trafficTx-MulticastPackets  Counter,
            trafficTx-BroadcastPackets  Counter,
            trafficTx-PausePackets      Counter,
            trafficRx-Packets           Counter,
            trafficRx-Bytes             Counter,
            trafficRx-UnicastPackets    Counter,
            trafficRx-MulticastPackets  Counter,
            trafficRx-BroadcastPackets  Counter,
            trafficRx-PausePackets      Counter,
            trafficRx-BulkyPackets      Counter,
            trafficRx-ShortyPackets     Counter,
            trafficRx-FragmentPackets   Counter,
            trafficCRCError             Counter
        }

        trafficSlotIndex  OBJECT-TYPE
            SYNTAX  LSSlotID
            ACCESS  read-only
            STATUS  mandatory
            DESCRIPTION
                "slot index"
            ::= { tdmoeEthPortStatEntry 1 }

        trafficPortIndex  OBJECT-TYPE
            SYNTAX  TdmoeEthIndex
            ACCESS  read-only
            STATUS  mandatory
            DESCRIPTION
                "Port Index"
            ::= { tdmoeEthPortStatEntry 2 }

        trafficTx-Packets    OBJECT-TYPE
            SYNTAX  Counter
            ACCESS  read-only
            STATUS  mandatory
            DESCRIPTION
                "The number of good transmitted frames "
            ::= { tdmoeEthPortStatEntry 3 }

        trafficTx-Bytes       OBJECT-TYPE
            SYNTAX  Counter
            ACCESS  read-only
            STATUS  mandatory
            DESCRIPTION
                "The number of good transmitted bytes "
            ::= { tdmoeEthPortStatEntry 4 }

        trafficTx-UnicastPackets  OBJECT-TYPE
            SYNTAX  Counter
            ACCESS  read-only
            STATUS  mandatory
            DESCRIPTION
                "The number of good frames sent that have a unicast destination MAC address."
            ::= { tdmoeEthPortStatEntry 5}

        trafficTx-MulticastPackets  OBJECT-TYPE
            SYNTAX  Counter
            ACCESS  read-only
            STATUS  mandatory
            DESCRIPTION
                "The number of good frames sent that have a multicast destination MAC address."
            ::= { tdmoeEthPortStatEntry 6}

        trafficTx-BroadcastPackets  OBJECT-TYPE
            SYNTAX  Counter
            ACCESS  read-only
            STATUS  mandatory
            DESCRIPTION
                "The number of good frames sent that have a broadcast destination MAC address."
            ::= { tdmoeEthPortStatEntry 7}

        trafficTx-PausePackets   OBJECT-TYPE
            SYNTAX  Counter
            ACCESS  read-only
            STATUS  mandatory
            DESCRIPTION
                "transmitted pause packets."
            ::= { tdmoeEthPortStatEntry 8}

        trafficRx-Packets    OBJECT-TYPE
            SYNTAX  Counter
            ACCESS  read-only
            STATUS  mandatory
            DESCRIPTION
                "The number of good received packets "
            ::= { tdmoeEthPortStatEntry 9}

        trafficRx-Bytes   OBJECT-TYPE
            SYNTAX  Counter
            ACCESS  read-only
            STATUS  mandatory
            DESCRIPTION
                "The number of good received bytes "
            ::= { tdmoeEthPortStatEntry 10 }

        trafficRx-UnicastPackets   OBJECT-TYPE
            SYNTAX  Counter
            ACCESS  read-only
            STATUS  mandatory
            DESCRIPTION
                ""
            ::= { tdmoeEthPortStatEntry 11}

        trafficRx-MulticastPackets  OBJECT-TYPE
            SYNTAX  Counter
            ACCESS  read-only
            STATUS  mandatory
            DESCRIPTION
                "The number of good frames sent that have a multicast destination MAC address."
            ::= { tdmoeEthPortStatEntry 12}

        trafficRx-BroadcastPackets  OBJECT-TYPE
            SYNTAX  Counter
            ACCESS  read-only
            STATUS  mandatory
            DESCRIPTION
                "The number of good frames sent that have a multicast destination MAC address."
            ::= { tdmoeEthPortStatEntry 13}


        trafficRx-PausePackets         OBJECT-TYPE
            SYNTAX  Counter
            ACCESS  read-only
            STATUS  mandatory
            DESCRIPTION
                "transmitted pause packets."
            ::= { tdmoeEthPortStatEntry 14}

        trafficRx-BulkyPackets  OBJECT-TYPE
            SYNTAX  Counter
            ACCESS  read-only
            STATUS  mandatory
            DESCRIPTION
                "Total frames received with a length of more than MaxSize octets(ethernet packet length 1514) but with a valid FCS."
            ::= { tdmoeEthPortStatEntry 15 }


        trafficRx-ShortyPackets  OBJECT-TYPE
            SYNTAX  Counter
            ACCESS  read-only
            STATUS  mandatory
            DESCRIPTION
                "Total frames received with a length of less than 64 octets but with a valid FCS."
            ::= { tdmoeEthPortStatEntry 16}

        trafficRx-FragmentPackets  OBJECT-TYPE
            SYNTAX  Counter
            ACCESS  read-only
            STATUS  mandatory
            DESCRIPTION
                ""
            ::= { tdmoeEthPortStatEntry 17}

        trafficCRCError  OBJECT-TYPE
            SYNTAX  Counter
            ACCESS  read-only
            STATUS  mandatory
            DESCRIPTION
                "Total frames received with a CRC error"
            ::= { tdmoeEthPortStatEntry 18}







        tdmoeBundleStatusTable  OBJECT-TYPE
            SYNTAX  SEQUENCE OF TdmoeBundleStatusEntry
            ACCESS  not-accessible
            STATUS  mandatory
            DESCRIPTION
                "bundle statistics table"
            ::= {tdmoeStatTable  3}

        tdmoeBundleStatusEntry  OBJECT-TYPE
            SYNTAX  TdmoeBundleStatusEntry
            ACCESS  not-accessible
            STATUS  mandatory
            DESCRIPTION
                "An entry in bundle statistics table."
            INDEX { bundleStatusSlot , bundleStatusTrib ,
                    bundleStatusBundleID }
            ::= { tdmoeBundleStatusTable 1 }

        TdmoeBundleStatusEntry ::= SEQUENCE  {
            bundleStatusSlot            LSSlotID,
            bundleStatusTrib            TdmoeTribPort,
            bundleStatusBundleID        TdmoeBundleId2,
            bundleStatus                INTEGER
        }



        bundleStatusSlot  OBJECT-TYPE
            SYNTAX  LSSlotID
            ACCESS  read-only
            STATUS  mandatory
            DESCRIPTION
                "slot index"
            ::= { tdmoeBundleStatusEntry 1 }

        bundleStatusTrib  OBJECT-TYPE
            SYNTAX  TdmoeTribPort
            ACCESS  read-only
            STATUS  mandatory
            DESCRIPTION
                "TDMoE alarm portIndex"
            ::= { tdmoeBundleStatusEntry 2 }

        bundleStatusBundleID   OBJECT-TYPE
            SYNTAX   TdmoeBundleId2
            ACCESS  read-only
            STATUS  mandatory
            DESCRIPTION
                "TDMoE bundle 1-32"
            ::= { tdmoeBundleStatusEntry 3 }

        bundleStatus  OBJECT-TYPE
            SYNTAX  INTEGER {
                    inactive (1),
                    active   (2)
                }
            ACCESS  read-only
            STATUS  mandatory
            DESCRIPTION
                "Bundle Status"
            ::= { tdmoeBundleStatusEntry 4 }


        tdmoeEthPortStatusTable      OBJECT-TYPE
            SYNTAX  SEQUENCE OF TdmoeEthPortStatusEntry
            ACCESS  not-accessible
            STATUS  mandatory
            DESCRIPTION
                "Eth port Status Table."
            ::= { tdmoeStatTable 4 }

        tdmoeEthPortStatusEntry       OBJECT-TYPE
            SYNTAX  TdmoeEthPortStatusEntry
            ACCESS  not-accessible
            STATUS  mandatory
            DESCRIPTION
                "Eth Phy Config Entry."
            INDEX { enetSlotIndex , enetPortIndex }
            ::= { tdmoeEthPortStatusTable 1 }

        TdmoeEthPortStatusEntry ::= SEQUENCE {
            enetSlotIndex               LSSlotID,
            enetPortIndex               TdmoeEthIndex,
            enetState                   INTEGER,
            enetAutoNegotiation         INTEGER,
            enetSpeed                   INTEGER,
            enetDuplex                  INTEGER,
            enetAutolaserShutdown       INTEGER,
            link                        INTEGER
        }

        enetSlotIndex  OBJECT-TYPE
            SYNTAX  LSSlotID
            ACCESS  read-only
            STATUS  mandatory
            DESCRIPTION
                "slot index"
            ::= { tdmoeEthPortStatusEntry 1 }

        enetPortIndex    OBJECT-TYPE
            SYNTAX  TdmoeEthIndex
            ACCESS  read-only
            STATUS  mandatory
            DESCRIPTION
                "eth port 1-4"
            ::= { tdmoeEthPortStatusEntry 2 }

        enetState         OBJECT-TYPE
            SYNTAX  INTEGER {
                    enable  (1),
                    disable (2)
                }
            ACCESS  read-only
            STATUS  mandatory
            DESCRIPTION
                "port State"
            ::= { tdmoeEthPortStatusEntry 3 }

        enetAutoNegotiation    OBJECT-TYPE
            SYNTAX  INTEGER {
                    enable  (1),
                    disable (2)

                }
            ACCESS  read-only
            STATUS  mandatory
            DESCRIPTION
                "auto negotiation state"
            ::= {tdmoeEthPortStatusEntry 4 }

        enetSpeed    OBJECT-TYPE
            SYNTAX  INTEGER {
                    mbps-10   (1),
                    mbps-100  (2),
                    mbps-1000 (3)
                }
            ACCESS  read-only
            STATUS  mandatory
            DESCRIPTION
                "port speed 10/100/1000 mbps"
            ::= {tdmoeEthPortStatusEntry 5 }

        enetDuplex      OBJECT-TYPE
            SYNTAX  INTEGER {
                    half   (1),
                    full   (2)
                }
            ACCESS  read-only
            STATUS  mandatory
            DESCRIPTION
                "port duplex mode(half/full)"
            ::= {tdmoeEthPortStatusEntry 6 }

        enetAutolaserShutdown    OBJECT-TYPE
            SYNTAX  INTEGER {
                    enable  (1),
                    disable (2)

                }
            ACCESS  read-only
            STATUS  mandatory
            DESCRIPTION
                "autolasershutdown state"
            ::= {tdmoeEthPortStatusEntry 7}

        link    OBJECT-TYPE
            SYNTAX  INTEGER {
                    down  (1),
                    up    (2)

                }
            ACCESS  read-only
            STATUS  mandatory
            DESCRIPTION
                "link state"
            ::= {tdmoeEthPortStatusEntry 8}

--  Optical Information Table
--



        tdmoeOpticalInfoTable  OBJECT-TYPE
            SYNTAX  SEQUENCE OF OpticalInfoEntry
            ACCESS  not-accessible
            STATUS  mandatory
            DESCRIPTION
                "optical information table"
            ::= {tdmoeStatTable  5}

        opticalInfoEntry  OBJECT-TYPE
            SYNTAX  OpticalInfoEntry
            ACCESS  not-accessible
            STATUS  mandatory
            DESCRIPTION
                "An entry in optical information table."
            INDEX { opticalSlotIndex , opticalPortIndex }
            ::= { tdmoeOpticalInfoTable 1 }

        OpticalInfoEntry ::= SEQUENCE  {
            opticalSlotIndex            LSSlotID,
            opticalPortIndex            INTEGER,
            opticalConnector            INTEGER,
            opticalTransceiver          DisplayString,
            opticalLinkLength           DisplayString,
            opticalTechnology           DisplayString,
            opticalEncoding             DisplayString,
            opticalLength-9-125-um      DisplayString,
            opticalLength-50-125-um     DisplayString,
            opticalLength-62p5-125-um   DisplayString,
            opticalTemperature          DisplayString,
            opticalVcc                  DisplayString,
            opticalTxBias               DisplayString,
            opticalTxPower              DisplayString,
            opticalRxPower              DisplayString,
            opticalDate              DisplayString,
            opticalVendorName              DisplayString,
            opticalOUI              DisplayString,
            opticalPN              DisplayString,
            opticalRev              DisplayString,
            opticalWavelength              DisplayString
        }

        opticalSlotIndex  OBJECT-TYPE
            SYNTAX  LSSlotID
            ACCESS  read-only
            STATUS  mandatory
            DESCRIPTION
                "slot index"
            ::= { opticalInfoEntry 1 }

        opticalPortIndex  OBJECT-TYPE
            SYNTAX  INTEGER {
                    eth-1 (1),
                    eth-2 (2)
                }
            ACCESS  read-only
            STATUS  mandatory
            DESCRIPTION
                "optical port"
            ::= { opticalInfoEntry 2 }

        opticalConnector  OBJECT-TYPE
            SYNTAX  INTEGER {
                    not-available(1),
                    sc(2),
                    fiber-channel-style-1-copper(3),
                    fiber-channel-style-2-copper(4),
                    bnc-tnc(5),
                    fibre-channel-coaxial-header(6),
                    fiberJack(7),
                    lc(8),
                    mt-rj(9),
                    mu(10),
                    sg(11),
                    optcal-pigtail(12),
                    hssdc-ii(13),
                    copper-pigtail(14)
                }
            ACCESS  read-only
            STATUS  mandatory
            DESCRIPTION
                "SFP connector"
            ::= { opticalInfoEntry 3 }

        opticalTransceiver  OBJECT-TYPE
            SYNTAX  DisplayString (SIZE (0..255))
            ACCESS  read-only
            STATUS  mandatory
            DESCRIPTION
                "SFP transceiver"
            ::= { opticalInfoEntry 4 }

        opticalLinkLength  OBJECT-TYPE
            SYNTAX  DisplayString (SIZE (0..255))
            ACCESS  read-only
            STATUS  mandatory
            DESCRIPTION
                "SFP link length"
            ::= { opticalInfoEntry 5 }

        opticalTechnology  OBJECT-TYPE
            SYNTAX  DisplayString (SIZE (0..255))
            ACCESS  read-only
            STATUS  mandatory
            DESCRIPTION
                "SFP technology"
            ::= { opticalInfoEntry 6 }

        opticalEncoding  OBJECT-TYPE
            SYNTAX  DisplayString (SIZE (0..255))
            ACCESS  read-only
            STATUS  mandatory
            DESCRIPTION
                "SFP encoding"
            ::= { opticalInfoEntry 7 }

        opticalLength-9-125-um  OBJECT-TYPE
            SYNTAX  DisplayString (SIZE (0..255))
            ACCESS  read-only
            STATUS  mandatory
            DESCRIPTION
                "SFP length for 9/125 um fiber"
            ::= { opticalInfoEntry 8 }

        opticalLength-50-125-um  OBJECT-TYPE
            SYNTAX  DisplayString (SIZE (0..255))
            ACCESS  read-only
            STATUS  mandatory
            DESCRIPTION
                "SFP length for 50/125 um fiber"
            ::= { opticalInfoEntry 9 }

        opticalLength-62p5-125-um  OBJECT-TYPE
            SYNTAX  DisplayString (SIZE (0..255))
            ACCESS  read-only
            STATUS  mandatory
            DESCRIPTION
                "SFP length for 62.5/125 um fiber"
            ::= { opticalInfoEntry 10 }

        opticalTemperature  OBJECT-TYPE
            SYNTAX  DisplayString (SIZE (0..255))
            ACCESS  read-only
            STATUS  mandatory
            DESCRIPTION
                "SFP Temperature"
            ::= { opticalInfoEntry 11 }

        opticalVcc  OBJECT-TYPE
            SYNTAX  DisplayString (SIZE (0..255))
            ACCESS  read-only
            STATUS  mandatory
            DESCRIPTION
                "SFP Vcc"
            ::= { opticalInfoEntry 12 }

        opticalTxBias  OBJECT-TYPE
            SYNTAX  DisplayString (SIZE (0..255))
            ACCESS  read-only
            STATUS  mandatory
            DESCRIPTION
                "SFP Tx Bias current"
            ::= { opticalInfoEntry 13 }

        opticalTxPower  OBJECT-TYPE
            SYNTAX  DisplayString (SIZE (0..255))
            ACCESS  read-only
            STATUS  mandatory
            DESCRIPTION
                "SFP Tx power"
            ::= { opticalInfoEntry 14 }

        opticalRxPower  OBJECT-TYPE
            SYNTAX  DisplayString (SIZE (0..255))
            ACCESS  read-only
            STATUS  mandatory
            DESCRIPTION
                "SFP Rx power"
            ::= { opticalInfoEntry 15 }

        opticalDate             OBJECT-TYPE
            SYNTAX  DisplayString (SIZE (0..255))
            ACCESS  read-only
            STATUS  mandatory
            DESCRIPTION
                "SFP Rx power"
            ::= { opticalInfoEntry 16 }

        opticalVendorName              OBJECT-TYPE
            SYNTAX  DisplayString (SIZE (0..255))
            ACCESS  read-only
            STATUS  mandatory
            DESCRIPTION
                "SFP Rx power"
            ::= { opticalInfoEntry 17 }

        opticalOUI              OBJECT-TYPE
            SYNTAX  DisplayString (SIZE (0..255))
            ACCESS  read-only
            STATUS  mandatory
            DESCRIPTION
                "SFP Rx power"
            ::= { opticalInfoEntry 18 }

        opticalPN              OBJECT-TYPE
            SYNTAX  DisplayString (SIZE (0..255))
            ACCESS  read-only
            STATUS  mandatory
            DESCRIPTION
                "SFP Rx power"
            ::= { opticalInfoEntry 19 }

        opticalRev              OBJECT-TYPE
            SYNTAX  DisplayString (SIZE (0..255))
            ACCESS  read-only
            STATUS  mandatory
            DESCRIPTION
                "SFP Rx power"
            ::= { opticalInfoEntry 20 }

        opticalWavelength           OBJECT-TYPE
            SYNTAX  DisplayString (SIZE (0..255))
            ACCESS  read-only
            STATUS  mandatory
            DESCRIPTION
                "SFP Rx power"
            ::= { opticalInfoEntry 21 }
--
-- Transmission delay measurement map table
--

        toeRoundTripMapTable  OBJECT-TYPE
            SYNTAX  SEQUENCE OF ToeRoundTripMapEntry
            ACCESS  not-accessible
            STATUS  mandatory
            DESCRIPTION
                "Transmission delay measurement map table"
            ::= {tdmoeStatTable  6}

        toeRoundTripMapEntry  OBJECT-TYPE
            SYNTAX  ToeRoundTripMapEntry
            ACCESS  not-accessible
            STATUS  mandatory
            DESCRIPTION
                "An entry in transmission delay measurement map table."
            INDEX { diagRoundTripMapSlotIndex , diagRoundTripMapPortIndex }
            ::= { toeRoundTripMapTable 1 }

        ToeRoundTripMapEntry ::= SEQUENCE  {
            diagRoundTripMapSlotIndex           LSSlotID,
            diagRoundTripMapPortIndex           TdmoeTribPort,
            diagRoundTripMapBundleID            TdmoeBundleId2,
            diagRoundTripMapPeriod              INTEGER,
            diagRoundTripMapEnable              INTEGER,
            diagRoundTripMapErrorCode           INTEGER,
            diagRoundTripMapElapseTime          INTEGER,
            diagRoundTripMapMax                 DisplayString,
            diagRoundTripMapMin                 DisplayString,
            diagRoundTripMapAvg                 DisplayString,
            diagRoundTripMapPacketLoss          Counter
        }

        diagRoundTripMapSlotIndex  OBJECT-TYPE
            SYNTAX  LSSlotID
            ACCESS  read-only
            STATUS  mandatory
            DESCRIPTION
                "Slot 1~12, total 12 slots."
            ::= { toeRoundTripMapEntry 1 }

        diagRoundTripMapPortIndex    OBJECT-TYPE
            SYNTAX  TdmoeTribPort
            ACCESS  read-only
            STATUS  mandatory
            DESCRIPTION
                "trib port 1~4 "
            ::= { toeRoundTripMapEntry 2 }

        diagRoundTripMapBundleID      OBJECT-TYPE
            SYNTAX  TdmoeBundleId2
            ACCESS  read-only
            STATUS  mandatory
            DESCRIPTION
                "bundle ID "
            ::= { toeRoundTripMapEntry 3}

        diagRoundTripMapPeriod  OBJECT-TYPE
            SYNTAX  INTEGER (1..600)
            ACCESS  read-only
            STATUS  mandatory
            DESCRIPTION
                "Period time for transmission delay measurement (second) "
            ::= { toeRoundTripMapEntry 4 }

        diagRoundTripMapEnable  OBJECT-TYPE
            SYNTAX  INTEGER {
                    enable(1),
                    disable(2)
                }
            ACCESS  read-only
            STATUS  mandatory
            DESCRIPTION
                "Ethernet transmission time delay measurement control "
            ::= { toeRoundTripMapEntry 5 }

        diagRoundTripMapErrorCode  OBJECT-TYPE
            SYNTAX  INTEGER {
                    ok(1),
                    inactive-delay-measurement(2),
                    no-measurement-available(3),
                    not-receive-any-return-packet(5),
                    packet-loss-too-much(9),
                    na(254),
                    unknown-problem(255)
                }
            ACCESS  read-only
            STATUS  mandatory
            DESCRIPTION
                "Test measurement result: 2, 3, 4, etc..
                Result 2 means 'test ok.'.
                Result 3 means 'Bundle inactive delay measurement not available.'.
                Result 4 means 'Did not receive any return packet, no measurement available, please retest.'."
            ::= { toeRoundTripMapEntry 6 }

        diagRoundTripMapElapseTime  OBJECT-TYPE
            SYNTAX  INTEGER (1..600)
            ACCESS  read-only
            STATUS  mandatory
            DESCRIPTION
                "Elapsed time (second) "
            ::= { toeRoundTripMapEntry 7 }

        diagRoundTripMapMax  OBJECT-TYPE
            SYNTAX  DisplayString (SIZE(0..255))
            ACCESS  read-only
            STATUS  mandatory
            DESCRIPTION
                "Maximum transmission delay time (millisecond) "
            ::= { toeRoundTripMapEntry 8 }

        diagRoundTripMapMin  OBJECT-TYPE
            SYNTAX  DisplayString (SIZE(0..255))
            ACCESS  read-only
            STATUS  mandatory
            DESCRIPTION
                "Minimum transmission delay time (millisecond) "
            ::= { toeRoundTripMapEntry 9 }

        diagRoundTripMapAvg  OBJECT-TYPE
            SYNTAX  DisplayString (SIZE(0..255))
            ACCESS  read-only
            STATUS  mandatory
            DESCRIPTION
                "Average transmission delay time (millisecond) "
            ::= { toeRoundTripMapEntry 10 }

        diagRoundTripMapPacketLoss  OBJECT-TYPE
            SYNTAX  Counter
            ACCESS  read-only
            STATUS  mandatory
            DESCRIPTION
                "Round trip test packet loss "
            ::= { toeRoundTripMapEntry 11 }

--
--  SYSTEM Information Table
--

        tdmoeSystemInfoTable  OBJECT-TYPE
            SYNTAX  SEQUENCE OF SystemInfoEntry
            ACCESS  not-accessible
            STATUS  mandatory
            DESCRIPTION
                "The system information table."
            ::= { tdmoe-card 9}

        systemInfoEntry  OBJECT-TYPE
            SYNTAX  SystemInfoEntry
            ACCESS  not-accessible
            STATUS  mandatory
            DESCRIPTION
                "An entry in the system information table."
            INDEX { tdmoeSystemSlot }
            ::= { tdmoeSystemInfoTable 1 }

        SystemInfoEntry ::= SEQUENCE {
            tdmoeSystemSlot             LSSlotID,
            tdmoePROMVersion            DisplayString,
            tdmoeHardwareVersion        DisplayString,
            tdmoeFpgaVersion            DisplayString,
            tdmoeOscType                DisplayString,
            tdmoeBank1Version           DisplayString,
            tdmoeBank2Version           DisplayString,
            tdmoeActiveBank             INTEGER,
            tdmoeNextBank               INTEGER
        }

        tdmoeSystemSlot  OBJECT-TYPE
            SYNTAX  LSSlotID
            ACCESS  read-only
            STATUS  mandatory
            DESCRIPTION
                "slot index"
            ::= { systemInfoEntry 1 }

        tdmoePROMVersion  OBJECT-TYPE
            SYNTAX  DisplayString (SIZE (0..255) )
            ACCESS  read-only
            STATUS  mandatory
            DESCRIPTION
                " tdmoe PROM Version"
            ::= { systemInfoEntry 2 }

        tdmoeHardwareVersion  OBJECT-TYPE
            SYNTAX  DisplayString (SIZE (0..255) )
            ACCESS  read-only
            STATUS  mandatory
            DESCRIPTION
                " tdmoe Hardware Version"
            ::= { systemInfoEntry 3 }

        tdmoeFpgaVersion  OBJECT-TYPE
            SYNTAX  DisplayString (SIZE (0..40))
            ACCESS  read-only
            STATUS  mandatory
            DESCRIPTION
                "FPGA Version"
            ::= { systemInfoEntry 4 }

        tdmoeOscType  OBJECT-TYPE
            SYNTAX  DisplayString (SIZE (0..255))
            ACCESS  read-only
            STATUS  mandatory
            DESCRIPTION
                "osc version"
            ::= { systemInfoEntry 5 }

        tdmoeBank1Version    OBJECT-TYPE
            SYNTAX  DisplayString (SIZE (0..255))
            ACCESS  read-only
            STATUS  mandatory
            DESCRIPTION
                "Bank-1 Version"
            ::= { systemInfoEntry 6 }

        tdmoeBank2Version    OBJECT-TYPE
            SYNTAX  DisplayString (SIZE (0..255))
            ACCESS  read-only
            STATUS  mandatory
            DESCRIPTION
                "Bank-2 Version"
            ::= { systemInfoEntry 7}

        tdmoeActiveBank    OBJECT-TYPE
            SYNTAX  INTEGER{
                    bank-1(1),
                    bank-2(2)
                }
            ACCESS  read-only
            STATUS  mandatory
            DESCRIPTION
                "Active Bank 1/2"
            ::= { systemInfoEntry 8 }

        tdmoeNextBank    OBJECT-TYPE
            SYNTAX  INTEGER{
                    bank-1(1),
                    bank-2(2)
                }
            ACCESS  read-write
            STATUS  mandatory
            DESCRIPTION
                "Next Bank 1/2"
            ::= { systemInfoEntry 9 }

--
--  Command Control Table
--

        tdmoeCommandControlTable  OBJECT-TYPE
            SYNTAX  SEQUENCE OF TdmoeCommandControlEntry
            ACCESS  not-accessible
            STATUS  mandatory
            DESCRIPTION
                "The command control table."
            ::= { tdmoe-card 10}

        tdmoeCommandControlEntry  OBJECT-TYPE
            SYNTAX  TdmoeCommandControlEntry
            ACCESS  not-accessible
            STATUS  mandatory
            DESCRIPTION
                "An entry in the command control table."
            INDEX { tdmoeComCtrlSlot }
            ::= { tdmoeCommandControlTable 1 }

        TdmoeCommandControlEntry ::= SEQUENCE {
            tdmoeComCtrlSlot            LSSlotID,
            tdmoePerfReset              INTEGER,
            tdmoeAlarmHistoryReset      INTEGER,
            tdmoeCardReset              INTEGER,
            tdmoeLoadDefault            INTEGER
        }

        tdmoeComCtrlSlot  OBJECT-TYPE
            SYNTAX  LSSlotID
            ACCESS  read-only
            STATUS  mandatory
            DESCRIPTION
                "slot index"
            ::= { tdmoeCommandControlEntry 1 }

        tdmoePerfReset    OBJECT-TYPE
            SYNTAX  INTEGER {
                    reset(1)
                }
            ACCESS  read-write
            STATUS  mandatory
            DESCRIPTION
                "Command: Reset User Performance"
            ::= { tdmoeCommandControlEntry 2 }

        tdmoeAlarmHistoryReset    OBJECT-TYPE
            SYNTAX  INTEGER {
                    reset(1)
                }
            ACCESS  read-write
            STATUS  mandatory
            DESCRIPTION
                "Command: Reset Alarm History"
            ::= { tdmoeCommandControlEntry 3 }

        tdmoeCardReset    OBJECT-TYPE
            SYNTAX  INTEGER {
                    reset(1)
                }
            ACCESS  read-write
            STATUS  mandatory
            DESCRIPTION
                "Command: Reset "
            ::= { tdmoeCommandControlEntry 4 }

        tdmoeLoadDefault    OBJECT-TYPE
            SYNTAX  INTEGER {
                    load-default(1)
                }
            ACCESS  read-write
            STATUS  mandatory
            DESCRIPTION
                "Command: Load Default"
            ::= { tdmoeCommandControlEntry 5}


--
--    Vlan VID setup table
--

        toeVlanSetupVidTable  OBJECT-TYPE
            SYNTAX  SEQUENCE OF ToeVlanSetupVidEntry
            ACCESS  not-accessible
            STATUS  mandatory
            DESCRIPTION
                "TDMOE Vlan VID setup table"
            ::= { tdmoe-card 11 }

        toeVlanSetupVidEntry  OBJECT-TYPE
            SYNTAX  ToeVlanSetupVidEntry
            ACCESS  not-accessible
            STATUS  mandatory
            DESCRIPTION
                "An entry in TDMOE Vlan VID setup table"
            INDEX { tvSetupVidSlot }
            ::= { toeVlanSetupVidTable 1 }

        ToeVlanSetupVidEntry ::= SEQUENCE  {
            tvSetupVidSlot              LSSlotID,
            tvVLAN802-1Q                INTEGER,
            tvTdmPvid                   INTEGER,
            tvEth1Pvid                  INTEGER,
            tvEth2Pvid                  INTEGER,
            tvEth3Pvid                  INTEGER,
            tvEth4Pvid                  INTEGER
        }

        tvSetupVidSlot  OBJECT-TYPE
            SYNTAX  LSSlotID
            ACCESS  read-only
            STATUS  mandatory
            DESCRIPTION
                "slot index"
            ::= { toeVlanSetupVidEntry 1 }

        tvVLAN802-1Q  OBJECT-TYPE
            SYNTAX  INTEGER {
                    disable(1),
                    enable(2)
                }
            ACCESS  read-write
            STATUS  mandatory
            DESCRIPTION
                "802.1Q VLAN"
            ::= { toeVlanSetupVidEntry 2 }

        tvTdmPvid  OBJECT-TYPE
            SYNTAX  INTEGER (1..4095)
            ACCESS  read-write
            STATUS  mandatory
            DESCRIPTION
                "VID for TDM"
            ::= { toeVlanSetupVidEntry 3 }

        tvEth1Pvid  OBJECT-TYPE
            SYNTAX  INTEGER (1..4095)
            ACCESS  read-write
            STATUS  mandatory
            DESCRIPTION
                "VID for ethernet port 1"
            ::= { toeVlanSetupVidEntry 4 }

        tvEth2Pvid  OBJECT-TYPE
            SYNTAX  INTEGER (1..4095)
            ACCESS  read-write
            STATUS  mandatory
            DESCRIPTION
                "VID for ethernet port 2"
            ::= { toeVlanSetupVidEntry 5 }

        tvEth3Pvid  OBJECT-TYPE
            SYNTAX  INTEGER (1..4095)
            ACCESS  read-write
            STATUS  mandatory
            DESCRIPTION
                "VID for ethernet port 3"
            ::= { toeVlanSetupVidEntry 6 }

        tvEth4Pvid  OBJECT-TYPE
            SYNTAX  INTEGER (1..4095)
            ACCESS  read-write
            STATUS  mandatory
            DESCRIPTION
                "VID for ethernet port 4"
            ::= { toeVlanSetupVidEntry 7 }


--
--    Vlan Group Setup Table
--
--
        toeVlanSetupGroupTable  OBJECT-TYPE
            SYNTAX  SEQUENCE OF ToeVlanSetupGroupEntry
            ACCESS  not-accessible
            STATUS  mandatory
            DESCRIPTION
                "Vlan Group Setup Table"
            ::= { tdmoe-card 12 }

        toeVlanSetupGroupEntry  OBJECT-TYPE
            SYNTAX  ToeVlanSetupGroupEntry
            ACCESS  not-accessible
            STATUS  mandatory
            DESCRIPTION
                "An entry in Vlan Group Setup Table"
            INDEX { tvSetupGroupSlot , tvGroupIndex }
            ::= { toeVlanSetupGroupTable 1 }

        ToeVlanSetupGroupEntry ::= SEQUENCE  {
            tvSetupGroupSlot            LSSlotID,
            tvGroupIndex                INTEGER,
            tvTdmTag                    INTEGER,
            tvEth1Tag                   INTEGER,
            tvEth2Tag                   INTEGER,
            tvEth3Tag                   INTEGER,
            tvEth4Tag                   INTEGER,
            tvVlanID                    INTEGER,
            tvEnable                    INTEGER
        }

        tvSetupGroupSlot  OBJECT-TYPE
            SYNTAX  LSSlotID
            ACCESS  read-only
            STATUS  mandatory
            DESCRIPTION
                "slot index"
            ::= { toeVlanSetupGroupEntry 1 }

        tvGroupIndex  OBJECT-TYPE
            SYNTAX  INTEGER (1..16)
            ACCESS  read-only
            STATUS  mandatory
            DESCRIPTION
                "group index"
            ::= { toeVlanSetupGroupEntry 2 }

        tvTdmTag  OBJECT-TYPE
            SYNTAX  INTEGER {
                    no(1),
                    tag(2),
                    untag(3)
                }
            ACCESS  read-write
            STATUS  mandatory
            DESCRIPTION
                "vlan tdm tag/uptag"
            ::= { toeVlanSetupGroupEntry 3 }

        tvEth1Tag  OBJECT-TYPE
            SYNTAX  INTEGER {
                    no(1),
                    tag(2),
                    untag(3)
                }
            ACCESS  read-write
            STATUS  mandatory
            DESCRIPTION
                "vlan ethernet port 1 tag/uptag"
            ::= { toeVlanSetupGroupEntry 4 }

        tvEth2Tag  OBJECT-TYPE
            SYNTAX  INTEGER {
                    no(1),
                    tag(2),
                    untag(3)
                }
            ACCESS  read-write
            STATUS  mandatory
            DESCRIPTION
                "vlan ethernet port 2 tag/uptag"
            ::= { toeVlanSetupGroupEntry 5 }

        tvEth3Tag  OBJECT-TYPE
            SYNTAX  INTEGER {
                    no(1),
                    tag(2),
                    untag(3)
                }
            ACCESS  read-write
            STATUS  mandatory
            DESCRIPTION
                "vlan ethernet port 3 tag/uptag"
            ::= { toeVlanSetupGroupEntry 6 }

        tvEth4Tag  OBJECT-TYPE
            SYNTAX  INTEGER {
                    no(1),
                    tag(2),
                    untag(3)
                }
            ACCESS  read-write
            STATUS  mandatory
            DESCRIPTION
                "vlan ethernet port 4 tag/uptag"
            ::= { toeVlanSetupGroupEntry 7 }

        tvVlanID  OBJECT-TYPE
            SYNTAX  INTEGER (1..4095)
            ACCESS  read-write
            STATUS  mandatory
            DESCRIPTION
                "vlan vid"
            ::= { toeVlanSetupGroupEntry 8 }

        tvEnable  OBJECT-TYPE
            SYNTAX  INTEGER {
                    disable(1),
                    enable(2)
                }
            ACCESS  read-write
            STATUS  mandatory
            DESCRIPTION
                "group enable"
            ::= { toeVlanSetupGroupEntry 9 }

        toeTotalCard   OBJECT-TYPE
            SYNTAX  INTEGER
            ACCESS  read-only
            STATUS  mandatory
            DESCRIPTION
                "Total cards of TDMoE"
            ::= { tdmoe-card 100 }



--======================================================================--
--======================================================================--
--  8DBRA-card MIB
--======================================================================--
--======================================================================--

--
--  8DBRA Configuartion
--


        dbraBackupTable  OBJECT-TYPE
            SYNTAX  SEQUENCE OF DbraBackupEntry
            ACCESS  not-accessible
            STATUS  mandatory
            DESCRIPTION
                "The DBRA Backup table."
            ::= { oct-dbra-card 1 }

        dbraBackupEntry  OBJECT-TYPE
            SYNTAX  DbraBackupEntry
            ACCESS  not-accessible
            STATUS  mandatory
            DESCRIPTION
                "An entry in the dbra backup table."
            INDEX { dbraBackupSlotIndex }
            ::= { dbraBackupTable 1 }

        DbraBackupEntry ::= SEQUENCE {
            dbraBackupSlotIndex         LSSlotID,
            dbraBackupType              INTEGER,
            dbraSite                    INTEGER,
            dbraMode                    INTEGER,
            dbraForceSwitch             INTEGER,
            dbraStatus                  INTEGER
        }

        dbraBackupSlotIndex  OBJECT-TYPE
            SYNTAX  LSSlotID
            ACCESS  read-only
            STATUS  mandatory
            DESCRIPTION
                "DBRA slot index"
            ::= { dbraBackupEntry 1 }

        dbraBackupType  OBJECT-TYPE
            SYNTAX  INTEGER {
                    no(1),
                    port-backup(2),
                    card-backup(3),
                    dual-host(4)
                }
            ACCESS  read-write
            STATUS  mandatory
            DESCRIPTION
                "DBRA backup mode"
            ::= { dbraBackupEntry 2 }

        dbraSite  OBJECT-TYPE
            SYNTAX  INTEGER {
                    primary(1),
                    secondary(2),
                    none(3)
                }
            ACCESS  read-write
            STATUS  mandatory
            DESCRIPTION
                "DBRA dual host site"
            ::= { dbraBackupEntry 3}

        dbraMode  OBJECT-TYPE
            SYNTAX  INTEGER {
                    non-revertible(1),
                    revertible(2),
                    none(3)
                }
            ACCESS  read-write
            STATUS  mandatory
            DESCRIPTION
                "Only use in card backup to determine whether slot changes to working
                or stand-by mode "
            ::= { dbraBackupEntry 4}

        dbraForceSwitch  OBJECT-TYPE
            SYNTAX  INTEGER {
                    no(1),
                    force(2),
                    none(3)
                }
            ACCESS  read-write
            STATUS  mandatory
            DESCRIPTION
                "Only use in card backup to force slot changes to working
                or stand-by mode "
            ::= { dbraBackupEntry 5}

        dbraStatus     OBJECT-TYPE
            SYNTAX  INTEGER {
                    working(1),
                    stand-by(2),
                    none(3)
                }
            ACCESS  read-only
            STATUS  mandatory
            DESCRIPTION
                "Only show in card-backup to indicate the slot is working
                or stand-by STATUS "
            ::= { dbraBackupEntry 6}

--port map

        dbraPortMapTable  OBJECT-TYPE
            SYNTAX  SEQUENCE OF DbraPortMapEntry
            ACCESS  not-accessible
            STATUS  mandatory
            DESCRIPTION
                "The DBRA Port Map table."
            ::= { oct-dbra-card 2 }


        dbraPortMapEntry  OBJECT-TYPE
            SYNTAX  DbraPortMapEntry
            ACCESS  not-accessible
            STATUS  mandatory
            DESCRIPTION
                "An entry in the dbra port map table."
            INDEX { dbraPortMapSlotIndex }
            ::= { dbraPortMapTable 1 }

        DbraPortMapEntry ::= SEQUENCE {
            dbraPortMapSlotIndex        LSSlotID,
            dbraVirtualPort             INTEGER,
            dbraTsStart                 INTEGER,
            dbraTotalTS                 INTEGER,
            dbraRS232Port               INTEGER,
            dbraCommand                 INTEGER
        }

        dbraPortMapSlotIndex  OBJECT-TYPE
            SYNTAX  LSSlotID
            ACCESS  read-only
            STATUS  mandatory
            DESCRIPTION
                "DBRA slot index"
            ::= { dbraPortMapEntry 1 }

        dbraVirtualPort  OBJECT-TYPE
            SYNTAX  INTEGER {
                    vp1(1),
                    vp2(2),
                    vp3(3),
                    vp4(4)
                }
            ACCESS  read-write
            STATUS  mandatory
            DESCRIPTION
                "DBRA virtual port"
            ::= { dbraPortMapEntry 2 }

        dbraTsStart  OBJECT-TYPE
            SYNTAX  INTEGER (1..32)
            ACCESS  read-write
            STATUS  mandatory
            DESCRIPTION
                "DBRA Time Slot Start range(1-32)"
            ::= { dbraPortMapEntry 3 }

        dbraTotalTS  OBJECT-TYPE
            SYNTAX  INTEGER (1..20)
            ACCESS  read-write
            STATUS  mandatory
            DESCRIPTION
                "DBRA Time Slot Start (1-20)"
            ::= { dbraPortMapEntry 4}

        dbraRS232Port  OBJECT-TYPE
            SYNTAX  INTEGER (1..8)
            ACCESS  read-write
            STATUS  mandatory
            DESCRIPTION
                "DBRA rs232 port"
            ::= { dbraPortMapEntry 5}

        dbraCommand  OBJECT-TYPE
            SYNTAX  INTEGER  {
                    setonly(1),
                    clear(2),
                    clearAndset(3)
                }
            ACCESS  read-write
            STATUS  mandatory
            DESCRIPTION
                "DBRA rs232 port"
            ::= { dbraPortMapEntry 6}


-- rs232 config

        dbraRs232ConfigTable  OBJECT-TYPE
            SYNTAX  SEQUENCE OF DbraRs232ConfigEntry
            ACCESS  not-accessible
            STATUS  mandatory
            DESCRIPTION
                "The DBRA rs232 config table."
            ::= { oct-dbra-card 3 }

        dbraRs232ConfigEntry  OBJECT-TYPE
            SYNTAX  DbraRs232ConfigEntry
            ACCESS  not-accessible
            STATUS  mandatory
            DESCRIPTION
                "An entry in the dbra rs232 config table."
            INDEX { dbraRs232SlotIndex , dbraRs232PortIndex }
            ::= { dbraRs232ConfigTable 1 }

        DbraRs232ConfigEntry ::= SEQUENCE {
            dbraRs232SlotIndex          LSSlotID,
            dbraRs232PortIndex          PortID,
            dbraRate                    INTEGER,
            dbraInterface               INTEGER
        }

        dbraRs232SlotIndex  OBJECT-TYPE
            SYNTAX  LSSlotID
            ACCESS  read-only
            STATUS  mandatory
            DESCRIPTION
                "DBRA slot index"
            ::= { dbraRs232ConfigEntry 1 }

        dbraRs232PortIndex  OBJECT-TYPE
            SYNTAX  PortID
            ACCESS  read-only
            STATUS  mandatory
            DESCRIPTION
                "dbra port 1-8"
            ::= { dbraRs232ConfigEntry 2 }

        dbraRate  OBJECT-TYPE
            SYNTAX  INTEGER {
                    r1-2K(1),
                    r2-4K(2),
                    r4-8K(3),
                    r9-6K(4),
                    r19-2K(5)
                }
            ACCESS  read-write
            STATUS  mandatory
            DESCRIPTION
                "DBRA rate"
            ::= { dbraRs232ConfigEntry 3 }

        dbraInterface  OBJECT-TYPE
            SYNTAX  INTEGER {
                    db25-RJ(1),
                    rj-only(2)
                }
            ACCESS  read-only
            STATUS  mandatory
            DESCRIPTION
                "DBRA interface"
            ::= { dbraRs232ConfigEntry 4 }



-- diagnostic control

        dbraDiagControlTable  OBJECT-TYPE
            SYNTAX  SEQUENCE OF DbraDiagControlEntry
            ACCESS  not-accessible
            STATUS  mandatory
            DESCRIPTION
                ""
            ::= { oct-dbra-card 4}

        dbraDiagControlEntry  OBJECT-TYPE
            SYNTAX  DbraDiagControlEntry
            ACCESS  not-accessible
            STATUS  mandatory
            DESCRIPTION
                ""
            INDEX { dbraDiagSlotIndex , dbraDiagPortIndex }
            ::= { dbraDiagControlTable 1 }

        DbraDiagControlEntry ::= SEQUENCE {
            dbraDiagSlotIndex           LSSlotID,
            dbraDiagPortIndex           PortID,
            dbrars232Loopback           INTEGER
        }

        dbraDiagSlotIndex  OBJECT-TYPE
            SYNTAX  LSSlotID
            ACCESS  read-only
            STATUS  mandatory
            DESCRIPTION
                "DBRA slot index"
            ::= { dbraDiagControlEntry 1 }

        dbraDiagPortIndex  OBJECT-TYPE
            SYNTAX  PortID
            ACCESS  read-only
            STATUS  mandatory
            DESCRIPTION
                "dbra port 1-8"
            ::= { dbraDiagControlEntry 2 }

        dbrars232Loopback  OBJECT-TYPE
            SYNTAX  INTEGER {
                    off(1),
                    to-rs232(2),
                    to-system(3)
                }
            ACCESS  read-write
            STATUS  mandatory
            DESCRIPTION
                "dbra loopback setup"
            ::= { dbraDiagControlEntry 3}


-- portmap information

        dbraPortMapInfoTable  OBJECT-TYPE
            SYNTAX  SEQUENCE OF DbraPortMapInfoEntry
            ACCESS  not-accessible
            STATUS  mandatory
            DESCRIPTION
                "The DBRA Port Map Information table."
            ::= { oct-dbra-card 5}


        dbraPortMapInfoEntry  OBJECT-TYPE
            SYNTAX  DbraPortMapInfoEntry
            ACCESS  not-accessible
            STATUS  mandatory
            DESCRIPTION
                "An entry in the dbra port map info table."
            INDEX { dbraPortMapInfoSlotIndex , dbraPortMapInfoPortIndex ,
                    dbraPortMapTimeSlotIndex }
            ::= { dbraPortMapInfoTable 1 }

        DbraPortMapInfoEntry ::= SEQUENCE {
            dbraPortMapInfoSlotIndex    LSSlotID,
            dbraPortMapInfoPortIndex    INTEGER,
            dbraPortMapTimeSlotIndex    INTEGER,
            dbraMapToPort               INTEGER
        }

        dbraPortMapInfoSlotIndex  OBJECT-TYPE
            SYNTAX  LSSlotID
            ACCESS  read-only
            STATUS  mandatory
            DESCRIPTION
                "DBRA slot index"
            ::= { dbraPortMapInfoEntry 1 }

        dbraPortMapInfoPortIndex  OBJECT-TYPE
            SYNTAX  INTEGER {
                    vp1(1),
                    vp2(2),
                    vp3(3),
                    vp4(4)
                }
            ACCESS  read-only
            STATUS  mandatory
            DESCRIPTION
                "DBRA virtual port"
            ::= { dbraPortMapInfoEntry 2 }

        dbraPortMapTimeSlotIndex  OBJECT-TYPE
            SYNTAX  INTEGER (1..32)
            ACCESS  read-only
            STATUS  mandatory
            DESCRIPTION
                "DBRA timeslot index"
            ::= { dbraPortMapInfoEntry 3 }

        dbraMapToPort  OBJECT-TYPE
            SYNTAX  INTEGER {
                    port-1(1),
                    port-2(2),
                    port-3(3),
                    port-4(4),
                    port-5(5),
                    port-6(6),
                    port-7(7),
                    port-8(8),
                    idle  (255)
                }
            ACCESS  read-only
            STATUS  mandatory
            DESCRIPTION
                "DBRA timeslot map to port"
            ::= { dbraPortMapInfoEntry 4 }

-- command control

        dbraCommandControlTable  OBJECT-TYPE
            SYNTAX  SEQUENCE OF DbraCommandControlEntry
            ACCESS  not-accessible
            STATUS  mandatory
            DESCRIPTION
                "The command control table."
            ::= { oct-dbra-card 6}

        dbraCommandControlEntry  OBJECT-TYPE
            SYNTAX  DbraCommandControlEntry
            ACCESS  not-accessible
            STATUS  mandatory
            DESCRIPTION
                "An entry in the command control table."
            INDEX { dbraCommandSlotIndex }
            ::= { dbraCommandControlTable 1 }

        DbraCommandControlEntry ::= SEQUENCE {
            dbraCommandSlotIndex        LSSlotID,
            dbraCardReset               INTEGER,
            dbraLoadDefault             INTEGER,
            dbraDataMode                INTEGER
        }

        dbraCommandSlotIndex  OBJECT-TYPE
            SYNTAX  LSSlotID
            ACCESS  read-only
            STATUS  mandatory
            DESCRIPTION
                "DBRA slot index"
            ::= { dbraCommandControlEntry 1 }

        dbraCardReset  OBJECT-TYPE
            SYNTAX  INTEGER {
                    reset(1)
                }
            ACCESS  read-write
            STATUS  mandatory
            DESCRIPTION
                "Reset dbra card"
            ::= { dbraCommandControlEntry 2 }

        dbraLoadDefault  OBJECT-TYPE
            SYNTAX  INTEGER {
                    load-default(1)
                }
            ACCESS  read-write
            STATUS  mandatory
            DESCRIPTION
                "Load default"
            ::= { dbraCommandControlEntry 3 }

        dbraDataMode  OBJECT-TYPE
            SYNTAX  INTEGER {
                    data-56k(1),
                    data-64k(2),
                    na(3)
                }
            ACCESS  read-write
            STATUS  mandatory
            DESCRIPTION
                "dbra data rate"
            ::= { dbraCommandControlEntry 4 }


-- card information

        dbraSystemInfoTable  OBJECT-TYPE
            SYNTAX  SEQUENCE OF DbraSystemInfoEntry
            ACCESS  not-accessible
            STATUS  mandatory
            DESCRIPTION
                "The system information table."
            ::= {  oct-dbra-card 7}

        dbraSystemInfoEntry  OBJECT-TYPE
            SYNTAX  DbraSystemInfoEntry
            ACCESS  not-accessible
            STATUS  mandatory
            DESCRIPTION
                "An entry in the system information table."
            INDEX { dbraSysInfoSlotIndex }
            ::= { dbraSystemInfoTable 1 }

        DbraSystemInfoEntry ::= SEQUENCE {
            dbraSysInfoSlotIndex        LSSlotID,
            dbraPROMVersion             DisplayString,
            dbraHardwareVersion         DisplayString,
            dbraFpgaVersion             DisplayString
        }

        dbraSysInfoSlotIndex  OBJECT-TYPE
            SYNTAX  LSSlotID
            ACCESS  read-only
            STATUS  mandatory
            DESCRIPTION
                "DBRA slot index"
            ::= { dbraSystemInfoEntry 1 }


        dbraPROMVersion  OBJECT-TYPE
            SYNTAX  DisplayString (SIZE (0..255) )
            ACCESS  read-only
            STATUS  mandatory
            DESCRIPTION
                " dbra PROM Version"
            ::= { dbraSystemInfoEntry 2 }

        dbraHardwareVersion  OBJECT-TYPE
            SYNTAX  DisplayString (SIZE (0..255) )
            ACCESS  read-only
            STATUS  mandatory
            DESCRIPTION
                " dbra Hardware Version"
            ::= { dbraSystemInfoEntry 3 }

        dbraFpgaVersion     OBJECT-TYPE
            SYNTAX  DisplayString (SIZE (0..255) )
            ACCESS  read-only
            STATUS  mandatory
            DESCRIPTION
                " dbra Fpga Version"
            ::= { dbraSystemInfoEntry 4 }

        dbraTotalCard   OBJECT-TYPE
            SYNTAX  INTEGER
            ACCESS  read-only
            STATUS  mandatory
            DESCRIPTION
                "Total cards of 8DBRA"
            ::= { oct-dbra-card 100 }


--======================================================================--
--======================================================================--
--  conference-card MIB
--======================================================================--
--======================================================================--

--
--  Basic Control Table
--
        confBasicControlTable  OBJECT-TYPE
            SYNTAX  SEQUENCE OF ConfBasicControlEntry
            ACCESS  not-accessible
            STATUS  mandatory
            DESCRIPTION
                "The conference basic control table."
            ::= { conference-card 1 }

        confBasicControlEntry  OBJECT-TYPE
            SYNTAX  ConfBasicControlEntry
            ACCESS  not-accessible
            STATUS  mandatory
            DESCRIPTION
                "An entry in the conference basic control table."
            INDEX { confBCIndex }
            ::= { confBasicControlTable 1 }

        ConfBasicControlEntry ::= SEQUENCE  {
            confBCIndex                 LSSlotID,
            confConferenceID            INTEGER,
            confFXS-L1-PhoneNumber      INTEGER,
            confFXS-L2-PhoneNumber      INTEGER,
            confEM-L3-PhoneNumber       INTEGER,
            confEM-L4-PhoneNumber       INTEGER,
            confWanRate                 INTEGER,
            confFXS-L1-Conference       INTEGER,
            confFXS-L2-Conference       INTEGER,
            confEM-L3-Conference        INTEGER,
            confEM-L4-Conference        INTEGER,
            confMediaType               INTEGER,
            confEchoCanceller           INTEGER,
            confPhoneMode               INTEGER
        }

        confBCIndex  OBJECT-TYPE
            SYNTAX  LSSlotID
            ACCESS  read-only
            STATUS  mandatory
            DESCRIPTION
                "CONF slot index"
            ::= { confBasicControlEntry 1 }

        confConferenceID  OBJECT-TYPE
            SYNTAX  INTEGER (0..99)
            ACCESS  read-write
            STATUS  mandatory
            DESCRIPTION
                "The conference card ID"
            ::= { confBasicControlEntry 2 }

        confFXS-L1-PhoneNumber  OBJECT-TYPE
            SYNTAX  INTEGER (0..89)
            ACCESS  read-write
            STATUS  mandatory
            DESCRIPTION
                "FXS(L1) phone number"
            ::= { confBasicControlEntry 3 }

        confFXS-L2-PhoneNumber  OBJECT-TYPE
            SYNTAX  INTEGER (0..89)
            ACCESS  read-write
            STATUS  mandatory
            DESCRIPTION
                "FXS(L2) phone number"
            ::= { confBasicControlEntry 4 }

        confEM-L3-PhoneNumber  OBJECT-TYPE
            SYNTAX  INTEGER (0..89)
            ACCESS  read-write
            STATUS  mandatory
            DESCRIPTION
                "EM(L3) phone number"
            ::= { confBasicControlEntry 5 }

        confEM-L4-PhoneNumber  OBJECT-TYPE
            SYNTAX  INTEGER (0..89)
            ACCESS  read-write
            STATUS  mandatory
            DESCRIPTION
                "EM(L4) phone number"
            ::= { confBasicControlEntry 6 }

        confWanRate  OBJECT-TYPE
            SYNTAX  INTEGER {
                    rate-64Kbs(1),
                    rate-128Kbs(2),
                    rate-192Kbs(3),
                    rate-256Kbs(4),
                    rate-320Kbs(5),
                    rate-384Kbs(6),
                    rate-448Kbs(7),
                    rate-512Kbs(8),
                    rate-576Kbs(9),
                    rate-640Kbs(10),
                    rate-702Kbs(11),
                    rate-768Kbs(12),
                    rate-832Kbs(13),
                    rate-896Kbs(14),
                    rate-960Kbs(15)
                }
            ACCESS  read-write
            STATUS  mandatory
            DESCRIPTION
                "WAN Rate"
            ::= { confBasicControlEntry 11 }

        confFXS-L1-Conference  OBJECT-TYPE
            SYNTAX  INTEGER {
                    conference-1(1),
                    conference-2(2),
                    conference-3(3),
                    disable(4)
                }
            ACCESS  read-write
            STATUS  mandatory
            DESCRIPTION
                "FXS(L1) Conference Group"
            ::= { confBasicControlEntry 12 }

        confFXS-L2-Conference  OBJECT-TYPE
            SYNTAX  INTEGER {
                    conference-1(1),
                    conference-2(2),
                    conference-3(3),
                    disable(4)
                }
            ACCESS  read-write
            STATUS  mandatory
            DESCRIPTION
                "FXS(L2) Conference Group"
            ::= { confBasicControlEntry 13 }

        confEM-L3-Conference  OBJECT-TYPE
            SYNTAX  INTEGER {
                    conference-1(1),
                    conference-2(2),
                    conference-3(3),
                    disable(4)
                }
            ACCESS  read-write
            STATUS  mandatory
            DESCRIPTION
                "E&M(L3) Conference Group"
            ::= { confBasicControlEntry 14 }

        confEM-L4-Conference  OBJECT-TYPE
            SYNTAX  INTEGER {
                    conference-1(1),
                    conference-2(2),
                    conference-3(3),
                    disable(4)
                }
            ACCESS  read-write
            STATUS  mandatory
            DESCRIPTION
                "E&M(L4) Conference Group"
            ::= { confBasicControlEntry 15 }

        confMediaType  OBJECT-TYPE
            SYNTAX  INTEGER {
                    g711(1),
                    g723(2)
                }
            ACCESS  read-write
            STATUS  mandatory
            DESCRIPTION
                "Media Type"
            ::= { confBasicControlEntry 16 }

        confEchoCanceller  OBJECT-TYPE
            SYNTAX  INTEGER {
                    enable(1),
                    disable(2)
                }
            ACCESS  read-write
            STATUS  mandatory
            DESCRIPTION
                "Echo Canceller"
            ::= { confBasicControlEntry 17 }

        confPhoneMode  OBJECT-TYPE
            SYNTAX  INTEGER {
                    dailNumber(1),
                    hotline(2)
                }
            ACCESS  read-write
            STATUS  mandatory
            DESCRIPTION
                "Phone Mode"
            ::= { confBasicControlEntry 18 }

--
--  FXS Control Table
--
        confFxsControlTable  OBJECT-TYPE
            SYNTAX  SEQUENCE OF ConfFxsControlEntry
            ACCESS  not-accessible
            STATUS  mandatory
            DESCRIPTION
                "The conference FXS control table."
            ::= { conference-card 2 }

        confFxsControlEntry  OBJECT-TYPE
            SYNTAX  ConfFxsControlEntry
            ACCESS  not-accessible
            STATUS  mandatory
            DESCRIPTION
                "An entry in the conference FXS control table."
            INDEX { confFxsCtrlSlotIndex , confFxsCtrlPortIndex }
            ::= { confFxsControlTable 1 }

        ConfFxsControlEntry ::= SEQUENCE  {
            confFxsCtrlSlotIndex        LSSlotID,
            confFxsCtrlPortIndex        INTEGER,
            confFxsCtrlTxGain           INTEGER,
            confFxsCtrlRxGain           INTEGER,
            confFxsCtrlCadence          INTEGER
        }

        confFxsCtrlSlotIndex  OBJECT-TYPE
            SYNTAX  LSSlotID
            ACCESS  read-only
            STATUS  mandatory
            DESCRIPTION
                "CONF slot index"
            ::= { confFxsControlEntry 1 }

        confFxsCtrlPortIndex  OBJECT-TYPE
            SYNTAX  INTEGER {
                    fxs-l1(1),
                    fxs-l2(2)
                }
            ACCESS  read-only
            STATUS  mandatory
            DESCRIPTION
                "FXS L1 to L2, total 2 ports"
            ::= { confFxsControlEntry 2 }

        confFxsCtrlTxGain  OBJECT-TYPE
            SYNTAX  INTEGER {
                    gain-0-db(1),
                    gain-neg-6-db(2),
                    gain-6-db(3)
                }
            ACCESS  read-write
            STATUS  mandatory
            DESCRIPTION
                "FXS Tx gain"
            ::= { confFxsControlEntry 3 }

        confFxsCtrlRxGain  OBJECT-TYPE
            SYNTAX  INTEGER {
                    gain-0-db(1),
                    gain-6-db(2)
                }
            ACCESS  read-write
            STATUS  mandatory
            DESCRIPTION
                "FXS Rx gain"
            ::= { confFxsControlEntry 4 }

        confFxsCtrlCadence  OBJECT-TYPE
            SYNTAX  INTEGER {
                    cadence-1-on-2-off(2),
                    cadence-2-on-4-off(3)
                }
            ACCESS  read-write
            STATUS  mandatory
            DESCRIPTION
                "FXS ring cadence"
            ::= { confFxsControlEntry 5 }

--
--  E&M Control Table
--
        confEmControlTable  OBJECT-TYPE
            SYNTAX  SEQUENCE OF ConfEmControlEntry
            ACCESS  not-accessible
            STATUS  mandatory
            DESCRIPTION
                "The conference E&M control table."
            ::= { conference-card 3 }

        confEmControlEntry  OBJECT-TYPE
            SYNTAX  ConfEmControlEntry
            ACCESS  not-accessible
            STATUS  mandatory
            DESCRIPTION
                "An entry in the conference E&M control table."
            INDEX { confEmCtrlSlotIndex , confEmCtrlPortIndex }
            ::= { confEmControlTable 1 }

        ConfEmControlEntry ::= SEQUENCE  {
            confEmCtrlSlotIndex         LSSlotID,
            confEmCtrlPortIndex         INTEGER,
            confEmCtrlMode              INTEGER,
            confEmCtrlSide              INTEGER,
            confEmCtrlType              INTEGER,
            confEmCtrlTxGain            INTEGER,
            confEmCtrlRxGain            INTEGER,
            confEmCtrlCadence           INTEGER
        }

        confEmCtrlSlotIndex  OBJECT-TYPE
            SYNTAX  LSSlotID
            ACCESS  read-only
            STATUS  mandatory
            DESCRIPTION
                "CONF slot index"
            ::= { confEmControlEntry 1 }

        confEmCtrlPortIndex  OBJECT-TYPE
            SYNTAX  INTEGER {
                    em-l3(1),
                    em-l4(2)
                }
            ACCESS  read-only
            STATUS  mandatory
            DESCRIPTION
                "E&M L3 to L4, total 2 ports"
            ::= { confEmControlEntry 2 }

        confEmCtrlMode  OBJECT-TYPE
            SYNTAX  INTEGER {
                    standard(1),
                    master(2)
                }
            ACCESS  read-only
            STATUS  mandatory
            DESCRIPTION
                "E&M mode"
            ::= { confEmControlEntry 3 }

        confEmCtrlSide  OBJECT-TYPE
            SYNTAX  INTEGER {
                    side-a(1),
                    side-b(2)
                }
            ACCESS  read-only
            STATUS  mandatory
            DESCRIPTION
                "E&M side"
            ::= { confEmControlEntry 4 }

        confEmCtrlType  OBJECT-TYPE
            SYNTAX  INTEGER {
                    type1(2),
                    type4(5),
                    type5(6)
                }
            ACCESS  read-only
            STATUS  mandatory
            DESCRIPTION
                "E&M type"
            ::= { confEmControlEntry 5 }

        confEmCtrlTxGain  OBJECT-TYPE
            SYNTAX  INTEGER {
                    gain-0-db(1),
                    gain-neg-6-db(2),
                    gain-6-db(3)
                }
            ACCESS  read-write
            STATUS  mandatory
            DESCRIPTION
                "E&M Tx gain"
            ::= { confEmControlEntry 6 }

        confEmCtrlRxGain  OBJECT-TYPE
            SYNTAX  INTEGER {
                    gain-0-db(1),
                    gain-4-db(2)
                }
            ACCESS  read-write
            STATUS  mandatory
            DESCRIPTION
                "E&M Rx gain"
            ::= { confEmControlEntry 7 }

        confEmCtrlCadence  OBJECT-TYPE
            SYNTAX  INTEGER {
                    cadence-5-on(1),
                    cadence-1-on-2-off(2),
                    cadence-2-on-4-off(3)
                }
            ACCESS  read-write
            STATUS  mandatory
            DESCRIPTION
                "E&M ring cadence"
            ::= { confEmControlEntry 8 }

--
--  Conference Status Table
--
        confStatusTable  OBJECT-TYPE
            SYNTAX  SEQUENCE OF ConfStatusEntry
            ACCESS  not-accessible
            STATUS  mandatory
            DESCRIPTION
                "The conference status table."
            ::= { conference-card 4 }

        confStatusEntry  OBJECT-TYPE
            SYNTAX  ConfStatusEntry
            ACCESS  not-accessible
            STATUS  mandatory
            DESCRIPTION
                "An entry in the conference status table."
            INDEX { confStaIndex }
            ::= { confStatusTable 1 }

        ConfStatusEntry ::= SEQUENCE  {
            confStaIndex                LSSlotID,
            confStaMappingStatus        INTEGER,
            confStaFXS-L1-Hook          INTEGER,
            confStaFXS-L1-Ring          INTEGER,
            confStaFXS-L2-Hook          INTEGER,
            confStaFXS-L2-Ring          INTEGER,
            confStaEM-L3-ELeadHook      INTEGER,
            confStaEM-L3-MLeadRing      INTEGER,
            confStaEM-L4-ELeadHook      INTEGER,
            confStaEM-L4-MLeadRing      INTEGER
        }

        confStaIndex  OBJECT-TYPE
            SYNTAX  LSSlotID
            ACCESS  read-only
            STATUS  mandatory
            DESCRIPTION
                "CONF slot index"
            ::= { confStatusEntry 1 }

        confStaMappingStatus  OBJECT-TYPE
            SYNTAX  INTEGER {
                    ok(1),
                    fail(2),
                    port1-fail(3),
                    port2-fail(4)
                }
            ACCESS  read-only
            STATUS  mandatory
            DESCRIPTION
                "Conference mapping status"
            ::= { confStatusEntry 2 }

        confStaFXS-L1-Hook  OBJECT-TYPE
            SYNTAX  INTEGER {
                    off(1),
                    on(2)
                }
            ACCESS  read-only
            STATUS  mandatory
            DESCRIPTION
                "FXS L1 hook"
            ::= { confStatusEntry 3 }

        confStaFXS-L1-Ring  OBJECT-TYPE
            SYNTAX  INTEGER {
                    off(1),
                    on(2)
                }
            ACCESS  read-only
            STATUS  mandatory
            DESCRIPTION
                "FXS L1 ring"
            ::= { confStatusEntry 4 }

        confStaFXS-L2-Hook  OBJECT-TYPE
            SYNTAX  INTEGER {
                    off(1),
                    on(2)
                }
            ACCESS  read-only
            STATUS  mandatory
            DESCRIPTION
                "FXS L2 hook"
            ::= { confStatusEntry 5 }

        confStaFXS-L2-Ring  OBJECT-TYPE
            SYNTAX  INTEGER {
                    off(1),
                    on(2)
                }
            ACCESS  read-only
            STATUS  mandatory
            DESCRIPTION
                "FXS L2 ring"
            ::= { confStatusEntry 6 }

        confStaEM-L3-ELeadHook  OBJECT-TYPE
            SYNTAX  INTEGER {
                    off(1),
                    on(2)
                }
            ACCESS  read-only
            STATUS  mandatory
            DESCRIPTION
                "E&M L3 E-lead hook"
            ::= { confStatusEntry 7 }

        confStaEM-L3-MLeadRing  OBJECT-TYPE
            SYNTAX  INTEGER {
                    off(1),
                    on(2)
                }
            ACCESS  read-only
            STATUS  mandatory
            DESCRIPTION
                "E&M L3 M-lead ring"
            ::= { confStatusEntry 8 }

        confStaEM-L4-ELeadHook  OBJECT-TYPE
            SYNTAX  INTEGER {
                    off(1),
                    on(2)
                }
            ACCESS  read-only
            STATUS  mandatory
            DESCRIPTION
                "E&M L4 E-lead hook"
            ::= { confStatusEntry 9 }

        confStaEM-L4-MLeadRing  OBJECT-TYPE
            SYNTAX  INTEGER {
                    off(1),
                    on(2)
                }
            ACCESS  read-only
            STATUS  mandatory
            DESCRIPTION
                "E&M L4 M-lead ring"
            ::= { confStatusEntry 10 }

--
--  Command Control Table
--
        confCommandCtrlTable  OBJECT-TYPE
            SYNTAX  SEQUENCE OF ConfCommandCtrlEntry
            ACCESS  not-accessible
            STATUS  mandatory
            DESCRIPTION
                "The conference command control table."
            ::= { conference-card 5 }

        confCommandCtrlEntry  OBJECT-TYPE
            SYNTAX  ConfCommandCtrlEntry
            ACCESS  not-accessible
            STATUS  mandatory
            DESCRIPTION
                "An entry in the conference command control table."
            INDEX { confCmdCtrlIndex }
            ::= { confCommandCtrlTable 1 }

        ConfCommandCtrlEntry ::= SEQUENCE  {
            confCmdCtrlIndex            LSSlotID,
            confCmdCtrlReset            INTEGER,
            confCmdCtrlLoadDefault      INTEGER
        }

        confCmdCtrlIndex  OBJECT-TYPE
            SYNTAX  LSSlotID
            ACCESS  read-only
            STATUS  mandatory
            DESCRIPTION
                "CONF slot index"
            ::= { confCommandCtrlEntry 1 }

        confCmdCtrlReset  OBJECT-TYPE
            SYNTAX  INTEGER {
                    reset(1)
                }
            ACCESS  read-write
            STATUS  mandatory
            DESCRIPTION
                "Command: Reset"
            ::= { confCommandCtrlEntry 2 }

        confCmdCtrlLoadDefault  OBJECT-TYPE
            SYNTAX  INTEGER {
                    load-default(1)
                }
            ACCESS  read-write
            STATUS  mandatory
            DESCRIPTION
                "Command: Load Default"
            ::= { confCommandCtrlEntry 3 }

--
--  RS232 Control Table
--
        confRs232ControlTable  OBJECT-TYPE
            SYNTAX  SEQUENCE OF ConfRs232ControlEntry
            ACCESS  not-accessible
            STATUS  mandatory
            DESCRIPTION
                "The conference RS232 control table."
            ::= { conference-card 6 }

        confRs232ControlEntry  OBJECT-TYPE
            SYNTAX  ConfRs232ControlEntry
            ACCESS  not-accessible
            STATUS  mandatory
            DESCRIPTION
                "An entry in the conference RS232 control table."
            INDEX { confRs232CtrlSlotIndex , confRs232CtrlPortIndex }
            ::= { confRs232ControlTable 1 }

        ConfRs232ControlEntry ::= SEQUENCE  {
            confRs232CtrlSlotIndex      LSSlotID,
            confRs232CtrlPortIndex      INTEGER,
            confRs232CtrlMode           INTEGER,
            confRs232CtrlBaudRate       INTEGER,
            confRs232CtrlDataLength     INTEGER,
            confRs232CtrlStopBit        INTEGER,
            confRs232CtrlParity         INTEGER,
            confRs232CtrlRTS            INTEGER,
            confRs232CtrlOnTimer        INTEGER,
            confRs232CtrlOffTimer       INTEGER
        }

        confRs232CtrlSlotIndex  OBJECT-TYPE
            SYNTAX  LSSlotID
            ACCESS  read-only
            STATUS  mandatory
            DESCRIPTION
                "CONF slot index"
            ::= { confRs232ControlEntry 1 }

        confRs232CtrlPortIndex  OBJECT-TYPE
            SYNTAX  INTEGER {
                    rs232-d1(1),
                    rs232-d2(2)
                }
            ACCESS  read-only
            STATUS  mandatory
            DESCRIPTION
                "RS232 D1 to D2, total 2 ports"
            ::= { confRs232ControlEntry 2 }

        confRs232CtrlMode  OBJECT-TYPE
            SYNTAX  INTEGER {
                    slave(1),
                    master(2)
                }
            ACCESS  read-write
            STATUS  mandatory
            DESCRIPTION
                "RS232 master/slave mode"
            ::= { confRs232ControlEntry 3 }

        confRs232CtrlBaudRate  OBJECT-TYPE
            SYNTAX  INTEGER {
                    rate-300(1),
                    rate-600(2),
                    rate-1200(3),
                    rate-2400(4),
                    rate-4800(5),
                    rate-9600(6),
                    rate-19200(7)
                }
            ACCESS  read-write
            STATUS  mandatory
            DESCRIPTION
                "RS232 baud rate"
            ::= { confRs232ControlEntry 4 }

        confRs232CtrlDataLength  OBJECT-TYPE
            SYNTAX  INTEGER {
                    data-8-bits(1),
                    data-7-bits(2),
                    data-6-bits(3),
                    data-5-bits(4)
                }
            ACCESS  read-write
            STATUS  mandatory
            DESCRIPTION
                "RS232 data length"
            ::= { confRs232ControlEntry 5 }

        confRs232CtrlStopBit  OBJECT-TYPE
            SYNTAX  INTEGER {
                    stop-1-bit(1),
                    stop-2-bits(2)
                }
            ACCESS  read-write
            STATUS  mandatory
            DESCRIPTION
                "RS232 stop bit"
            ::= { confRs232ControlEntry 6 }

        confRs232CtrlParity  OBJECT-TYPE
            SYNTAX  INTEGER {
                    none(1),
                    even(2),
                    odd(3)
                }
            ACCESS  read-write
            STATUS  mandatory
            DESCRIPTION
                "RS232 parity"
            ::= { confRs232ControlEntry 7 }

        confRs232CtrlRTS  OBJECT-TYPE
            SYNTAX  INTEGER {
                    active(1),
                    permanent(2)
                }
            ACCESS  read-write
            STATUS  mandatory
            DESCRIPTION
                "RS232 RTS"
            ::= { confRs232ControlEntry 8 }

        confRs232CtrlOnTimer  OBJECT-TYPE
            SYNTAX  INTEGER (0..60)
            ACCESS  read-write
            STATUS  mandatory
            DESCRIPTION
                "RS232 on timer"
            ::= { confRs232ControlEntry 9 }

        confRs232CtrlOffTimer  OBJECT-TYPE
            SYNTAX  INTEGER (0..60)
            ACCESS  read-write
            STATUS  mandatory
            DESCRIPTION
                "RS232 off timer"
            ::= { confRs232ControlEntry 10 }

--
--  RS232 Status Table
--
        confRs232StatusTable  OBJECT-TYPE
            SYNTAX  SEQUENCE OF ConfRs232StatusEntry
            ACCESS  not-accessible
            STATUS  mandatory
            DESCRIPTION
                "The conference RS232 status table."
            ::= { conference-card 7 }

        confRs232StatusEntry  OBJECT-TYPE
            SYNTAX  ConfRs232StatusEntry
            ACCESS  not-accessible
            STATUS  mandatory
            DESCRIPTION
                "An entry in the conference RS232 status table."
            INDEX { confRs232StaSlotIndex , confRs232StaPortIndex }
            ::= { confRs232StatusTable 1 }

        ConfRs232StatusEntry ::= SEQUENCE  {
            confRs232StaSlotIndex       LSSlotID,
            confRs232StaPortIndex       INTEGER,
            confRs232StaRTS             INTEGER,
            confRs232StaCTS             INTEGER,
            confRs232StaDTR             INTEGER,
            confRs232StaDSR             INTEGER,
            confRs232StaDCD             INTEGER
        }

        confRs232StaSlotIndex  OBJECT-TYPE
            SYNTAX  LSSlotID
            ACCESS  read-only
            STATUS  mandatory
            DESCRIPTION
                "CONF slot index"
            ::= { confRs232StatusEntry 1 }

        confRs232StaPortIndex  OBJECT-TYPE
            SYNTAX  INTEGER {
                    rs232-d1(1),
                    rs232-d2(2)
                }
            ACCESS  read-only
            STATUS  mandatory
            DESCRIPTION
                "RS232 D1 to D2, total 2 ports"
            ::= { confRs232StatusEntry 2 }

        confRs232StaRTS  OBJECT-TYPE
            SYNTAX  INTEGER {
                    no(1),
                    yes(2)
                }
            ACCESS  read-only
            STATUS  mandatory
            DESCRIPTION
                "RS232 RTS status"
            ::= { confRs232StatusEntry 3 }

        confRs232StaCTS  OBJECT-TYPE
            SYNTAX  INTEGER {
                    no(1),
                    yes(2)
                }
            ACCESS  read-only
            STATUS  mandatory
            DESCRIPTION
                "RS232 CTS status"
            ::= { confRs232StatusEntry 4 }

        confRs232StaDTR  OBJECT-TYPE
            SYNTAX  INTEGER {
                    no(1),
                    yes(2)
                }
            ACCESS  read-only
            STATUS  mandatory
            DESCRIPTION
                "RS232 DTR status"
            ::= { confRs232StatusEntry 5 }

        confRs232StaDSR  OBJECT-TYPE
            SYNTAX  INTEGER {
                    no(1),
                    yes(2)
                }
            ACCESS  read-only
            STATUS  mandatory
            DESCRIPTION
                "RS232 DSR status"
            ::= { confRs232StatusEntry 6 }

        confRs232StaDCD  OBJECT-TYPE
            SYNTAX  INTEGER {
                    no(1),
                    yes(2)
                }
            ACCESS  read-only
            STATUS  mandatory
            DESCRIPTION
                "RS232 DCD status"
            ::= { confRs232StatusEntry 7 }

--
--  RS232 Loopback Table
--
        confRs232LoopbackTable  OBJECT-TYPE
            SYNTAX  SEQUENCE OF ConfRs232LoopbackEntry
            ACCESS  not-accessible
            STATUS  mandatory
            DESCRIPTION
                "The conference RS232 Loopback table."
            ::= { conference-card 8 }

        confRs232LoopbackEntry  OBJECT-TYPE
            SYNTAX  ConfRs232LoopbackEntry
            ACCESS  not-accessible
            STATUS  mandatory
            DESCRIPTION
                "An entry in the conference RS232 Loopback table."
            INDEX { confRs232LBSlotIndex }
            ::= { confRs232LoopbackTable 1 }

        ConfRs232LoopbackEntry ::= SEQUENCE  {
            confRs232LBSlotIndex      LSSlotID,
            confRs232D1Loopback         INTEGER,
            confRs232D2Loopback         INTEGER
        }

        confRs232LBSlotIndex  OBJECT-TYPE
            SYNTAX  LSSlotID
            ACCESS  read-only
            STATUS  mandatory
            DESCRIPTION
                "CONF slot index"
            ::= { confRs232LoopbackEntry 1 }

        confRs232D1Loopback  OBJECT-TYPE
            SYNTAX  INTEGER {
                    off(1),
                    to-local(2),
                    to-rs232(3)
                }
            ACCESS  read-write
            STATUS  mandatory
            DESCRIPTION
                "RS232 D1 loopback"
            ::= { confRs232LoopbackEntry 2 }

        confRs232D2Loopback  OBJECT-TYPE
            SYNTAX  INTEGER {
                    off(1),
                    to-local(2),
                    to-rs232(3)
                }
            ACCESS  read-write
            STATUS  mandatory
            DESCRIPTION
                "RS232 D1 loopback"
            ::= { confRs232LoopbackEntry 3 }

--
--  Group Call Table
--
        confGroupCallTable  OBJECT-TYPE
            SYNTAX  SEQUENCE OF ConfGroupCallEntry
            ACCESS  not-accessible
            STATUS  mandatory
            DESCRIPTION
                "The conference group call table."
            ::= { conference-card 9 }

        confGroupCallEntry  OBJECT-TYPE
            SYNTAX  ConfGroupCallEntry
            ACCESS  not-accessible
            STATUS  mandatory
            DESCRIPTION
                "An entry in the conference group call table."
            INDEX { confGroupCallSlotIndex , confGroupCallPortIndex }
            ::= { confGroupCallTable 1 }

        ConfGroupCallEntry ::= SEQUENCE  {
            confGroupCallSlotIndex      LSSlotID,
            confGroupCallPortIndex      INTEGER,
            confGroupCallGroupCall1     INTEGER,
            confGroupCallGroupCall2     INTEGER,
            confGroupCallGroupCall3     INTEGER,
            confGroupCallGroupCall4     INTEGER
        }

        confGroupCallSlotIndex  OBJECT-TYPE
            SYNTAX  LSSlotID
            ACCESS  read-only
            STATUS  mandatory
            DESCRIPTION
                "CONF slot index"
            ::= { confGroupCallEntry 1 }

        confGroupCallPortIndex  OBJECT-TYPE
            SYNTAX  INTEGER {
                    fxs-l1(1),
                    fxs-l2(2),
                    em-l3(3),
                    em-l4(4)
                }
            ACCESS  read-only
            STATUS  mandatory
            DESCRIPTION
                "FXS L1 to L2, E&M L3 to L4, total 4 ports"
            ::= { confGroupCallEntry 2 }

        confGroupCallGroupCall1  OBJECT-TYPE
            SYNTAX  INTEGER {
                    off(1),
                    no-90(2),
                    no-91(3),
                    no-92(4),
                    no-93(5),
                    no-94(6),
                    no-95(7),
                    no-96(8),
                    no-97(9),
                    no-98(10),
                    no-99(11),
                    no-AA(12),
                    no-BB(13),
                    no-CC(14),
                    no-DD(15)
                }
            ACCESS  read-write
            STATUS  mandatory
            DESCRIPTION
                "Group Call 1 Number"
            ::= { confGroupCallEntry 3 }

        confGroupCallGroupCall2  OBJECT-TYPE
            SYNTAX  INTEGER {
                    off(1),
                    no-90(2),
                    no-91(3),
                    no-92(4),
                    no-93(5),
                    no-94(6),
                    no-95(7),
                    no-96(8),
                    no-97(9),
                    no-98(10),
                    no-99(11),
                    no-AA(12),
                    no-BB(13),
                    no-CC(14),
                    no-DD(15)
                }
            ACCESS  read-write
            STATUS  mandatory
            DESCRIPTION
                "Group Call 2 Number"
            ::= { confGroupCallEntry 4 }

        confGroupCallGroupCall3  OBJECT-TYPE
            SYNTAX  INTEGER {
                    off(1),
                    no-90(2),
                    no-91(3),
                    no-92(4),
                    no-93(5),
                    no-94(6),
                    no-95(7),
                    no-96(8),
                    no-97(9),
                    no-98(10),
                    no-99(11),
                    no-AA(12),
                    no-BB(13),
                    no-CC(14),
                    no-DD(15)
                }
            ACCESS  read-write
            STATUS  mandatory
            DESCRIPTION
                "Group Call 3 Number"
            ::= { confGroupCallEntry 5 }

        confGroupCallGroupCall4  OBJECT-TYPE
            SYNTAX  INTEGER {
                    off(1),
                    no-90(2),
                    no-91(3),
                    no-92(4),
                    no-93(5),
                    no-94(6),
                    no-95(7),
                    no-96(8),
                    no-97(9),
                    no-98(10),
                    no-99(11),
                    no-AA(12),
                    no-BB(13),
                    no-CC(14),
                    no-DD(15)
                }
            ACCESS  read-write
            STATUS  mandatory
            DESCRIPTION
                "Group Call 4 Number"
            ::= { confGroupCallEntry 6 }

        confTotalCard   OBJECT-TYPE
            SYNTAX  INTEGER
            ACCESS  read-only
            STATUS  mandatory
            DESCRIPTION
                "Total cards of CONF"
            ::= { conference-card 100 }


--======================================================================--
--  triE1card MIB
--======================================================================--

--
--  Line Control Table
--

        triE1LineControlTable  OBJECT-TYPE
            SYNTAX  SEQUENCE OF TriE1LineControlEntry
            ACCESS  not-accessible
            STATUS  mandatory
            DESCRIPTION
                "The DS1 line control table."
            ::= { triE1card 1 }

        triE1LineControlEntry  OBJECT-TYPE
            SYNTAX  TriE1LineControlEntry
            ACCESS  not-accessible
            STATUS  mandatory
            DESCRIPTION
                "An entry in the DS1 line control table."
            INDEX { triE1LCSlotIndex , triE1LCPortIndex }
            ::= { triE1LineControlTable 1 }

        TriE1LineControlEntry ::= SEQUENCE  {
            triE1LCSlotIndex           LSSlotID,
            triE1LCPortIndex           ThreePortID,
            triE1LineFrame             INTEGER,
            triE1LineCoding            INTEGER,
            triE1Interface             INTEGER,
            triE1FDL                   INTEGER,
            triE1FDLSabit              INTEGER,
            triE1AIS                   INTEGER,
            triE1RAI                   INTEGER,
            triE1CRC                   INTEGER,
            triE1IdleCode              INTEGER,
            triE1CASMode               INTEGER,
            triE1SignallingMode        INTEGER,
            triE1CGA                   INTEGER,
            triE1OutOfService          INTEGER,
            triE1SNCPdelay             INTEGER,
            triE1SNCPsendAIS           INTEGER
        }

        triE1LCSlotIndex  OBJECT-TYPE
            SYNTAX  LSSlotID
            ACCESS  read-only
            STATUS  mandatory
            DESCRIPTION
                "3E1 slot index"
            ::= { triE1LineControlEntry 1 }

        triE1LCPortIndex  OBJECT-TYPE
            SYNTAX  ThreePortID
            ACCESS  read-only
            STATUS  mandatory
            DESCRIPTION
                "Port 1 to 3, total 3 ports."
            ::= { triE1LineControlEntry 2 }

        triE1LineFrame  OBJECT-TYPE
            SYNTAX  INTEGER   {
                    on(1),
                    off(2)
                }
            ACCESS  read-write
            STATUS  mandatory
            DESCRIPTION
                "Line frame format"
            ::= { triE1LineControlEntry 3 }

        triE1LineCoding  OBJECT-TYPE
            SYNTAX  INTEGER   {
                    ami(1),
                    hdb3(2)
                }
            ACCESS  read-write
            STATUS  mandatory
            DESCRIPTION
                "Line Coding type"
            ::= { triE1LineControlEntry 4 }

        triE1Interface  OBJECT-TYPE
            SYNTAX  INTEGER   {
                    twisted-pair(1),
                    coaxial-cable(2)
                }
            ACCESS  read-only
            STATUS  mandatory
            DESCRIPTION
                "Interface indicates that TriE1 line use 75/120 Ohm Cable."
            ::= { triE1LineControlEntry 5 }

        triE1FDL  OBJECT-TYPE
            SYNTAX  INTEGER   {
                    fdl(1),
                    off(2),
                    hdlc(3),
                    ssm(4)
--                        ssm-hdlc(5)
                }
            ACCESS  read-write
            STATUS  mandatory
            DESCRIPTION
                "TriE1 Facility Data Link ON/OFF"
            ::= { triE1LineControlEntry 6 }

        triE1FDLSabit  OBJECT-TYPE
            SYNTAX  INTEGER   {
                    sa4(1),
                    sa5(2),
                    sa6(3),
                    sa7(4),
                    sa8(5),
                    sa4-5(6)
                }
            ACCESS  read-write
            STATUS  mandatory
            DESCRIPTION
                "TriE1 Facility Data Link use Sax bit"
            ::= { triE1LineControlEntry 7 }

        triE1AIS  OBJECT-TYPE
            SYNTAX  INTEGER   {
                    frame(1),
--                    unframe(2),
                    off(3)
                }
            ACCESS  read-write
            STATUS  mandatory
            DESCRIPTION
                "TriE1 line Alarm Indication Signal."
            ::= { triE1LineControlEntry 8 }

        triE1RAI  OBJECT-TYPE
            SYNTAX  INTEGER   {
                    on(1),
                    off(2)
                }
            ACCESS  read-write
            STATUS  mandatory
            DESCRIPTION
                "RAI-ON indicates that RAI (Remote Alarm Indication) ON."
            ::= { triE1LineControlEntry 9 }

        triE1CRC  OBJECT-TYPE
            SYNTAX  INTEGER   {
                    on(1),
                    off(2)
                }
            ACCESS  read-write
            STATUS  mandatory
            DESCRIPTION
                "TriE1 Cycle Redundancy Check ON/OFF"
            ::= { triE1LineControlEntry 10 }

        triE1IdleCode  OBJECT-TYPE
            SYNTAX  INTEGER
            ACCESS  read-write
            STATUS  mandatory
            DESCRIPTION
                "Line Idle Code Value"
            ::= { triE1LineControlEntry 11 }

        triE1CASMode  OBJECT-TYPE
            SYNTAX  INTEGER   {
                    on(1),
                    off(2)
                }
            ACCESS  read-write
            STATUS  mandatory
            DESCRIPTION
                "CAS or CCS"
            ::= { triE1LineControlEntry 12 }

        triE1SignallingMode  OBJECT-TYPE
            SYNTAX  INTEGER   {
                    trans(1),
                    cd01(2)
                }
            ACCESS  read-write
            STATUS  mandatory
            DESCRIPTION
                "TRANS or CD01"
            ::= { triE1LineControlEntry 13 }

        triE1CGA  OBJECT-TYPE
            SYNTAX  INTEGER   {
                    norm(1)
                }
            ACCESS  read-write
            STATUS  mandatory
            DESCRIPTION
                "Method used to signal the Carrier Group Alarm state
                to the other end of the selected link."
            ::= { triE1LineControlEntry 14 }

        triE1OutOfService  OBJECT-TYPE
            SYNTAX  INTEGER   {
                    busy(1),
                    idle(2)
                }
            ACCESS  read-write
            STATUS  mandatory
            DESCRIPTION
                "When NORM (CGA) is select, the parameter determines the
                state of the A, B signaling bits during the
                Out-of-Service periods."
            ::= { triE1LineControlEntry 15 }

        triE1SNCPdelay  OBJECT-TYPE
            SYNTAX  INTEGER  (0..99)
            ACCESS  read-write
            STATUS  mandatory
            DESCRIPTION
                "DS0-SNCP port delay."
            ::= { triE1LineControlEntry 16 }

        triE1SNCPsendAIS  OBJECT-TYPE
            SYNTAX  INTEGER   {
                    on(1),
                    off(2)
                }
            ACCESS  read-write
            STATUS  mandatory
            DESCRIPTION
                "DS0-SNCP port send AIS."
            ::= { triE1LineControlEntry 17 }

--
--  User Current Performance Table
--

        triE1UserCurrPerfTable  OBJECT-TYPE
            SYNTAX  SEQUENCE OF TriE1UserCurrPerfEntry
            ACCESS  not-accessible
            STATUS  mandatory
            DESCRIPTION
                "User Current Performance Table"
            ::= { triE1card 2 }

        triE1UserCurrPerfEntry  OBJECT-TYPE
            SYNTAX  TriE1UserCurrPerfEntry
            ACCESS  not-accessible
            STATUS  mandatory
            DESCRIPTION
                "User current performance entry"
            INDEX { triE1UCPSlotIndex , triE1UCPPortIndex }
            ::= { triE1UserCurrPerfTable 1 }

        TriE1UserCurrPerfEntry ::= SEQUENCE  {
            triE1UCPSlotIndex          LSSlotID,
            triE1UCPPortIndex          ThreePortID,
            triE1UserCurrPerfES        INTEGER,
            triE1UserCurrPerfSES       INTEGER,
            triE1UserCurrPerfBES       INTEGER,
            triE1UserCurrPerfUAS       INTEGER,
            triE1UserCurrPerfCSS       INTEGER,
            triE1UserCurrPerfBPV       INTEGER,
            triE1UserCurrPerfDMs       INTEGER,
            triE1User15MinElapsed      INTEGER,
            triE1UserValid15Min        INTEGER
        }

        triE1UCPSlotIndex  OBJECT-TYPE
            SYNTAX  LSSlotID
            ACCESS  read-only
            STATUS  mandatory
            DESCRIPTION
                "3E1 slot index"
            ::= { triE1UserCurrPerfEntry 1 }

        triE1UCPPortIndex  OBJECT-TYPE
            SYNTAX  ThreePortID
            ACCESS  read-only
            STATUS  mandatory
            DESCRIPTION
                "Port 1 to 3, total 3 ports."
            ::= { triE1UserCurrPerfEntry 2 }

        triE1UserCurrPerfES  OBJECT-TYPE
            SYNTAX  INTEGER
            ACCESS  read-only
            STATUS  mandatory
            DESCRIPTION
                " ES Error Counter "
            ::= { triE1UserCurrPerfEntry 3 }

        triE1UserCurrPerfSES  OBJECT-TYPE
            SYNTAX  INTEGER
            ACCESS  read-only
            STATUS  mandatory
            DESCRIPTION
                " SES Error Counter "
            ::= { triE1UserCurrPerfEntry 4 }

        triE1UserCurrPerfBES  OBJECT-TYPE
            SYNTAX  INTEGER
            ACCESS  read-only
            STATUS  mandatory
            DESCRIPTION
                " BES Error Counter "
            ::= { triE1UserCurrPerfEntry 5 }

        triE1UserCurrPerfUAS  OBJECT-TYPE
            SYNTAX  INTEGER
            ACCESS  read-only
            STATUS  mandatory
            DESCRIPTION
                " UAS Error Counter "
            ::= { triE1UserCurrPerfEntry 6 }

        triE1UserCurrPerfCSS  OBJECT-TYPE
            SYNTAX  INTEGER
            ACCESS  read-only
            STATUS  mandatory
            DESCRIPTION
                " CS Error Counter "
            ::= { triE1UserCurrPerfEntry 7 }

        triE1UserCurrPerfBPV  OBJECT-TYPE
            SYNTAX  INTEGER
            ACCESS  read-only
            STATUS  mandatory
            DESCRIPTION
                " BPV Error Counter "
            ::= { triE1UserCurrPerfEntry 8 }

        triE1UserCurrPerfDMs  OBJECT-TYPE
            SYNTAX  INTEGER
            ACCESS  read-only
            STATUS  mandatory
            DESCRIPTION
                " DM Error Counter "
            ::= { triE1UserCurrPerfEntry 9 }

        triE1User15MinElapsed  OBJECT-TYPE
            SYNTAX  INTEGER
            ACCESS  read-only
            STATUS  mandatory
            DESCRIPTION
                " Current 15-minute time elapsed"
            ::= { triE1UserCurrPerfEntry 11 }

        triE1UserValid15Min  OBJECT-TYPE
            SYNTAX  INTEGER
            ACCESS  read-only
            STATUS  mandatory
            DESCRIPTION
                " Current 1-day Valid 15-min interval"
            ::= { triE1UserCurrPerfEntry 12 }


--
--  User Interval Performance Table
--

        triE1UserIntvPerfTable  OBJECT-TYPE
            SYNTAX  SEQUENCE OF TriE1UserIntvPerfEntry
            ACCESS  not-accessible
            STATUS  mandatory
            DESCRIPTION
                "User Interval Performance Table"
            ::= { triE1card 3 }

        triE1UserIntvPerfEntry  OBJECT-TYPE
            SYNTAX  TriE1UserIntvPerfEntry
            ACCESS  not-accessible
            STATUS  mandatory
            DESCRIPTION
                "User interval performance entry"
            INDEX { triE1UIPSlotIndex , triE1UIPPortIndex ,
                    triE1UserIntvPerfNumber }
            ::= { triE1UserIntvPerfTable 1 }

        TriE1UserIntvPerfEntry ::= SEQUENCE  {
            triE1UIPSlotIndex          LSSlotID,
            triE1UIPPortIndex          ThreePortID,
            triE1UserIntvPerfNumber    INTEGER  (1..96),
            triE1UserIntvPerfES        INTEGER,
            triE1UserIntvPerfSES       INTEGER,
            triE1UserIntvPerfBES       INTEGER,
            triE1UserIntvPerfUAS       INTEGER,
            triE1UserIntvPerfCSS       INTEGER,
            triE1UserIntvPerfBPV       INTEGER,
            triE1UserIntvPerfDMs       INTEGER
        }

        triE1UIPSlotIndex  OBJECT-TYPE
            SYNTAX  LSSlotID
            ACCESS  read-only
            STATUS  mandatory
            DESCRIPTION
                "3E1 slot index"
            ::= { triE1UserIntvPerfEntry 1 }

        triE1UIPPortIndex  OBJECT-TYPE
            SYNTAX  ThreePortID
            ACCESS  read-only
            STATUS  mandatory
            DESCRIPTION
                "Port 1 to 3, total 3 ports."
            ::= { triE1UserIntvPerfEntry 2 }

        triE1UserIntvPerfNumber  OBJECT-TYPE
            SYNTAX  INTEGER (1..96)
            ACCESS  read-only
            STATUS  mandatory
            DESCRIPTION
                "Interval Index"
            ::= { triE1UserIntvPerfEntry 3 }

        triE1UserIntvPerfES  OBJECT-TYPE
            SYNTAX  INTEGER
            ACCESS  read-only
            STATUS  mandatory
            DESCRIPTION
                " ES Error Counter "
            ::= { triE1UserIntvPerfEntry 4 }

        triE1UserIntvPerfSES  OBJECT-TYPE
            SYNTAX  INTEGER
            ACCESS  read-only
            STATUS  mandatory
            DESCRIPTION
                " SES Error Counter "
            ::= { triE1UserIntvPerfEntry 5 }

        triE1UserIntvPerfBES  OBJECT-TYPE
            SYNTAX  INTEGER
            ACCESS  read-only
            STATUS  mandatory
            DESCRIPTION
                " BES Error Counter "
            ::= { triE1UserIntvPerfEntry 6 }

        triE1UserIntvPerfUAS  OBJECT-TYPE
            SYNTAX  INTEGER
            ACCESS  read-only
            STATUS  mandatory
            DESCRIPTION
                " UAS Error Counter "
            ::= { triE1UserIntvPerfEntry 7 }

        triE1UserIntvPerfCSS  OBJECT-TYPE
            SYNTAX  INTEGER
            ACCESS  read-only
            STATUS  mandatory
            DESCRIPTION
                " CSS Error Counter "
            ::= { triE1UserIntvPerfEntry 8 }

        triE1UserIntvPerfBPV  OBJECT-TYPE
            SYNTAX  INTEGER
            ACCESS  read-only
            STATUS  mandatory
            DESCRIPTION
                " BPV Error Counter "
            ::= { triE1UserIntvPerfEntry 9 }

        triE1UserIntvPerfDMs   OBJECT-TYPE
            SYNTAX  INTEGER
            ACCESS  read-only
            STATUS  mandatory
            DESCRIPTION
                " DM Error Counter "
            ::= { triE1UserIntvPerfEntry 10 }


--
--  User Total Performance Table
--
        triE1UserTotalPerfTable  OBJECT-TYPE
            SYNTAX  SEQUENCE OF TriE1UserTotalPerfEntry
            ACCESS  not-accessible
            STATUS  mandatory
            DESCRIPTION
                "User Total Performance Table"
            ::= { triE1card 4 }

        triE1UserTotalPerfEntry  OBJECT-TYPE
            SYNTAX  TriE1UserTotalPerfEntry
            ACCESS  not-accessible
            STATUS  mandatory
            DESCRIPTION
                "User total performance entry"
            INDEX { triE1UTPSlotIndex , triE1UTPPortIndex }
            ::= { triE1UserTotalPerfTable 1 }

        TriE1UserTotalPerfEntry ::= SEQUENCE  {
            triE1UTPSlotIndex          LSSlotID,
            triE1UTPPortIndex          ThreePortID,
            triE1UserTotalPerfES       INTEGER,
            triE1UserTotalPerfSES      INTEGER,
            triE1UserTotalPerfBES      INTEGER,
            triE1UserTotalPerfUAS      INTEGER,
            triE1UserTotalPerfCSS      INTEGER,
            triE1UserTotalPerfBPV      INTEGER,
            triE1UserTotalPerfDMs      INTEGER
        }

        triE1UTPSlotIndex  OBJECT-TYPE
            SYNTAX  LSSlotID
            ACCESS  read-only
            STATUS  mandatory
            DESCRIPTION
                "3E1 slot index"
            ::= { triE1UserTotalPerfEntry 1 }

        triE1UTPPortIndex  OBJECT-TYPE
            SYNTAX  ThreePortID
            ACCESS  read-only
            STATUS  mandatory
            DESCRIPTION
                "Port 1 to 3, total 3 ports."
            ::= { triE1UserTotalPerfEntry 2 }

        triE1UserTotalPerfES  OBJECT-TYPE
            SYNTAX  INTEGER
            ACCESS  read-only
            STATUS  mandatory
            DESCRIPTION
                " ES Error Counter "
            ::= { triE1UserTotalPerfEntry 3 }

        triE1UserTotalPerfSES  OBJECT-TYPE
            SYNTAX  INTEGER
            ACCESS  read-only
            STATUS  mandatory
            DESCRIPTION
                " SES Error Counter "
            ::= { triE1UserTotalPerfEntry 4 }

        triE1UserTotalPerfBES  OBJECT-TYPE
            SYNTAX  INTEGER
            ACCESS  read-only
            STATUS  mandatory
            DESCRIPTION
                " BES Error Counter "
            ::= { triE1UserTotalPerfEntry 5 }

        triE1UserTotalPerfUAS  OBJECT-TYPE
            SYNTAX  INTEGER
            ACCESS  read-only
            STATUS  mandatory
            DESCRIPTION
                " UAS Error Counter "
            ::= { triE1UserTotalPerfEntry 6 }

        triE1UserTotalPerfCSS  OBJECT-TYPE
            SYNTAX  INTEGER
            ACCESS  read-only
            STATUS  mandatory
            DESCRIPTION
                " CSS Error Counter "
            ::= { triE1UserTotalPerfEntry 7 }

        triE1UserTotalPerfBPV  OBJECT-TYPE
            SYNTAX  INTEGER
            ACCESS  read-only
            STATUS  mandatory
            DESCRIPTION
                " BPV Error Counter "
            ::= { triE1UserTotalPerfEntry 8 }

        triE1UserTotalPerfDMs  OBJECT-TYPE
            SYNTAX  INTEGER
            ACCESS  read-only
            STATUS  mandatory
            DESCRIPTION
                " DM Error Counter "
            ::= { triE1UserTotalPerfEntry 9 }


--
--  User Seven Days Performance Table
--
        triE1User7DaysPerfTable  OBJECT-TYPE
            SYNTAX  SEQUENCE OF TriE1User7DaysPerfEntry
            ACCESS  not-accessible
            STATUS  mandatory
            DESCRIPTION
                "User 7 Days Performance Table"
            ::= { triE1card 5 }

        triE1User7DaysPerfEntry  OBJECT-TYPE
            SYNTAX  TriE1User7DaysPerfEntry
            ACCESS  not-accessible
            STATUS  mandatory
            DESCRIPTION
                "User 7 days performance table"
            INDEX { triE1USDSlotIndex , triE1USDPortIndex ,
                    triE1UserDaysIndex }
            ::= { triE1User7DaysPerfTable 1 }

        TriE1User7DaysPerfEntry ::= SEQUENCE  {
            triE1USDSlotIndex      LSSlotID,
            triE1USDPortIndex      ThreePortID,
            triE1UserDaysIndex     INTEGER (1..7),
            triE1UserDateStrIndex  DisplayString (SIZE (0..255) ),
            triE1User7DaysPerfES   INTEGER,
            triE1User7DaysPerfSES  INTEGER,
            triE1User7DaysPerfBES  INTEGER,
            triE1User7DaysPerfUAS  INTEGER,
            triE1User7DaysPerfCSS  INTEGER,
            triE1User7DaysPerfDMs  INTEGER,
            triE1User7DaysPerfBPV  INTEGER
        }

        triE1USDSlotIndex  OBJECT-TYPE
            SYNTAX  LSSlotID
            ACCESS  read-only
            STATUS  mandatory
            DESCRIPTION
                "3E1 slot index"
            ::= { triE1User7DaysPerfEntry 1 }

        triE1USDPortIndex  OBJECT-TYPE
            SYNTAX  ThreePortID
            ACCESS  read-only
            STATUS  mandatory
            DESCRIPTION
                "Port 1 to 3, total 3 ports."
            ::= { triE1User7DaysPerfEntry 2 }

        triE1UserDaysIndex  OBJECT-TYPE
            SYNTAX  INTEGER (1..7)
            ACCESS  read-only
            STATUS  mandatory
            DESCRIPTION
                "Seven Days index "
            ::= { triE1User7DaysPerfEntry 3 }

        triE1UserDateStrIndex  OBJECT-TYPE
            SYNTAX  DisplayString (SIZE (0..255) )
            ACCESS  read-only
            STATUS  mandatory
            DESCRIPTION
                "Seven Days String "
            ::= { triE1User7DaysPerfEntry 4 }

        triE1User7DaysPerfES  OBJECT-TYPE
            SYNTAX  INTEGER
            ACCESS  read-only
            STATUS  mandatory
            DESCRIPTION
                " ES Error Counter "
            ::= { triE1User7DaysPerfEntry 5 }

        triE1User7DaysPerfSES  OBJECT-TYPE
            SYNTAX  INTEGER
            ACCESS  read-only
            STATUS  mandatory
            DESCRIPTION
                " SES Error Counter "
            ::= { triE1User7DaysPerfEntry 6 }

        triE1User7DaysPerfBES  OBJECT-TYPE
            SYNTAX  INTEGER
            ACCESS  read-only
            STATUS  mandatory
            DESCRIPTION
                " BES Error Counter "
            ::= { triE1User7DaysPerfEntry 7 }

        triE1User7DaysPerfUAS  OBJECT-TYPE
            SYNTAX  INTEGER
            ACCESS  read-only
            STATUS  mandatory
            DESCRIPTION
                " UAS Error Counter "
            ::= { triE1User7DaysPerfEntry 8 }

        triE1User7DaysPerfCSS  OBJECT-TYPE
            SYNTAX  INTEGER
            ACCESS  read-only
            STATUS  mandatory
            DESCRIPTION
                " CSS Error Counter "
            ::= { triE1User7DaysPerfEntry 9 }

        triE1User7DaysPerfDMs  OBJECT-TYPE
            SYNTAX  INTEGER
            ACCESS  read-only
            STATUS  mandatory
            DESCRIPTION
                " DM Error Counter "
            ::= { triE1User7DaysPerfEntry 10 }

        triE1User7DaysPerfBPV  OBJECT-TYPE
            SYNTAX  INTEGER
            ACCESS  read-only
            STATUS  mandatory
            DESCRIPTION
                " BPV Error Counter "
            ::= { triE1User7DaysPerfEntry 11 }


--
--  Line Current Performance Table
--

        triE1LineCurrPerfTable  OBJECT-TYPE
            SYNTAX  SEQUENCE OF TriE1LineCurrPerfEntry
            ACCESS  not-accessible
            STATUS  mandatory
            DESCRIPTION
                "Line Current Performance Table"
            ::= { triE1card 10 }

        triE1LineCurrPerfEntry  OBJECT-TYPE
            SYNTAX  TriE1LineCurrPerfEntry
            ACCESS  not-accessible
            STATUS  mandatory
            DESCRIPTION
                "Line current performance entry"
            INDEX { triE1LCPSlotIndex , triE1LCPPortIndex }
            ::= { triE1LineCurrPerfTable 1 }

        TriE1LineCurrPerfEntry ::= SEQUENCE  {
            triE1LCPSlotIndex          LSSlotID,
            triE1LCPPortIndex          ThreePortID,
            triE1LineCurrPerfES        INTEGER,
            triE1LineCurrPerfSES       INTEGER,
            triE1LineCurrPerfBES       INTEGER,
            triE1LineCurrPerfUAS       INTEGER,
            triE1LineCurrPerfCSS       INTEGER,
            triE1LineCurrPerfBPV       INTEGER,
            triE1LineCurrPerfDMs       INTEGER,
            triE1Line15MinElapsed      INTEGER,
            triE1LineValid15Min        INTEGER
        }

        triE1LCPSlotIndex  OBJECT-TYPE
            SYNTAX  LSSlotID
            ACCESS  read-only
            STATUS  mandatory
            DESCRIPTION
                "3E1 slot index"
            ::= { triE1LineCurrPerfEntry 1 }

        triE1LCPPortIndex  OBJECT-TYPE
            SYNTAX  ThreePortID
            ACCESS  read-only
            STATUS  mandatory
            DESCRIPTION
                "Port 1 to 3, total 3 ports."
            ::= { triE1LineCurrPerfEntry 2 }

        triE1LineCurrPerfES  OBJECT-TYPE
            SYNTAX  INTEGER
            ACCESS  read-only
            STATUS  mandatory
            DESCRIPTION
                " ESS Error Counter "
            ::= { triE1LineCurrPerfEntry 3 }

        triE1LineCurrPerfSES  OBJECT-TYPE
            SYNTAX  INTEGER
            ACCESS  read-only
            STATUS  mandatory
            DESCRIPTION
                " SES Error Counter "
            ::= { triE1LineCurrPerfEntry 4 }

        triE1LineCurrPerfBES  OBJECT-TYPE
            SYNTAX  INTEGER
            ACCESS  read-only
            STATUS  mandatory
            DESCRIPTION
                " BES Error Counter "
            ::= { triE1LineCurrPerfEntry 5 }

        triE1LineCurrPerfUAS  OBJECT-TYPE
            SYNTAX  INTEGER
            ACCESS  read-only
            STATUS  mandatory
            DESCRIPTION
                " UAS Error Counter "
            ::= { triE1LineCurrPerfEntry 6 }

        triE1LineCurrPerfCSS  OBJECT-TYPE
            SYNTAX  INTEGER
            ACCESS  read-only
            STATUS  mandatory
            DESCRIPTION
                " CSS Error Counter "
            ::= { triE1LineCurrPerfEntry 7 }

        triE1LineCurrPerfBPV  OBJECT-TYPE
            SYNTAX  INTEGER
            ACCESS  read-only
            STATUS  mandatory
            DESCRIPTION
                " BPV Error Counter "
            ::= { triE1LineCurrPerfEntry 8 }

        triE1LineCurrPerfDMs  OBJECT-TYPE
            SYNTAX  INTEGER
            ACCESS  read-only
            STATUS  mandatory
            DESCRIPTION
                " DM Error Counter "
            ::= { triE1LineCurrPerfEntry 9 }

        triE1Line15MinElapsed  OBJECT-TYPE
            SYNTAX  INTEGER
            ACCESS  read-only
            STATUS  mandatory
            DESCRIPTION
                " Current 15-minute time elapsed"
            ::= { triE1LineCurrPerfEntry 11 }

        triE1LineValid15Min  OBJECT-TYPE
            SYNTAX  INTEGER
            ACCESS  read-only
            STATUS  mandatory
            DESCRIPTION
                " Current 1-day Valid 15-min interval"
            ::= { triE1LineCurrPerfEntry 12 }


--
--  Line Interval Performance Table
--

        triE1LineIntvPerfTable  OBJECT-TYPE
            SYNTAX  SEQUENCE OF TriE1LineIntvPerfEntry
            ACCESS  not-accessible
            STATUS  mandatory
            DESCRIPTION
                "Line Interval Performance Table"
            ::= { triE1card 11 }

        triE1LineIntvPerfEntry  OBJECT-TYPE
            SYNTAX  TriE1LineIntvPerfEntry
            ACCESS  not-accessible
            STATUS  mandatory
            DESCRIPTION
                "Line interval performance entry"
            INDEX { triE1LIPSlotIndex , triE1LIPPortIndex ,
                    triE1LineIntvPerfNumber }
            ::= { triE1LineIntvPerfTable 1 }

        TriE1LineIntvPerfEntry ::= SEQUENCE {
            triE1LIPSlotIndex           LSSlotID,
            triE1LIPPortIndex           ThreePortID,
            triE1LineIntvPerfNumber     INTEGER  (1..96),
            triE1LineIntvPerfES         INTEGER,
            triE1LineIntvPerfSES        INTEGER,
            triE1LineIntvPerfBES        INTEGER,
            triE1LineIntvPerfUAS        INTEGER,
            triE1LineIntvPerfCSS        INTEGER,
            triE1LineIntvPerfBPV        INTEGER,
            triE1LineIntvPerfDMs        INTEGER,
            triE1LineIntvAvailable      INTEGER
        }

        triE1LIPSlotIndex  OBJECT-TYPE
            SYNTAX  LSSlotID
            ACCESS  read-only
            STATUS  mandatory
            DESCRIPTION
                "3E1 slot index"
            ::= { triE1LineIntvPerfEntry 1 }

        triE1LIPPortIndex  OBJECT-TYPE
            SYNTAX  ThreePortID
            ACCESS  read-only
            STATUS  mandatory
            DESCRIPTION
                "Port 1 to 3, total 3 ports."
            ::= { triE1LineIntvPerfEntry 2 }

        triE1LineIntvPerfNumber  OBJECT-TYPE
            SYNTAX  INTEGER (1..96)
            ACCESS  read-only
            STATUS  mandatory
            DESCRIPTION
                " Interval Index "
            ::= { triE1LineIntvPerfEntry 3 }

        triE1LineIntvPerfES  OBJECT-TYPE
            SYNTAX  INTEGER
            ACCESS  read-only
            STATUS  mandatory
            DESCRIPTION
                " ES Error Counter "
            ::= { triE1LineIntvPerfEntry 4 }

        triE1LineIntvPerfSES  OBJECT-TYPE
            SYNTAX  INTEGER
            ACCESS  read-only
            STATUS  mandatory
            DESCRIPTION
                " SES Error Counter "
            ::= { triE1LineIntvPerfEntry 5 }

        triE1LineIntvPerfBES  OBJECT-TYPE
            SYNTAX  INTEGER
            ACCESS  read-only
            STATUS  mandatory
            DESCRIPTION
                " BES Error Counter "
            ::= { triE1LineIntvPerfEntry 6 }

        triE1LineIntvPerfUAS  OBJECT-TYPE
            SYNTAX  INTEGER
            ACCESS  read-only
            STATUS  mandatory
            DESCRIPTION
                " UAS Error Counter "
            ::= { triE1LineIntvPerfEntry 7 }

        triE1LineIntvPerfCSS  OBJECT-TYPE
            SYNTAX  INTEGER
            ACCESS  read-only
            STATUS  mandatory
            DESCRIPTION
                " CSS Error Counter "
            ::= { triE1LineIntvPerfEntry 8 }

        triE1LineIntvPerfBPV  OBJECT-TYPE
            SYNTAX  INTEGER
            ACCESS  read-only
            STATUS  mandatory
            DESCRIPTION
                " BPV Error Counter "
            ::= { triE1LineIntvPerfEntry 9 }

        triE1LineIntvPerfDMs  OBJECT-TYPE
            SYNTAX  INTEGER
            ACCESS  read-only
            STATUS  mandatory
            DESCRIPTION
                " BPV Error Counter "
            ::= { triE1LineIntvPerfEntry 10 }

        triE1LineIntvAvailable  OBJECT-TYPE
            SYNTAX  INTEGER   {
                    available(1),
                    na(2)
                }
            ACCESS  read-only
            STATUS  mandatory
            DESCRIPTION
                " Interval Available "
            ::= { triE1LineIntvPerfEntry 11 }


--
--  Line Total Performance Table
--

        triE1LineTotalPerfTable  OBJECT-TYPE
            SYNTAX  SEQUENCE OF TriE1LineTotalPerfEntry
            ACCESS  not-accessible
            STATUS  mandatory
            DESCRIPTION
                "Line Total Performance Table"
            ::= { triE1card 12 }

        triE1LineTotalPerfEntry  OBJECT-TYPE
            SYNTAX  TriE1LineTotalPerfEntry
            ACCESS  not-accessible
            STATUS  mandatory
            DESCRIPTION
                "Line total performance table"
            INDEX { triE1LTPSlotIndex , triE1LTPPortIndex }
            ::= { triE1LineTotalPerfTable 1 }

        TriE1LineTotalPerfEntry ::= SEQUENCE  {
            triE1LTPSlotIndex          LSSlotID,
            triE1LTPPortIndex          ThreePortID,
            triE1LineTotalPerfES       INTEGER,
            triE1LineTotalPerfSES      INTEGER,
            triE1LineTotalPerfBES      INTEGER,
            triE1LineTotalPerfUAS      INTEGER,
            triE1LineTotalPerfCSS      INTEGER,
            triE1LineTotalPerfBPV      INTEGER,
            triE1LineTotalPerfDMs      INTEGER
        }

        triE1LTPSlotIndex  OBJECT-TYPE
            SYNTAX  LSSlotID
            ACCESS  read-only
            STATUS  mandatory
            DESCRIPTION
                "3E1 slot index"
            ::= { triE1LineTotalPerfEntry 1 }

        triE1LTPPortIndex  OBJECT-TYPE
            SYNTAX  ThreePortID
            ACCESS  read-only
            STATUS  mandatory
            DESCRIPTION
                "Port 1 to 3, total 3 ports."
            ::= { triE1LineTotalPerfEntry 2 }

        triE1LineTotalPerfES  OBJECT-TYPE
            SYNTAX  INTEGER
            ACCESS  read-only
            STATUS  mandatory
            DESCRIPTION
                " ES Error Counter "
            ::= { triE1LineTotalPerfEntry 3 }

        triE1LineTotalPerfSES  OBJECT-TYPE
            SYNTAX  INTEGER
            ACCESS  read-only
            STATUS  mandatory
            DESCRIPTION
                " SES Error Counter "
            ::= { triE1LineTotalPerfEntry 4 }

        triE1LineTotalPerfBES  OBJECT-TYPE
            SYNTAX  INTEGER
            ACCESS  read-only
            STATUS  mandatory
            DESCRIPTION
                " BES Error Counter "
            ::= { triE1LineTotalPerfEntry 5 }

        triE1LineTotalPerfUAS  OBJECT-TYPE
            SYNTAX  INTEGER
            ACCESS  read-only
            STATUS  mandatory
            DESCRIPTION
                " UAS Error Counter "
            ::= { triE1LineTotalPerfEntry 6 }

        triE1LineTotalPerfCSS  OBJECT-TYPE
            SYNTAX  INTEGER
            ACCESS  read-only
            STATUS  mandatory
            DESCRIPTION
                " CSS Error Counter "
            ::= { triE1LineTotalPerfEntry 7 }

        triE1LineTotalPerfBPV  OBJECT-TYPE
            SYNTAX  INTEGER
            ACCESS  read-only
            STATUS  mandatory
            DESCRIPTION
                " BPV Error Counter "
            ::= { triE1LineTotalPerfEntry 8 }

        triE1LineTotalPerfDMs  OBJECT-TYPE
            SYNTAX  INTEGER
            ACCESS  read-only
            STATUS  mandatory
            DESCRIPTION
                " DM Error Counter "
            ::= { triE1LineTotalPerfEntry 9 }


--
--  Line Seven Days Performance Table
--
        triE1Line7DaysPerfTable  OBJECT-TYPE
            SYNTAX  SEQUENCE OF TriE1Line7DaysPerfEntry
            ACCESS  not-accessible
            STATUS  mandatory
            DESCRIPTION
                "Line 7 Days Performance Table"
            ::= { triE1card 13 }

        triE1Line7DaysPerfEntry  OBJECT-TYPE
            SYNTAX  TriE1Line7DaysPerfEntry
            ACCESS  not-accessible
            STATUS  mandatory
            DESCRIPTION
                "Line 7 days performance entry"
            INDEX { triE1LSPSlotIndex , triE1LSPPortIndex ,
                    triE1LineDaysIndex }
            ::= { triE1Line7DaysPerfTable 1 }

        TriE1Line7DaysPerfEntry ::= SEQUENCE  {
            triE1LSPSlotIndex      LSSlotID,
            triE1LSPPortIndex      ThreePortID,
            triE1LineDaysIndex     INTEGER (1..7),
            triE1LineDateStrIndex  DisplayString (SIZE (0..255) ),
            triE1Line7DaysPerfES   INTEGER,
            triE1Line7DaysPerfSES  INTEGER,
            triE1Line7DaysPerfBES  INTEGER,
            triE1Line7DaysPerfUAS  INTEGER,
            triE1Line7DaysPerfCSS  INTEGER,
            triE1Line7DaysPerfDMs  INTEGER,
            triE1Line7DaysPerfBPV  INTEGER
        }

        triE1LSPSlotIndex  OBJECT-TYPE
            SYNTAX  LSSlotID
            ACCESS  read-only
            STATUS  mandatory
            DESCRIPTION
                "3E1 slot index"
            ::= { triE1Line7DaysPerfEntry 1 }

        triE1LSPPortIndex  OBJECT-TYPE
            SYNTAX  ThreePortID
            ACCESS  read-only
            STATUS  mandatory
            DESCRIPTION
                "Port 1 to 3, total 3 ports."
            ::= { triE1Line7DaysPerfEntry 2 }

        triE1LineDaysIndex  OBJECT-TYPE
            SYNTAX  INTEGER (1..7)
            ACCESS  read-only
            STATUS  mandatory
            DESCRIPTION
                "Seven Days index "
            ::= { triE1Line7DaysPerfEntry 3 }

        triE1LineDateStrIndex  OBJECT-TYPE
            SYNTAX  DisplayString (SIZE (0..255) )
            ACCESS  read-only
            STATUS  mandatory
            DESCRIPTION
                "Seven Days String "
            ::= { triE1Line7DaysPerfEntry 4 }

        triE1Line7DaysPerfES  OBJECT-TYPE
            SYNTAX  INTEGER
            ACCESS  read-only
            STATUS  mandatory
            DESCRIPTION
                " ES Error Counter "
            ::= { triE1Line7DaysPerfEntry 5 }

        triE1Line7DaysPerfSES  OBJECT-TYPE
            SYNTAX  INTEGER
            ACCESS  read-only
            STATUS  mandatory
            DESCRIPTION
                " SES Error Counter "
            ::= { triE1Line7DaysPerfEntry 6 }

        triE1Line7DaysPerfBES  OBJECT-TYPE
            SYNTAX  INTEGER
            ACCESS  read-only
            STATUS  mandatory
            DESCRIPTION
                " BES Error Counter "
            ::= { triE1Line7DaysPerfEntry 7 }

        triE1Line7DaysPerfUAS  OBJECT-TYPE
            SYNTAX  INTEGER
            ACCESS  read-only
            STATUS  mandatory
            DESCRIPTION
                " UAS Error Counter "
            ::= { triE1Line7DaysPerfEntry 8 }

        triE1Line7DaysPerfCSS  OBJECT-TYPE
            SYNTAX  INTEGER
            ACCESS  read-only
            STATUS  mandatory
            DESCRIPTION
                " CSS Error Counter "
            ::= { triE1Line7DaysPerfEntry 9 }

        triE1Line7DaysPerfDMs  OBJECT-TYPE
            SYNTAX  INTEGER
            ACCESS  read-only
            STATUS  mandatory
            DESCRIPTION
                " DM Error Counter "
            ::= { triE1Line7DaysPerfEntry 10 }

        triE1Line7DaysPerfBPV  OBJECT-TYPE
            SYNTAX  INTEGER
            ACCESS  read-only
            STATUS  mandatory
            DESCRIPTION
                " BPV Error Counter "
            ::= { triE1Line7DaysPerfEntry 11 }


--
--  Alarm History Table
--

        triE1AlarmHistoryTable  OBJECT-TYPE
            SYNTAX  SEQUENCE OF TriE1AlarmHistoryEntry
            ACCESS  not-accessible
            STATUS  mandatory
            DESCRIPTION
                "Alarm History Table"
            ::= { triE1card 15 }

        triE1AlarmHistoryEntry  OBJECT-TYPE
            SYNTAX  TriE1AlarmHistoryEntry
            ACCESS  not-accessible
            STATUS  mandatory
            DESCRIPTION
                "Alarm history entry"
            INDEX { triE1AHSlotIndex , triE1AHPortIndex ,
                    triE1AlarmHistoryIndex }
            ::= { triE1AlarmHistoryTable 1 }

        TriE1AlarmHistoryEntry ::= SEQUENCE {
            triE1AHSlotIndex           LSSlotID,
            triE1AHPortIndex           ThreePortID,
            triE1AlarmHistoryIndex     INTEGER,
            triE1Threshold             INTEGER,
            triE1CurrentState          INTEGER,
            triE1CurrentCount          INTEGER,
            triE1Alarm                 LsAlarmSeverity
        }

        triE1AHSlotIndex  OBJECT-TYPE
            SYNTAX  LSSlotID
            ACCESS  read-only
            STATUS  mandatory
            DESCRIPTION
                "3E1 slot index"
            ::= { triE1AlarmHistoryEntry 1 }

        triE1AHPortIndex  OBJECT-TYPE
            SYNTAX  ThreePortID
            ACCESS  read-only
            STATUS  mandatory
            DESCRIPTION
                "Port 1 to 3, total 3 ports."
            ::= { triE1AlarmHistoryEntry 2 }

        triE1AlarmHistoryIndex  OBJECT-TYPE
            SYNTAX  INTEGER {
                    rai-line(1),
                    ais-line(2),
                    los-line(3),
                    lof-line(4),
                    bpv-line(5),
                    ess-line(6),
                    uas-line(7),
                    css-line(8),
                    ais-insert(9)
                }
            ACCESS  read-only
            STATUS  mandatory
            DESCRIPTION
                " Alarm History Index "
            ::= { triE1AlarmHistoryEntry 3 }

        triE1Threshold  OBJECT-TYPE
            SYNTAX  INTEGER
            ACCESS  read-only
            STATUS  mandatory
            DESCRIPTION
                " Alarm History Threshold Value "
            ::= { triE1AlarmHistoryEntry 4 }

        triE1CurrentState  OBJECT-TYPE
            SYNTAX  INTEGER {
                    ok(1),
                    alarm(2),
                    disable(3)
                }
            ACCESS  read-only
            STATUS  mandatory
            DESCRIPTION
                " Alarm History Current State"
            ::= { triE1AlarmHistoryEntry 5 }

        triE1CurrentCount  OBJECT-TYPE
            SYNTAX  INTEGER
            ACCESS  read-only
            STATUS  mandatory
            DESCRIPTION
                " Alarm History Current Count "
            ::= { triE1AlarmHistoryEntry 6 }

        triE1Alarm  OBJECT-TYPE
            SYNTAX  LsAlarmSeverity
            ACCESS  read-only
            STATUS  mandatory
            DESCRIPTION
                "Alarm History Alarm State"
            ::= { triE1AlarmHistoryEntry 7 }


--
--  Line Availability Table
--

        triE1LineAvailTable  OBJECT-TYPE
            SYNTAX  SEQUENCE OF TriE1LineAvailEntry
            ACCESS  not-accessible
            STATUS  mandatory
            DESCRIPTION
                "The DS1 line control table."
            ::= { triE1card 16 }

        triE1LineAvailEntry  OBJECT-TYPE
            SYNTAX  TriE1LineAvailEntry
            ACCESS  not-accessible
            STATUS  mandatory
            DESCRIPTION
                "An entry in the DS1 line control table."
            INDEX { triE1LASlotIndex , triE1LAPortIndex }
            ::= { triE1LineAvailTable 1 }

        TriE1LineAvailEntry ::= SEQUENCE {
            triE1LASlotIndex           LSSlotID,
            triE1LAPortIndex           ThreePortID,
            triE1AvailableSeconds      DisplayString,
            triE1UnavailableSeconds    DisplayString,
            triE1LineAvailability      DisplayString
        }

        triE1LASlotIndex  OBJECT-TYPE
            SYNTAX  LSSlotID
            ACCESS  read-only
            STATUS  mandatory
            DESCRIPTION
                "3E1 slot index"
            ::= { triE1LineAvailEntry 1 }

        triE1LAPortIndex  OBJECT-TYPE
            SYNTAX  ThreePortID
            ACCESS  read-only
            STATUS  mandatory
            DESCRIPTION
                "Port 1 to 3, total 3 ports."
            ::= { triE1LineAvailEntry 2 }

        triE1AvailableSeconds  OBJECT-TYPE
            SYNTAX  DisplayString (SIZE(0..255))
            ACCESS  read-only
            STATUS  mandatory
            DESCRIPTION
                "Line Available Seconds"
            ::= { triE1LineAvailEntry 3 }

        triE1UnavailableSeconds  OBJECT-TYPE
            SYNTAX  DisplayString (SIZE(0..255))
            ACCESS  read-only
            STATUS  mandatory
            DESCRIPTION
                "Line Unavailable Seconds"
            ::= { triE1LineAvailEntry 4 }

        triE1LineAvailability  OBJECT-TYPE
            SYNTAX  DisplayString (SIZE(0..255))
            ACCESS  read-only
            STATUS  mandatory
            DESCRIPTION
                "Line Available Percentage"
            ::= { triE1LineAvailEntry 5 }


--
--  Alarm Control Table
--

        triE1AlarmControlTable  OBJECT-TYPE
            SYNTAX  SEQUENCE OF TriE1AlarmControlEntry
            ACCESS  not-accessible
            STATUS  mandatory
            DESCRIPTION
                "The alarm control table."
            ::= { triE1card 17 }

        triE1AlarmControlEntry  OBJECT-TYPE
            SYNTAX  TriE1AlarmControlEntry
            ACCESS  not-accessible
            STATUS  mandatory
            DESCRIPTION
                "An entry in the DS1 alarm control table."
            INDEX { triE1ACSlotIndex , triE1ACPortIndex }
            ::= { triE1AlarmControlTable 1 }

        TriE1AlarmControlEntry ::= SEQUENCE {
            triE1ACSlotIndex           LSSlotID,
            triE1ACPortIndex           ThreePortID,
            triE1RAILine               LsAlarmSeverity,
            triE1AISLine               LsAlarmSeverity,
            triE1LOSLine               LsAlarmSeverity,
            triE1LOFLine               LsAlarmSeverity,
            triE1BPVLine               LsAlarmSeverity,
            triE1ESSLine               LsAlarmSeverity,
            triE1UASLine               LsAlarmSeverity,
            triE1CSSLine               LsAlarmSeverity,
            triE1AISinsert             LsAlarmSeverity
        }

        triE1ACSlotIndex  OBJECT-TYPE
            SYNTAX  LSSlotID
            ACCESS  read-only
            STATUS  mandatory
            DESCRIPTION
                "3E1 slot index"
            ::= { triE1AlarmControlEntry 1 }

        triE1ACPortIndex  OBJECT-TYPE
            SYNTAX  ThreePortID
            ACCESS  read-only
            STATUS  mandatory
            DESCRIPTION
                "Port 1 to 3, total 3 ports."
            ::= { triE1AlarmControlEntry 2 }

        triE1RAILine  OBJECT-TYPE
            SYNTAX  LsAlarmSeverity
            ACCESS  read-write
            STATUS  mandatory
            DESCRIPTION
                "RAI-Line State"
            ::= { triE1AlarmControlEntry 3 }

        triE1AISLine  OBJECT-TYPE
            SYNTAX  LsAlarmSeverity
            ACCESS  read-write
            STATUS  mandatory
            DESCRIPTION
                "AIS-Line State"
            ::= { triE1AlarmControlEntry 4 }

        triE1LOSLine  OBJECT-TYPE
            SYNTAX  LsAlarmSeverity
            ACCESS  read-write
            STATUS  mandatory
            DESCRIPTION
                "LOS-line State"
            ::= { triE1AlarmControlEntry 5 }

        triE1LOFLine  OBJECT-TYPE
            SYNTAX  LsAlarmSeverity
            ACCESS  read-write
            STATUS  mandatory
            DESCRIPTION
                "LOF-Line State"
            ::= { triE1AlarmControlEntry 6 }

        triE1BPVLine  OBJECT-TYPE
            SYNTAX  LsAlarmSeverity
            ACCESS  read-write
            STATUS  mandatory
            DESCRIPTION
                "BPV-Line State"
            ::= { triE1AlarmControlEntry 7 }

        triE1ESSLine  OBJECT-TYPE
            SYNTAX  LsAlarmSeverity
            ACCESS  read-write
            STATUS  mandatory
            DESCRIPTION
                "ESS-Line State"
            ::= { triE1AlarmControlEntry 8 }

        triE1UASLine  OBJECT-TYPE
            SYNTAX  LsAlarmSeverity
            ACCESS  read-write
            STATUS  mandatory
            DESCRIPTION
                "UAS-Line State"
            ::= { triE1AlarmControlEntry 9 }

        triE1CSSLine  OBJECT-TYPE
            SYNTAX  LsAlarmSeverity
            ACCESS  read-write
            STATUS  mandatory
            DESCRIPTION
                "CS-Line State"
            ::= { triE1AlarmControlEntry 10 }

        triE1AISinsert  OBJECT-TYPE
            SYNTAX  LsAlarmSeverity
            ACCESS  read-write
            STATUS  mandatory
            DESCRIPTION
                "3E1 AIS insert"
            ::= { triE1AlarmControlEntry 11 }


--
--  Threshold Control Table
--

        triE1ThresholdCtrlTable  OBJECT-TYPE
            SYNTAX  SEQUENCE OF TriE1ThresholdCtrlEntry
            ACCESS  not-accessible
            STATUS  mandatory
            DESCRIPTION
                "The alarm control table."
            ::= { triE1card 18 }

        triE1ThresholdCtrlEntry  OBJECT-TYPE
            SYNTAX  TriE1ThresholdCtrlEntry
            ACCESS  not-accessible
            STATUS  mandatory
            DESCRIPTION
                "An entry in the DS1 threshold control table."
            INDEX { triE1TCSlotIndex , triE1TCPortIndex }
            ::= { triE1ThresholdCtrlTable 1 }

        TriE1ThresholdCtrlEntry ::= SEQUENCE {
            triE1TCSlotIndex           LSSlotID,
            triE1TCPortIndex           ThreePortID,
            triE1ThresholdBPVLine      INTEGER,
            triE1ThresholdESSLine      INTEGER,
            triE1ThresholdUASLine      INTEGER,
            triE1ThresholdCSSLine      INTEGER,
            triE1ThresholdAISinsert    INTEGER
        }

        triE1TCSlotIndex  OBJECT-TYPE
            SYNTAX  LSSlotID
            ACCESS  read-only
            STATUS  mandatory
            DESCRIPTION
                "3E1 slot index"
            ::= { triE1ThresholdCtrlEntry 1 }

        triE1TCPortIndex  OBJECT-TYPE
            SYNTAX  ThreePortID
            ACCESS  read-only
            STATUS  mandatory
            DESCRIPTION
                "Port 1 to 3, total 3 ports."
            ::= { triE1ThresholdCtrlEntry 2 }

        triE1ThresholdBPVLine  OBJECT-TYPE
            SYNTAX  INTEGER
            ACCESS  read-write
            STATUS  mandatory
            DESCRIPTION
                " Threshold of BPV-Line "
            ::= { triE1ThresholdCtrlEntry 3 }

        triE1ThresholdESSLine  OBJECT-TYPE
            SYNTAX  INTEGER
            ACCESS  read-write
            STATUS  mandatory
            DESCRIPTION
                " Threshold of ESS-Line "
            ::= { triE1ThresholdCtrlEntry 4 }

        triE1ThresholdUASLine  OBJECT-TYPE
            SYNTAX  INTEGER
            ACCESS  read-write
            STATUS  mandatory
            DESCRIPTION
                " Threshold of UAS-Line "
            ::= { triE1ThresholdCtrlEntry 5 }

        triE1ThresholdCSSLine  OBJECT-TYPE
            SYNTAX  INTEGER
            ACCESS  read-write
            STATUS  mandatory
            DESCRIPTION
                " Threshold of CS-Line "
            ::= { triE1ThresholdCtrlEntry 6 }

        triE1ThresholdAISinsert  OBJECT-TYPE
            SYNTAX  INTEGER
            ACCESS  read-write
            STATUS  mandatory
            DESCRIPTION
                " Threshold of 3E1 AIS Insert"
            ::= { triE1ThresholdCtrlEntry 7 }


--
-- Line Diagnostic Control Table
--

        triE1LineDiagCtrlTable  OBJECT-TYPE
            SYNTAX  SEQUENCE OF TriE1LineDiagCtrlEntry
            ACCESS  not-accessible
            STATUS  mandatory
            DESCRIPTION
                "The alarm control table."
            ::= { triE1card 19 }

        triE1LineDiagCtrlEntry  OBJECT-TYPE
            SYNTAX  TriE1LineDiagCtrlEntry
            ACCESS  not-accessible
            STATUS  mandatory
            DESCRIPTION
                "An entry in the DS1 threshold control table."
            INDEX { triE1LDCSlotIndex , triE1LDCPortIndex }
            ::= { triE1LineDiagCtrlTable 1 }

        TriE1LineDiagCtrlEntry ::= SEQUENCE {
            triE1LDCSlotIndex          LSSlotID,
            triE1LDCPortIndex          ThreePortID,
            triE1LoopbackType          INTEGER,
            triE1LoopbackStatus        INTEGER,
            triE1PRBSControl           INTEGER,
            triE1PRBSStatus            INTEGER,
            triE1PRBSElapseSeconds     INTEGER,
            triE1PRBSErrorSeconds      INTEGER,
            triE1PRBSErrorCounts       INTEGER,
            triE1InbandLbPeriod        INTEGER,
            triE1remBERTControl        INTEGER,
            triE1remBERTStatus         INTEGER,
            triE1remBERTCounter        INTEGER,
            triE1remBERTElapsed        INTEGER,
            triE1remBERTErrorSecs      INTEGER,
            triE1remPattUnsyncSecs     INTEGER
        }

        triE1LDCSlotIndex  OBJECT-TYPE
            SYNTAX  LSSlotID
            ACCESS  read-only
            STATUS  mandatory
            DESCRIPTION
                "3E1 slot index"
            ::= { triE1LineDiagCtrlEntry 1 }

        triE1LDCPortIndex  OBJECT-TYPE
            SYNTAX  ThreePortID
            ACCESS  read-only
            STATUS  mandatory
            DESCRIPTION
                "Port 1 to 3, total 3 ports."
            ::= { triE1LineDiagCtrlEntry 2 }

        triE1LoopbackType  OBJECT-TYPE
            SYNTAX  INTEGER {
                    no-loopback(1),
                    local-loopback(2),
                    payload-loopback(3),
                    line-loopback(4),
                    remote-PLB-Active(5),
                    remote-LLB-Active(6),
                    remote-PLB-Deactive(7),
                    remote-LLB-Deactive(8),
                    remote-DTE1-Active(9),
                    remote-DTE1-Deactive(10),
                    remote-DTE2-Active(11),
                    remote-DTE2-Deactive(12)
                }
            ACCESS  read-write
            STATUS  mandatory
            DESCRIPTION
                "triE1 Loopback Type"
            ::= { triE1LineDiagCtrlEntry 3 }

        triE1LoopbackStatus  OBJECT-TYPE
            SYNTAX  INTEGER {
                    success(1),
                    fail(2),
                    loopback-not-active(3)
                }
            ACCESS  read-only
            STATUS  mandatory
            DESCRIPTION
                "triE1 Loopback Status"
            ::= { triE1LineDiagCtrlEntry 4 }

        triE1PRBSControl  OBJECT-TYPE
            SYNTAX  INTEGER {
                    prbs-deactive(1),
                    prbs-active-full(2),
                    prbs-reset-error-count(3),
                    prbs-inject-error(4)
                }
            ACCESS  read-write
            STATUS  mandatory
            DESCRIPTION
                "triE1 PRBS Control"
            ::= { triE1LineDiagCtrlEntry 5 }

        triE1PRBSStatus  OBJECT-TYPE
            SYNTAX  INTEGER {
                    prbs-sync(1),
                    prbs-unsync(2),
                    prbs-not-active(3)
                }
            ACCESS  read-only
            STATUS  mandatory
            DESCRIPTION
                "triE1 PRBS Status"
            ::= { triE1LineDiagCtrlEntry 6 }

        triE1PRBSElapseSeconds  OBJECT-TYPE
            SYNTAX  INTEGER
            ACCESS  read-only
            STATUS  mandatory
            DESCRIPTION
                "triE1 PRBS Elapse Seconds"
            ::= { triE1LineDiagCtrlEntry 7 }

        triE1PRBSErrorSeconds  OBJECT-TYPE
            SYNTAX  INTEGER
            ACCESS  read-only
            STATUS  mandatory
            DESCRIPTION
                "triE1 PRBS Error Seconds"
            ::= { triE1LineDiagCtrlEntry 8 }

        triE1PRBSErrorCounts  OBJECT-TYPE
            SYNTAX  INTEGER
            ACCESS  read-only
            STATUS  mandatory
            DESCRIPTION
                "triE1 PRBS Error Counts"
            ::= { triE1LineDiagCtrlEntry 9 }

        triE1InbandLbPeriod  OBJECT-TYPE
            SYNTAX  INTEGER
            ACCESS  read-write
            STATUS  mandatory
            DESCRIPTION
                "period(in seconds) of TriE1 inband local, payload, or line loopback"
            ::= { triE1LineDiagCtrlEntry 10 }

        triE1remBERTControl    OBJECT-TYPE
            SYNTAX  INTEGER {
                    bert-off(1),
                    bert-full(2),
                    bert-dte1(3),
                    bert-dte2(4),
                    bert-inject-error(5),
                    bert-reset(6)
                }
            ACCESS  read-write
            STATUS  mandatory
            DESCRIPTION
                "remBert Control"
            ::= { triE1LineDiagCtrlEntry 11 }

        triE1remBERTStatus  OBJECT-TYPE
            SYNTAX  INTEGER {
                    bert-sync(1),
                    bert-unsync(2),
                    bert-not-active(3)
                }
            ACCESS  read-only
            STATUS  mandatory
            DESCRIPTION
                "remBERT Status"
            ::= { triE1LineDiagCtrlEntry 13 }

        triE1remBERTCounter  OBJECT-TYPE
            SYNTAX  INTEGER
            ACCESS  read-only
            STATUS  mandatory
            DESCRIPTION
                "remBERT Counter"
            ::= { triE1LineDiagCtrlEntry 14 }

        triE1remBERTElapsed  OBJECT-TYPE
            SYNTAX  INTEGER
            ACCESS  read-only
            STATUS  mandatory
            DESCRIPTION
                "remBERT Elapsed Time"
            ::= { triE1LineDiagCtrlEntry 15 }

        triE1remBERTErrorSecs  OBJECT-TYPE
            SYNTAX  INTEGER
            ACCESS  read-only
            STATUS  mandatory
            DESCRIPTION
                "remBERT Error Seconds"
            ::= { triE1LineDiagCtrlEntry 16 }

        triE1remPattUnsyncSecs  OBJECT-TYPE
            SYNTAX  INTEGER
            ACCESS  read-only
            STATUS  mandatory
            DESCRIPTION
                "remBERT Pattern Unsync Seconds"
            ::= { triE1LineDiagCtrlEntry 17 }


--
--  Command Control Table
--

        triE1CommandCtrlTable  OBJECT-TYPE
            SYNTAX  SEQUENCE OF TriE1CommandCtrlEntry
            ACCESS  not-accessible
            STATUS  mandatory
            DESCRIPTION
                "The command control table."
            ::= { triE1card 20 }

        triE1CommandCtrlEntry  OBJECT-TYPE
            SYNTAX  TriE1CommandCtrlEntry
            ACCESS  not-accessible
            STATUS  mandatory
            DESCRIPTION
                "An entry in the command control table."
            INDEX { triE1CCSlotIndex , triE1CCPortIndex }
            ::= { triE1CommandCtrlTable 1 }

        TriE1CommandCtrlEntry ::= SEQUENCE {
            triE1CCSlotIndex           LSSlotID,
            triE1CCPortIndex           ThreePortID,
            --triE1AlarmQueueReset       INTEGER,
            triE1UserPerfReset         INTEGER,
            --triE1AlarmHistoryReset     INTEGER,
            triE1PortReset             INTEGER,
            triE1PortLoadDefault       INTEGER
        }

        triE1CCSlotIndex  OBJECT-TYPE
            SYNTAX  LSSlotID
            ACCESS  read-only
            STATUS  mandatory
            DESCRIPTION
                "3E1 slot index"
            ::= { triE1CommandCtrlEntry 1 }

        triE1CCPortIndex  OBJECT-TYPE
            SYNTAX  ThreePortID
            ACCESS  read-only
            STATUS  mandatory
            DESCRIPTION
                "Port 1 to 3, total 3 ports."
            ::= { triE1CommandCtrlEntry 2 }

--        triE1AlarmQueueReset    OBJECT-TYPE
--            SYNTAX  INTEGER {
--                    no(0),
--                    reset(1)
--                }
--            ACCESS  read-write
--            STATUS  mandatory
--            DESCRIPTION
--                "Command: Reset Alarm Queue "
--            ::= { triE1CommandCtrlEntry 3 }

        triE1UserPerfReset    OBJECT-TYPE
            SYNTAX  INTEGER {
                    no(0),
                    reset(1)
                }
            ACCESS  read-write
            STATUS  mandatory
            DESCRIPTION
                "Command: Reset User Performance"
            ::= { triE1CommandCtrlEntry 4 }

--        triE1AlarmHistoryReset    OBJECT-TYPE
--            SYNTAX  INTEGER {
--                    no(0),
--                    reset(1)
--                }
--            ACCESS  read-write
--            STATUS  mandatory
--            DESCRIPTION
--                "Command: Reset Alarm History"
--            ::= { triE1CommandCtrlEntry 5 }

        triE1PortReset    OBJECT-TYPE
            SYNTAX  INTEGER {
                    no(0),
                    reset(1)
                }
            ACCESS  read-write
            STATUS  mandatory
            DESCRIPTION
                "Command: Reset TriE1 Port"
            ::= { triE1CommandCtrlEntry 6 }

        triE1PortLoadDefault    OBJECT-TYPE
            SYNTAX  INTEGER {
                    no(0),
                    load-default(1)
                }
            ACCESS  read-write
            STATUS  mandatory
            DESCRIPTION
                "Command: Load Default TriE1 Port"
            ::= { triE1CommandCtrlEntry 7 }


--
--  SYSTEM Information Table
--

        triE1SystemInfoTable  OBJECT-TYPE
            SYNTAX  SEQUENCE OF TriE1SystemInfoEntry
            ACCESS  not-accessible
            STATUS  mandatory
            DESCRIPTION
                "The system information table."
            ::= { triE1card 21 }

        triE1SystemInfoEntry  OBJECT-TYPE
            SYNTAX  TriE1SystemInfoEntry
            ACCESS  not-accessible
            STATUS  mandatory
            DESCRIPTION
                "An entry in the system information table."
            INDEX { triE1SISlotIndex }
            ::= { triE1SystemInfoTable 1 }

        TriE1SystemInfoEntry ::= SEQUENCE {
            triE1SISlotIndex           LSSlotID,
            triE1PROMVersion           DisplayString,
            triE1HardwareVersion       DisplayString
        }

        triE1SISlotIndex  OBJECT-TYPE
            SYNTAX  LSSlotID
            ACCESS  read-only
            STATUS  mandatory
            DESCRIPTION
                "3E1 slot index"
            ::= { triE1SystemInfoEntry 1 }

        triE1PROMVersion  OBJECT-TYPE
            SYNTAX  DisplayString (SIZE (0..255) )
            ACCESS  read-only
            STATUS  mandatory
            DESCRIPTION
                " triE1 PROM Version"
            ::= { triE1SystemInfoEntry 2 }

        triE1HardwareVersion  OBJECT-TYPE
            SYNTAX  DisplayString (SIZE (0..255) )
            ACCESS  read-only
            STATUS  mandatory
            DESCRIPTION
                " triE1 Hardware Version"
            ::= { triE1SystemInfoEntry 3 }


--
--  3E1 Customer Information Table
--

        triE1CustomerInfoTable  OBJECT-TYPE
            SYNTAX  SEQUENCE OF TriE1CustomerInfoEntry
            ACCESS  not-accessible
            STATUS  mandatory
            DESCRIPTION
                "The Customer Information table."
            ::= { triE1card 99 }

        triE1CustomerInfoEntry  OBJECT-TYPE
            SYNTAX  TriE1CustomerInfoEntry
            ACCESS  not-accessible
            STATUS  mandatory
            DESCRIPTION
                "An entry in the Customer Information table."
            INDEX { triE1CISlotIndex , triE1CIPortIndex }
            ::= { triE1CustomerInfoTable 1 }

        TriE1CustomerInfoEntry ::= SEQUENCE {
            triE1CISlotIndex              LSSlotID,
            triE1CIPortIndex              ThreePortID,
            triE1CICustomerInfo           DisplayString (SIZE(0..64))
        }

        triE1CISlotIndex    OBJECT-TYPE
            SYNTAX  LSSlotID
            ACCESS  read-only
            STATUS  mandatory
            DESCRIPTION
                "3E1 slot index"
            ::= { triE1CustomerInfoEntry 1 }

        triE1CIPortIndex    OBJECT-TYPE
            SYNTAX  ThreePortID
            ACCESS  read-only
            STATUS  mandatory
            DESCRIPTION
                "Port number"
            ::= { triE1CustomerInfoEntry 2 }

        triE1CICustomerInfo  OBJECT-TYPE
            SYNTAX  DisplayString (SIZE (0..64) )
            ACCESS  read-write
            STATUS  mandatory
            DESCRIPTION
                "Customer information"
            ::= { triE1CustomerInfoEntry 3 }


--
--  Remote Link Identification Table
--

        triE1RemoteLinkIDTable  OBJECT-TYPE
            SYNTAX  SEQUENCE OF TriE1RemoteLinkIDEntry
            ACCESS  not-accessible
            STATUS  mandatory
            DESCRIPTION
                "Remote Link Identification Table"
            ::= { triE1card 22 }

        triE1RemoteLinkIDEntry  OBJECT-TYPE
            SYNTAX  TriE1RemoteLinkIDEntry
            ACCESS  not-accessible
            STATUS  mandatory
            DESCRIPTION
                "Remote Link Identification entry"
            INDEX { triE1LIDSlotIndex , triE1LIDPortIndex }
            ::= { triE1RemoteLinkIDTable 1 }

        TriE1RemoteLinkIDEntry ::= SEQUENCE {
            triE1LIDSlotIndex           LSSlotID,
            triE1LIDPortIndex           ThreePortID,
            triE1RemLinkIDType          INTEGER,
            triE1RemLinkIDRack          INTEGER,
            triE1RemLinkIDSlotNo        INTEGER,
            triE1RemLinkIDPort          INTEGER,
            triE1RemLinkIDSerialNo      INTEGER,
            triE1RemBackupSlotNUM       INTEGER,
            triE1RemBackupPort          INTEGER
        }

        triE1LIDSlotIndex  OBJECT-TYPE
            SYNTAX  LSSlotID
            ACCESS  read-only
            STATUS  mandatory
            DESCRIPTION
                "3E1 slot index"
            ::= { triE1RemoteLinkIDEntry 1 }

        triE1LIDPortIndex  OBJECT-TYPE
            SYNTAX  ThreePortID
            ACCESS  read-only
            STATUS  mandatory
            DESCRIPTION
                "Port 1 to 3, total 3 ports."
            ::= { triE1RemoteLinkIDEntry 2 }

        triE1RemLinkIDType  OBJECT-TYPE
            SYNTAX  INTEGER {
                    notAvailable(0),
                    cpe(1),
                    an(2)
                }
            ACCESS  read-only
            STATUS  mandatory
            DESCRIPTION
                "Type of remote site."
            ::= { triE1RemoteLinkIDEntry 3 }

        triE1RemLinkIDRack  OBJECT-TYPE
            SYNTAX  INTEGER {
                    notAvailable(0)
                }
            ACCESS  read-only
            STATUS  mandatory
            DESCRIPTION
                "Remote Link Identification Rack"
            ::= { triE1RemoteLinkIDEntry 4 }

        triE1RemLinkIDSlotNo  OBJECT-TYPE
            SYNTAX  INTEGER {
                    notAvailable(0)
                }
            ACCESS  read-only
            STATUS  mandatory
            DESCRIPTION
                "Remote Link Identification SlotNumber"
            ::= { triE1RemoteLinkIDEntry 5 }

        triE1RemLinkIDPort  OBJECT-TYPE
            SYNTAX  INTEGER {
                    notAvailable(0)
                }
            ACCESS  read-only
            STATUS  mandatory
            DESCRIPTION
                "Remote Link Identification Port"
            ::= { triE1RemoteLinkIDEntry 6 }

        triE1RemLinkIDSerialNo  OBJECT-TYPE
            SYNTAX  INTEGER {
                    notAvailable(0)
                }
            ACCESS  read-only
            STATUS  mandatory
            DESCRIPTION
                "Remote Link Identification Serial Number"
            ::= { triE1RemoteLinkIDEntry 7 }

        triE1RemBackupSlotNUM  OBJECT-TYPE
            SYNTAX  INTEGER {
                    notAvailable(0)
                }
            ACCESS  read-only
            STATUS  mandatory
            DESCRIPTION
                "Remote Link Identification Backup Slot Number"
            ::= { triE1RemoteLinkIDEntry 8 }

        triE1RemBackupPort  OBJECT-TYPE
            SYNTAX  INTEGER {
                    notAvailable(0)
                }
            ACCESS  read-only
            STATUS  mandatory
            DESCRIPTION
                "Remote Link Identification Backup Port"
            ::= { triE1RemoteLinkIDEntry 9 }

        triE1TotalCard   OBJECT-TYPE
            SYNTAX  INTEGER
            ACCESS  read-only
            STATUS  mandatory
            DESCRIPTION
                "Total cards of 3E1"
            ::= { triE1card 100 }


--======================================================================--
--======================================================================--
--  3T1 card MIB
--======================================================================--
--======================================================================--

--
--  Line Control Table
--

        triT1LineControlTable  OBJECT-TYPE
            SYNTAX  SEQUENCE OF TriT1LineControlEntry
            ACCESS  not-accessible
            STATUS  mandatory
            DESCRIPTION
                "The DS1 line control table."
            ::= { triT1card 1 }

        triT1LineControlEntry  OBJECT-TYPE
            SYNTAX  TriT1LineControlEntry
            ACCESS  not-accessible
            STATUS  mandatory
            DESCRIPTION
                "An entry in the DS1 line control table."
            INDEX { triT1LCslot , triT1LCport }
            ::= { triT1LineControlTable 1 }

        TriT1LineControlEntry ::= SEQUENCE  {
            triT1LCslot                   LSSlotID,
            triT1LCport                   ThreePortID,
            triT1LineFrame                INTEGER,
            triT1LineCoding               INTEGER,
            triT1Interface                INTEGER,
            triT1LineBuildOut             INTEGER,
            triT1Equalizer                INTEGER,
            triT1AIS                      INTEGER,
            triT1YEL                      INTEGER,
            triT1Inband                   INTEGER,
            triT1IdleCode                 INTEGER,
            triT1CASMode                  INTEGER,
            triT1SignallingMode           INTEGER,
            triT1CGA                      INTEGER,
            triT1OutOfService             INTEGER,
            triT1FDL                      INTEGER,
            triT1SNCPdelay                INTEGER,
            triT1SNCPsendAIS              INTEGER
        }

        triT1LCslot  OBJECT-TYPE
            SYNTAX  LSSlotID
            ACCESS  read-only
            STATUS  mandatory
            DESCRIPTION
                "3T1 slot index"
            ::= { triT1LineControlEntry 1 }

        triT1LCport  OBJECT-TYPE
            SYNTAX  ThreePortID
            ACCESS  read-only
            STATUS  mandatory
            DESCRIPTION
                "Port 1 to 3, total 3 ports."
            ::= { triT1LineControlEntry 2 }

        triT1LineFrame  OBJECT-TYPE
            SYNTAX  INTEGER   {
                    d4(1),
                    esf(2),
                    esfT1403(3),
                    none(4)
                }
            ACCESS  read-write
            STATUS  mandatory
            DESCRIPTION
                "Line frame format"
            ::= { triT1LineControlEntry 3 }

        triT1LineCoding  OBJECT-TYPE
            SYNTAX  INTEGER   {
                    ami(1),
                    b8zs(2)
                }
            ACCESS  read-write
            STATUS  mandatory
            DESCRIPTION
                "Line Coding type"
            ::= { triT1LineControlEntry 4 }

        triT1Interface  OBJECT-TYPE
            SYNTAX  INTEGER   {
                    longHaul(1),
                    shortHaul(2)
                }
            ACCESS  read-write
            STATUS  mandatory
            DESCRIPTION
                "Interface indicates that TriT1 line use Long/Short haul."
            ::= { triT1LineControlEntry 5 }

        triT1LineBuildOut  OBJECT-TYPE
            SYNTAX  INTEGER   {
                    lbo0dB(1),
                    lboNeg75dB(2),
                    lboNeg15dB(3)
                }
            ACCESS  read-write
            STATUS  mandatory
            DESCRIPTION
                "3T1 line build out: 0dB, -7.5dB, -15dB."
            ::= { triT1LineControlEntry 6 }

        triT1Equalizer  OBJECT-TYPE
            SYNTAX  INTEGER   {
                    equ0to110Ft(1),
                    equ110to220ft(2),
                    equ220to330ft(3),
                    equ330to440ft(4),
                    equ440to550ft(5),
                    equ550to660ft(6)
                }
            ACCESS  read-write
            STATUS  mandatory
            DESCRIPTION
                "3T1 line equalizer."
            ::= { triT1LineControlEntry 7 }

        triT1AIS  OBJECT-TYPE
            SYNTAX  INTEGER   {
                    frame(1),
--                    unframe(2),
                    off(3)
                }
            ACCESS  read-write
            STATUS  mandatory
            DESCRIPTION
                "3T1 line Alarm Indication Signal."
            ::= { triT1LineControlEntry 8 }

        triT1YEL  OBJECT-TYPE
            SYNTAX  INTEGER   {
                    on(1),
                    off(2)
                }
            ACCESS  read-write
            STATUS  mandatory
            DESCRIPTION
                "YEL-ON indicates that yellow alarm ON."
            ::= { triT1LineControlEntry 9 }

        triT1Inband  OBJECT-TYPE
            SYNTAX  INTEGER   {
                    on(1),
                    off(2)
                }
            ACCESS  read-write
            STATUS  mandatory
            DESCRIPTION
                "3T1 line inband ON/OFF"
            ::= { triT1LineControlEntry 10 }

        triT1IdleCode  OBJECT-TYPE
            SYNTAX  INTEGER
            ACCESS  read-write
            STATUS  mandatory
            DESCRIPTION
                "Line Idle Code Value"
            ::= { triT1LineControlEntry 11 }

        triT1CASMode  OBJECT-TYPE
            SYNTAX  INTEGER   {
                    on(1),
                    off(2)
                }
            ACCESS  read-write
            STATUS  mandatory
            DESCRIPTION
                "CAS or CCS"
            ::= { triT1LineControlEntry 12 }

        triT1SignallingMode  OBJECT-TYPE
            SYNTAX  INTEGER   {
                    trans(1)
                }
            ACCESS  read-write
            STATUS  mandatory
            DESCRIPTION
                "TRANS"
            ::= { triT1LineControlEntry 13 }

        triT1CGA  OBJECT-TYPE
            SYNTAX  INTEGER   {
                    norm(1)
                }
            ACCESS  read-write
            STATUS  mandatory
            DESCRIPTION
                "Method used to signal the Carrier Group Alarm state
                to the other end of the selected link."
            ::= { triT1LineControlEntry 14 }

        triT1OutOfService  OBJECT-TYPE
            SYNTAX  INTEGER   {
                    busy(1),
                    idle(2),
                    ais(3)
                }
            ACCESS  read-write
            STATUS  mandatory
            DESCRIPTION
                "When NORM (CGA) is select, the parameter determines the
                state of the A, B signaling bits during the
                Out-of-Service periods."
            ::= { triT1LineControlEntry 15 }

        triT1FDL  OBJECT-TYPE
            SYNTAX  INTEGER   {
                    on(1),
                    off(2)
                }
            ACCESS  read-write
            STATUS  mandatory
            DESCRIPTION
                "3T1 Facility Data Link ON/OFF"
            ::= { triT1LineControlEntry 16 }

        triT1SNCPdelay  OBJECT-TYPE
            SYNTAX  INTEGER  (0..99)
            ACCESS  read-write
            STATUS  mandatory
            DESCRIPTION
                "DS0-SNCP port delay."
            ::= { triT1LineControlEntry 17 }

        triT1SNCPsendAIS  OBJECT-TYPE
            SYNTAX  INTEGER   {
                    on(1),
                    off(2)
                }
            ACCESS  read-write
            STATUS  mandatory
            DESCRIPTION
                "DS0-SNCP port send AIS."
            ::= { triT1LineControlEntry 18 }



--
--  User Current Performance Table
--

        triT1UserCurrPerfTable  OBJECT-TYPE
            SYNTAX  SEQUENCE OF TriT1UserCurrPerfEntry
            ACCESS  not-accessible
            STATUS  mandatory
            DESCRIPTION
                "User Current Performance Table"
            ::= { triT1card 2 }

        triT1UserCurrPerfEntry  OBJECT-TYPE
            SYNTAX  TriT1UserCurrPerfEntry
            ACCESS  not-accessible
            STATUS  mandatory
            DESCRIPTION
                "User current performance entry"
            INDEX { triT1UCPslot , triT1UCPport }
            ::= { triT1UserCurrPerfTable 1 }

        TriT1UserCurrPerfEntry ::= SEQUENCE  {
            triT1UCPslot                  LSSlotID,
            triT1UCPport                  ThreePortID,
            triT1UserCurrPerfES           Gauge,
            triT1UserCurrPerfSES          Gauge,
            triT1UserCurrPerfBES          Gauge,
            triT1UserCurrPerfUAS          Gauge,
            triT1UserCurrPerfCSS          Gauge,
            triT1UserCurrPerfBPV          Gauge,
            triT1UserCurrPerfLOFC         Gauge,
            triT1UserCurr15MinTimeElapsed INTEGER,
            triT1UserValid15MinInterval   INTEGER
        }

        triT1UCPslot  OBJECT-TYPE
            SYNTAX  LSSlotID
            ACCESS  read-only
            STATUS  mandatory
            DESCRIPTION
                "3T1 slot index"
            ::= { triT1UserCurrPerfEntry 1 }

        triT1UCPport  OBJECT-TYPE
            SYNTAX  ThreePortID
            ACCESS  read-only
            STATUS  mandatory
            DESCRIPTION
                "Port 1 to 3, total 3 ports."
            ::= { triT1UserCurrPerfEntry 2 }

        triT1UserCurrPerfES  OBJECT-TYPE
            SYNTAX  Gauge
            ACCESS  read-only
            STATUS  mandatory
            DESCRIPTION
                " ES Error Counter "
            ::= { triT1UserCurrPerfEntry 3 }

        triT1UserCurrPerfSES  OBJECT-TYPE
            SYNTAX  Gauge
            ACCESS  read-only
            STATUS  mandatory
            DESCRIPTION
                " SES Error Counter "
            ::= { triT1UserCurrPerfEntry 4 }

        triT1UserCurrPerfBES  OBJECT-TYPE
            SYNTAX  Gauge
            ACCESS  read-only
            STATUS  mandatory
            DESCRIPTION
                " BES Error Counter "
            ::= { triT1UserCurrPerfEntry 5 }

        triT1UserCurrPerfUAS  OBJECT-TYPE
            SYNTAX  Gauge
            ACCESS  read-only
            STATUS  mandatory
            DESCRIPTION
                " UAS Error Counter "
            ::= { triT1UserCurrPerfEntry 6 }

        triT1UserCurrPerfCSS  OBJECT-TYPE
            SYNTAX  Gauge
            ACCESS  read-only
            STATUS  mandatory
            DESCRIPTION
                " CS Error Counter "
            ::= { triT1UserCurrPerfEntry 7 }

        triT1UserCurrPerfBPV  OBJECT-TYPE
            SYNTAX  Gauge
            ACCESS  read-only
            STATUS  mandatory
            DESCRIPTION
                " BPV Error Counter "
            ::= { triT1UserCurrPerfEntry 8 }

        triT1UserCurrPerfLOFC  OBJECT-TYPE
            SYNTAX  Gauge
            ACCESS  read-only
            STATUS  mandatory
            DESCRIPTION
                " LOFC Error Counter "
            ::= { triT1UserCurrPerfEntry 9 }

        triT1UserCurr15MinTimeElapsed  OBJECT-TYPE
            SYNTAX  INTEGER
            ACCESS  read-only
            STATUS  mandatory
            DESCRIPTION
                " Current 15-minute time elapsed"
            ::= { triT1UserCurrPerfEntry 11 }

        triT1UserValid15MinInterval  OBJECT-TYPE
            SYNTAX  INTEGER
            ACCESS  read-only
            STATUS  mandatory
            DESCRIPTION
                " Current 1-day Valid 15-min interval"
            ::= { triT1UserCurrPerfEntry 12 }


--
--  User Interval Performance Table
--

        triT1UserIntvPerfTable  OBJECT-TYPE
            SYNTAX  SEQUENCE OF TriT1UserIntvPerfEntry
            ACCESS  not-accessible
            STATUS  mandatory
            DESCRIPTION
                "User Interval Performance Table"
            ::= { triT1card 3 }

        triT1UserIntvPerfEntry  OBJECT-TYPE
            SYNTAX  TriT1UserIntvPerfEntry
            ACCESS  not-accessible
            STATUS  mandatory
            DESCRIPTION
                "User interval performance entry"
            INDEX { triT1UIPslot , triT1UIPport ,
                    triT1UserIntvPerfNumber }
            ::= { triT1UserIntvPerfTable 1 }

        TriT1UserIntvPerfEntry ::= SEQUENCE  {
            triT1UIPslot                  LSSlotID,
            triT1UIPport                  ThreePortID,
            triT1UserIntvPerfNumber       INTEGER,
            triT1UserIntvPerfES           Gauge,
            triT1UserIntvPerfSES          Gauge,
            triT1UserIntvPerfBES          Gauge,
            triT1UserIntvPerfUAS          Gauge,
            triT1UserIntvPerfCSS          Gauge,
            triT1UserIntvPerfBPV          Gauge,
            triT1UserIntvPerfLOFC         Gauge
        }

        triT1UIPslot  OBJECT-TYPE
            SYNTAX  LSSlotID
            ACCESS  read-only
            STATUS  mandatory
            DESCRIPTION
                "3T1 slot index"
            ::= { triT1UserIntvPerfEntry 1 }

        triT1UIPport  OBJECT-TYPE
            SYNTAX  ThreePortID
            ACCESS  read-only
            STATUS  mandatory
            DESCRIPTION
                "Port 1 to 3, total 3 ports."
            ::= { triT1UserIntvPerfEntry 2 }

        triT1UserIntvPerfNumber  OBJECT-TYPE
            SYNTAX  INTEGER (1..96)
            ACCESS  read-only
            STATUS  mandatory
            DESCRIPTION
                " Interval Index "
            ::= { triT1UserIntvPerfEntry 3 }

        triT1UserIntvPerfES  OBJECT-TYPE
            SYNTAX  Gauge
            ACCESS  read-only
            STATUS  mandatory
            DESCRIPTION
                " ES Error Counter "
            ::= { triT1UserIntvPerfEntry 4 }

        triT1UserIntvPerfSES  OBJECT-TYPE
            SYNTAX  Gauge
            ACCESS  read-only
            STATUS  mandatory
            DESCRIPTION
                " SES Error Counter "
            ::= { triT1UserIntvPerfEntry 5 }

        triT1UserIntvPerfBES  OBJECT-TYPE
            SYNTAX  Gauge
            ACCESS  read-only
            STATUS  mandatory
            DESCRIPTION
                " BES Error Counter "
            ::= { triT1UserIntvPerfEntry 6 }

        triT1UserIntvPerfUAS  OBJECT-TYPE
            SYNTAX  Gauge
            ACCESS  read-only
            STATUS  mandatory
            DESCRIPTION
                " UAS Error Counter "
            ::= { triT1UserIntvPerfEntry 7 }

        triT1UserIntvPerfCSS  OBJECT-TYPE
            SYNTAX  Gauge
            ACCESS  read-only
            STATUS  mandatory
            DESCRIPTION
                " CSS Error Counter "
            ::= { triT1UserIntvPerfEntry 8 }

        triT1UserIntvPerfBPV  OBJECT-TYPE
            SYNTAX  Gauge
            ACCESS  read-only
            STATUS  mandatory
            DESCRIPTION
                " BPV Error Counter "
            ::= { triT1UserIntvPerfEntry 9 }

        triT1UserIntvPerfLOFC  OBJECT-TYPE
            SYNTAX  Gauge
            ACCESS  read-only
            STATUS  mandatory
            DESCRIPTION
                " LOFC Error Counter "
            ::= { triT1UserIntvPerfEntry 10 }


--
--  User Total Performance Table
--
        triT1UserTotalPerfTable  OBJECT-TYPE
            SYNTAX  SEQUENCE OF TriT1UserTotalPerfEntry
            ACCESS  not-accessible
            STATUS  mandatory
            DESCRIPTION
                "User Total Performance Table"
            ::= { triT1card 4 }

        triT1UserTotalPerfEntry  OBJECT-TYPE
            SYNTAX  TriT1UserTotalPerfEntry
            ACCESS  not-accessible
            STATUS  mandatory
            DESCRIPTION
                "User total performance entry"
            INDEX { triT1UTPslot , triT1UTPport }
            ::= { triT1UserTotalPerfTable 1 }

        TriT1UserTotalPerfEntry ::= SEQUENCE  {
            triT1UTPslot                  LSSlotID,
            triT1UTPport                  ThreePortID,
            triT1UserTotalPerfES          Gauge,
            triT1UserTotalPerfSES         Gauge,
            triT1UserTotalPerfBES         Gauge,
            triT1UserTotalPerfUAS         Gauge,
            triT1UserTotalPerfCSS         Gauge,
            triT1UserTotalPerfBPV         Gauge,
            triT1UserTotalPerfLOFC        Gauge
        }

        triT1UTPslot  OBJECT-TYPE
            SYNTAX  LSSlotID
            ACCESS  read-only
            STATUS  mandatory
            DESCRIPTION
                "3T1 slot index"
            ::= { triT1UserTotalPerfEntry 1 }

        triT1UTPport  OBJECT-TYPE
            SYNTAX  ThreePortID
            ACCESS  read-only
            STATUS  mandatory
            DESCRIPTION
                "Port 1 to 3, total 3 ports."
            ::= { triT1UserTotalPerfEntry 2 }

        triT1UserTotalPerfES  OBJECT-TYPE
            SYNTAX  Gauge
            ACCESS  read-only
            STATUS  mandatory
            DESCRIPTION
                " ES Error Counter "
            ::= { triT1UserTotalPerfEntry 3 }

        triT1UserTotalPerfSES  OBJECT-TYPE
            SYNTAX  Gauge
            ACCESS  read-only
            STATUS  mandatory
            DESCRIPTION
                " SES Error Counter "
            ::= { triT1UserTotalPerfEntry 4 }

        triT1UserTotalPerfBES  OBJECT-TYPE
            SYNTAX  Gauge
            ACCESS  read-only
            STATUS  mandatory
            DESCRIPTION
                " BES Error Counter "
            ::= { triT1UserTotalPerfEntry 5 }

        triT1UserTotalPerfUAS  OBJECT-TYPE
            SYNTAX  Gauge
            ACCESS  read-only
            STATUS  mandatory
            DESCRIPTION
                " UAS Error Counter "
            ::= { triT1UserTotalPerfEntry 6 }

        triT1UserTotalPerfCSS  OBJECT-TYPE
            SYNTAX  Gauge
            ACCESS  read-only
            STATUS  mandatory
            DESCRIPTION
                " CSS Error Counter "
            ::= { triT1UserTotalPerfEntry 7 }

        triT1UserTotalPerfBPV  OBJECT-TYPE
            SYNTAX  Gauge
            ACCESS  read-only
            STATUS  mandatory
            DESCRIPTION
                " BPV Error Counter "
            ::= { triT1UserTotalPerfEntry 8 }

        triT1UserTotalPerfLOFC  OBJECT-TYPE
            SYNTAX  Gauge
            ACCESS  read-only
            STATUS  mandatory
            DESCRIPTION
                " LOFC Error Counter "
            ::= { triT1UserTotalPerfEntry 9 }


--
--  User Seven Days Performance Table
--
        triT1User7DaysPerfTable  OBJECT-TYPE
            SYNTAX  SEQUENCE OF TriT1User7DaysPerfEntry
            ACCESS  not-accessible
            STATUS  mandatory
            DESCRIPTION
                "User 7 Days Performance Table"
            ::= { triT1card 5 }

        triT1User7DaysPerfEntry  OBJECT-TYPE
            SYNTAX  TriT1User7DaysPerfEntry
            ACCESS  not-accessible
            STATUS  mandatory
            DESCRIPTION
                "User 7 days performance entry"
            INDEX { triT1USPslot , triT1USPport ,
                    triT1UserDaysIndex }
            ::= { triT1User7DaysPerfTable 1 }

        TriT1User7DaysPerfEntry ::= SEQUENCE  {
            triT1USPslot                  LSSlotID,
            triT1USPport                  ThreePortID,
            triT1UserDaysIndex            INTEGER,
            triT1UserDateStrIndex         DisplayString,
            triT1User7DaysPerfES          Gauge,
            triT1User7DaysPerfSES         Gauge,
            triT1User7DaysPerfBES         Gauge,
            triT1User7DaysPerfUAS         Gauge,
            triT1User7DaysPerfCSS         Gauge
        }

        triT1USPslot  OBJECT-TYPE
            SYNTAX  LSSlotID
            ACCESS  read-only
            STATUS  mandatory
            DESCRIPTION
                "3T1 slot index"
            ::= { triT1User7DaysPerfEntry 1 }

        triT1USPport  OBJECT-TYPE
            SYNTAX  ThreePortID
            ACCESS  read-only
            STATUS  mandatory
            DESCRIPTION
                "Port 1 to 3, total 3 ports."
            ::= { triT1User7DaysPerfEntry 2 }

        triT1UserDaysIndex  OBJECT-TYPE
            SYNTAX  INTEGER (1..7)
            ACCESS  read-only
            STATUS  mandatory
            DESCRIPTION
                "Seven Days index "
            ::= { triT1User7DaysPerfEntry 3 }

        triT1UserDateStrIndex  OBJECT-TYPE
            SYNTAX  DisplayString (SIZE (0..255) )
            ACCESS  read-only
            STATUS  mandatory
            DESCRIPTION
                "Seven Days String "
            ::= { triT1User7DaysPerfEntry 4 }

        triT1User7DaysPerfES  OBJECT-TYPE
            SYNTAX  Gauge
            ACCESS  read-only
            STATUS  mandatory
            DESCRIPTION
                " ES Error Counter "
            ::= { triT1User7DaysPerfEntry 5 }

        triT1User7DaysPerfSES  OBJECT-TYPE
            SYNTAX  Gauge
            ACCESS  read-only
            STATUS  mandatory
            DESCRIPTION
                " SES Error Counter "
            ::= { triT1User7DaysPerfEntry 6 }

        triT1User7DaysPerfBES  OBJECT-TYPE
            SYNTAX  Gauge
            ACCESS  read-only
            STATUS  mandatory
            DESCRIPTION
                " BES Error Counter "
            ::= { triT1User7DaysPerfEntry 7 }

        triT1User7DaysPerfUAS  OBJECT-TYPE
            SYNTAX  Gauge
            ACCESS  read-only
            STATUS  mandatory
            DESCRIPTION
                " UAS Error Counter "
            ::= { triT1User7DaysPerfEntry 8 }

        triT1User7DaysPerfCSS  OBJECT-TYPE
            SYNTAX  Gauge
            ACCESS  read-only
            STATUS  mandatory
            DESCRIPTION
                " CSS Error Counter "
            ::= { triT1User7DaysPerfEntry 9 }


--
--  Line Current Performance Table
--

        triT1LineCurrPerfTable  OBJECT-TYPE
            SYNTAX  SEQUENCE OF TriT1LineCurrPerfEntry
            ACCESS  not-accessible
            STATUS  mandatory
            DESCRIPTION
                "Line Current Performance Table"
            ::= { triT1card 6 }

        triT1LineCurrPerfEntry  OBJECT-TYPE
            SYNTAX  TriT1LineCurrPerfEntry
            ACCESS  not-accessible
            STATUS  mandatory
            DESCRIPTION
                "Line current performance entry"
            INDEX { triT1LCPslot , triT1LCPport }
            ::= { triT1LineCurrPerfTable 1 }

        TriT1LineCurrPerfEntry ::= SEQUENCE  {
            triT1LCPslot                  LSSlotID,
            triT1LCPport                  ThreePortID,
            triT1LineCurrPerfES           Gauge,
            triT1LineCurrPerfSES          Gauge,
            triT1LineCurrPerfBES          Gauge,
            triT1LineCurrPerfUAS          Gauge,
            triT1LineCurrPerfCSS          Gauge,
            triT1LineCurrPerfBPV          Gauge,
            triT1LineCurrPerfLOFC         Gauge,
            triT1LineCurr15MinTimeElapsed INTEGER,
            triT1LineValid15MinInterval   INTEGER
        }

        triT1LCPslot  OBJECT-TYPE
            SYNTAX  LSSlotID
            ACCESS  read-only
            STATUS  mandatory
            DESCRIPTION
                "3T1 slot index"
            ::= { triT1LineCurrPerfEntry 1 }

        triT1LCPport  OBJECT-TYPE
            SYNTAX  ThreePortID
            ACCESS  read-only
            STATUS  mandatory
            DESCRIPTION
                "Port 1 to 3, total 3 ports."
            ::= { triT1LineCurrPerfEntry 2 }

        triT1LineCurrPerfES  OBJECT-TYPE
            SYNTAX  Gauge
            ACCESS  read-only
            STATUS  mandatory
            DESCRIPTION
                " ESS Error Counter "
            ::= { triT1LineCurrPerfEntry 3 }

        triT1LineCurrPerfSES  OBJECT-TYPE
            SYNTAX  Gauge
            ACCESS  read-only
            STATUS  mandatory
            DESCRIPTION
                " SES Error Counter "
            ::= { triT1LineCurrPerfEntry 4 }

        triT1LineCurrPerfBES  OBJECT-TYPE
            SYNTAX  Gauge
            ACCESS  read-only
            STATUS  mandatory
            DESCRIPTION
                " BES Error Counter "
            ::= { triT1LineCurrPerfEntry 5 }

        triT1LineCurrPerfUAS  OBJECT-TYPE
            SYNTAX  Gauge
            ACCESS  read-only
            STATUS  mandatory
            DESCRIPTION
                " UAS Error Counter "
            ::= { triT1LineCurrPerfEntry 6 }

        triT1LineCurrPerfCSS  OBJECT-TYPE
            SYNTAX  Gauge
            ACCESS  read-only
            STATUS  mandatory
            DESCRIPTION
                " CSS Error Counter "
            ::= { triT1LineCurrPerfEntry 7 }

        triT1LineCurrPerfBPV  OBJECT-TYPE
            SYNTAX  Gauge
            ACCESS  read-only
            STATUS  mandatory
            DESCRIPTION
                " BPV Error Counter "
            ::= { triT1LineCurrPerfEntry 8 }

        triT1LineCurrPerfLOFC  OBJECT-TYPE
            SYNTAX  Gauge
            ACCESS  read-only
            STATUS  mandatory
            DESCRIPTION
                " LOFC Error Counter "
            ::= { triT1LineCurrPerfEntry 9 }

        triT1LineCurr15MinTimeElapsed  OBJECT-TYPE
            SYNTAX  INTEGER
            ACCESS  read-only
            STATUS  mandatory
            DESCRIPTION
                " Current 15-minute time elapsed"
            ::= { triT1LineCurrPerfEntry 11 }

        triT1LineValid15MinInterval  OBJECT-TYPE
            SYNTAX  INTEGER
            ACCESS  read-only
            STATUS  mandatory
            DESCRIPTION
                " Current 1-day Valid 15-min interval"
            ::= { triT1LineCurrPerfEntry 12 }


--
--  Line Interval Performance Table
--

        triT1LineIntvPerfTable  OBJECT-TYPE
            SYNTAX  SEQUENCE OF TriT1LineIntvPerfEntry
            ACCESS  not-accessible
            STATUS  mandatory
            DESCRIPTION
                "Line Interval Performance Table"
            ::= { triT1card 7 }

        triT1LineIntvPerfEntry  OBJECT-TYPE
            SYNTAX  TriT1LineIntvPerfEntry
            ACCESS  not-accessible
            STATUS  mandatory
            DESCRIPTION
                "Line interval performance entry"
            INDEX { triT1LIPslot , triT1LIPport ,
                    triT1LineIntvPerfNumber }
            ::= { triT1LineIntvPerfTable 1 }

        TriT1LineIntvPerfEntry ::= SEQUENCE  {
            triT1LIPslot                  LSSlotID,
            triT1LIPport                  ThreePortID,
            triT1LineIntvPerfNumber       INTEGER,
            triT1LineIntvPerfES           Gauge,
            triT1LineIntvPerfSES          Gauge,
            triT1LineIntvPerfBES          Gauge,
            triT1LineIntvPerfUAS          Gauge,
            triT1LineIntvPerfCSS          Gauge,
            triT1LineIntvPerfBPV          Gauge,
            triT1LineIntvPerfLOFC         Gauge,
            triT1LineIntvAvailable        INTEGER
        }

        triT1LIPslot  OBJECT-TYPE
            SYNTAX  LSSlotID
            ACCESS  read-only
            STATUS  mandatory
            DESCRIPTION
                "3T1 slot index"
            ::= { triT1LineIntvPerfEntry 1 }

        triT1LIPport  OBJECT-TYPE
            SYNTAX  ThreePortID
            ACCESS  read-only
            STATUS  mandatory
            DESCRIPTION
                "Port 1 to 3, total 3 ports."
            ::= { triT1LineIntvPerfEntry 2 }

        triT1LineIntvPerfNumber  OBJECT-TYPE
            SYNTAX  INTEGER (1..96)
            ACCESS  read-only
            STATUS  mandatory
            DESCRIPTION
                "Interval Index "
            ::= { triT1LineIntvPerfEntry 3 }

        triT1LineIntvPerfES  OBJECT-TYPE
            SYNTAX  Gauge
            ACCESS  read-only
            STATUS  mandatory
            DESCRIPTION
                " ES Error Counter "
            ::= { triT1LineIntvPerfEntry 4 }

        triT1LineIntvPerfSES  OBJECT-TYPE
            SYNTAX  Gauge
            ACCESS  read-only
            STATUS  mandatory
            DESCRIPTION
                " SES Error Counter "
            ::= { triT1LineIntvPerfEntry 5 }

        triT1LineIntvPerfBES  OBJECT-TYPE
            SYNTAX  Gauge
            ACCESS  read-only
            STATUS  mandatory
            DESCRIPTION
                " BES Error Counter "
            ::= { triT1LineIntvPerfEntry 6 }

        triT1LineIntvPerfUAS  OBJECT-TYPE
            SYNTAX  Gauge
            ACCESS  read-only
            STATUS  mandatory
            DESCRIPTION
                " UAS Error Counter "
            ::= { triT1LineIntvPerfEntry 7 }

        triT1LineIntvPerfCSS  OBJECT-TYPE
            SYNTAX  Gauge
            ACCESS  read-only
            STATUS  mandatory
            DESCRIPTION
                " CSS Error Counter "
            ::= { triT1LineIntvPerfEntry 8 }

        triT1LineIntvPerfBPV  OBJECT-TYPE
            SYNTAX  Gauge
            ACCESS  read-only
            STATUS  mandatory
            DESCRIPTION
                " BPV Error Counter "
            ::= { triT1LineIntvPerfEntry 9 }

        triT1LineIntvPerfLOFC  OBJECT-TYPE
            SYNTAX  Gauge
            ACCESS  read-only
            STATUS  mandatory
            DESCRIPTION
                " LOFC Error Counter "
            ::= { triT1LineIntvPerfEntry 10 }

        triT1LineIntvAvailable  OBJECT-TYPE
            SYNTAX  INTEGER   {
                    available(1),
                    na(2)
                }
            ACCESS  read-only
            STATUS  mandatory
            DESCRIPTION
                " Interval Available "
            ::= { triT1LineIntvPerfEntry 11 }


--
--  Line Total Performance Table
--

        triT1LineTotalPerfTable  OBJECT-TYPE
            SYNTAX  SEQUENCE OF TriT1LineTotalPerfEntry
            ACCESS  not-accessible
            STATUS  mandatory
            DESCRIPTION
                "Line Total Performance Table"
            ::= { triT1card 8 }

        triT1LineTotalPerfEntry  OBJECT-TYPE
            SYNTAX  TriT1LineTotalPerfEntry
            ACCESS  not-accessible
            STATUS  mandatory
            DESCRIPTION
                "Line total performance entry"
            INDEX { triT1LTPslot , triT1LTPport }
            ::= { triT1LineTotalPerfTable 1 }

        TriT1LineTotalPerfEntry ::= SEQUENCE  {
            triT1LTPslot                  LSSlotID,
            triT1LTPport                  ThreePortID,
            triT1LineTotalPerfES          Gauge,
            triT1LineTotalPerfSES         Gauge,
            triT1LineTotalPerfBES         Gauge,
            triT1LineTotalPerfUAS         Gauge,
            triT1LineTotalPerfCSS         Gauge,
            triT1LineTotalPerfBPV         Gauge,
            triT1LineTotalPerfLOFC        Gauge
        }

        triT1LTPslot  OBJECT-TYPE
            SYNTAX  LSSlotID
            ACCESS  read-only
            STATUS  mandatory
            DESCRIPTION
                "3T1 slot index"
            ::= { triT1LineTotalPerfEntry 1 }

        triT1LTPport  OBJECT-TYPE
            SYNTAX  ThreePortID
            ACCESS  read-only
            STATUS  mandatory
            DESCRIPTION
                "Port 1 to 3, total 3 ports."
            ::= { triT1LineTotalPerfEntry 2 }

        triT1LineTotalPerfES  OBJECT-TYPE
            SYNTAX  Gauge
            ACCESS  read-only
            STATUS  mandatory
            DESCRIPTION
                " ES Error Counter "
            ::= { triT1LineTotalPerfEntry 3 }

        triT1LineTotalPerfSES  OBJECT-TYPE
            SYNTAX  Gauge
            ACCESS  read-only
            STATUS  mandatory
            DESCRIPTION
                " SES Error Counter "
            ::= { triT1LineTotalPerfEntry 4 }

        triT1LineTotalPerfBES  OBJECT-TYPE
            SYNTAX  Gauge
            ACCESS  read-only
            STATUS  mandatory
            DESCRIPTION
                " BES Error Counter "
            ::= { triT1LineTotalPerfEntry 5 }

        triT1LineTotalPerfUAS  OBJECT-TYPE
            SYNTAX  Gauge
            ACCESS  read-only
            STATUS  mandatory
            DESCRIPTION
                " UAS Error Counter "
            ::= { triT1LineTotalPerfEntry 6 }

        triT1LineTotalPerfCSS  OBJECT-TYPE
            SYNTAX  Gauge
            ACCESS  read-only
            STATUS  mandatory
            DESCRIPTION
                " CSS Error Counter "
            ::= { triT1LineTotalPerfEntry 7 }

        triT1LineTotalPerfBPV  OBJECT-TYPE
            SYNTAX  Gauge
            ACCESS  read-only
            STATUS  mandatory
            DESCRIPTION
                " BPV Error Counter "
            ::= { triT1LineTotalPerfEntry 8 }

        triT1LineTotalPerfLOFC  OBJECT-TYPE
            SYNTAX  Gauge
            ACCESS  read-only
            STATUS  mandatory
            DESCRIPTION
                " LOFC Error Counter "
            ::= { triT1LineTotalPerfEntry 9 }


--
--  Line Seven Days Performance Table
--
        triT1Line7DaysPerfTable  OBJECT-TYPE
            SYNTAX  SEQUENCE OF TriT1Line7DaysPerfEntry
            ACCESS  not-accessible
            STATUS  mandatory
            DESCRIPTION
                "Line 7 Days Performance Table"
            ::= { triT1card 9 }

        triT1Line7DaysPerfEntry  OBJECT-TYPE
            SYNTAX  TriT1Line7DaysPerfEntry
            ACCESS  not-accessible
            STATUS  mandatory
            DESCRIPTION
                "Line 7 days performance entry"
            INDEX { triT1LSPslot , triT1LSPport ,
                    triT1LineDaysIndex }
            ::= { triT1Line7DaysPerfTable 1 }

        TriT1Line7DaysPerfEntry ::= SEQUENCE  {
            triT1LSPslot                  LSSlotID,
            triT1LSPport                  ThreePortID,
            triT1LineDaysIndex            INTEGER,
            triT1LineDateStrIndex         DisplayString,
            triT1Line7DaysPerfES          Gauge,
            triT1Line7DaysPerfSES         Gauge,
            triT1Line7DaysPerfBES         Gauge,
            triT1Line7DaysPerfUAS         Gauge,
            triT1Line7DaysPerfCSS         Gauge
        }

        triT1LSPslot  OBJECT-TYPE
            SYNTAX  LSSlotID
            ACCESS  read-only
            STATUS  mandatory
            DESCRIPTION
                "3T1 slot index"
            ::= { triT1Line7DaysPerfEntry 1 }

        triT1LSPport  OBJECT-TYPE
            SYNTAX  ThreePortID
            ACCESS  read-only
            STATUS  mandatory
            DESCRIPTION
                "Port 1 to 3, total 3 ports."
            ::= { triT1Line7DaysPerfEntry 2 }

        triT1LineDaysIndex  OBJECT-TYPE
            SYNTAX  INTEGER (1..7)
            ACCESS  read-only
            STATUS  mandatory
            DESCRIPTION
                "Seven Days index "
            ::= { triT1Line7DaysPerfEntry 3 }

        triT1LineDateStrIndex  OBJECT-TYPE
            SYNTAX  DisplayString (SIZE (0..255) )
            ACCESS  read-only
            STATUS  mandatory
            DESCRIPTION
                "Seven Days String "
            ::= { triT1Line7DaysPerfEntry 4 }

        triT1Line7DaysPerfES  OBJECT-TYPE
            SYNTAX  Gauge
            ACCESS  read-only
            STATUS  mandatory
            DESCRIPTION
                " ES Error Counter "
            ::= { triT1Line7DaysPerfEntry 5 }

        triT1Line7DaysPerfSES  OBJECT-TYPE
            SYNTAX  Gauge
            ACCESS  read-only
            STATUS  mandatory
            DESCRIPTION
                " SES Error Counter "
            ::= { triT1Line7DaysPerfEntry 6 }

        triT1Line7DaysPerfBES  OBJECT-TYPE
            SYNTAX  Gauge
            ACCESS  read-only
            STATUS  mandatory
            DESCRIPTION
                " BES Error Counter "
            ::= { triT1Line7DaysPerfEntry 7 }

        triT1Line7DaysPerfUAS  OBJECT-TYPE
            SYNTAX  Gauge
            ACCESS  read-only
            STATUS  mandatory
            DESCRIPTION
                " UAS Error Counter "
            ::= { triT1Line7DaysPerfEntry 8 }

        triT1Line7DaysPerfCSS  OBJECT-TYPE
            SYNTAX  Gauge
            ACCESS  read-only
            STATUS  mandatory
            DESCRIPTION
                " CSS Error Counter "
            ::= { triT1Line7DaysPerfEntry 9 }


--
--  Alarm History Table
--

        triT1AlarmHistoryTable  OBJECT-TYPE
            SYNTAX  SEQUENCE OF TriT1AlarmHistoryEntry
            ACCESS  not-accessible
            STATUS  mandatory
            DESCRIPTION
                "Alarm History Table"
            ::= { triT1card 12 }

        triT1AlarmHistoryEntry  OBJECT-TYPE
            SYNTAX  TriT1AlarmHistoryEntry
            ACCESS  not-accessible
            STATUS  mandatory
            DESCRIPTION
                "Alarm history entry"
            INDEX { triT1AHslot , triT1AHport ,
                    triT1AlarmHistoryIndex }
            ::= { triT1AlarmHistoryTable 1 }

        TriT1AlarmHistoryEntry ::= SEQUENCE  {
            triT1AHslot                   LSSlotID,
            triT1AHport                   ThreePortID,
            triT1AlarmHistoryIndex        INTEGER,
            triT1Threshold                INTEGER,
            triT1CurrentState             INTEGER,
            triT1CurrentCount             INTEGER,
            triT1Alarm                    LsAlarmSeverity
        }

        triT1AHslot  OBJECT-TYPE
            SYNTAX  LSSlotID
            ACCESS  read-only
            STATUS  mandatory
            DESCRIPTION
                "3T1 slot index"
            ::= { triT1AlarmHistoryEntry 1 }

        triT1AHport  OBJECT-TYPE
            SYNTAX  ThreePortID
            ACCESS  read-only
            STATUS  mandatory
            DESCRIPTION
                "Port 1 to 3, total 3 ports."
            ::= { triT1AlarmHistoryEntry 2 }

        triT1AlarmHistoryIndex  OBJECT-TYPE
            SYNTAX  INTEGER {
                    yelLine(1),
                    aisLine(2),
                    losLine(3),
                    lofLine(4),
                    bpvLine(5),
                    essLine(6),
                    uasLine(7),
                    cssLine(8),
                    aisInsert(9)
                }
            ACCESS  read-only
            STATUS  mandatory
            DESCRIPTION
                " Alarm History Index "
            ::= { triT1AlarmHistoryEntry 3 }

        triT1Threshold  OBJECT-TYPE
            SYNTAX  INTEGER
            ACCESS  read-only
            STATUS  mandatory
            DESCRIPTION
                " Alarm History Threshold Value "
            ::= { triT1AlarmHistoryEntry 4 }

        triT1CurrentState  OBJECT-TYPE
            SYNTAX  INTEGER {
                    ok(1),
                    alarm(2),
                    disable(3)
                }
            ACCESS  read-only
            STATUS  mandatory
            DESCRIPTION
                " Alarm History Current State"
            ::= { triT1AlarmHistoryEntry 5 }

        triT1CurrentCount  OBJECT-TYPE
            SYNTAX  INTEGER
            ACCESS  read-only
            STATUS  mandatory
            DESCRIPTION
                " Alarm History Current Count "
            ::= { triT1AlarmHistoryEntry 6 }

        triT1Alarm  OBJECT-TYPE
            SYNTAX  LsAlarmSeverity
            ACCESS  read-only
            STATUS  mandatory
            DESCRIPTION
                "Alarm History Alarm State"
            ::= { triT1AlarmHistoryEntry 7 }


--
--  Line Availability Table
--

        triT1LineAvailTable  OBJECT-TYPE
            SYNTAX  SEQUENCE OF TriT1LineAvailEntry
            ACCESS  not-accessible
            STATUS  mandatory
            DESCRIPTION
                "The DS1 line control table."
            ::= { triT1card 13 }

        triT1LineAvailEntry  OBJECT-TYPE
            SYNTAX  TriT1LineAvailEntry
            ACCESS  not-accessible
            STATUS  mandatory
            DESCRIPTION
                "An entry in the DS1 line control table."
            INDEX { triT1LAslot , triT1LAport }
            ::= { triT1LineAvailTable 1 }

        TriT1LineAvailEntry ::= SEQUENCE  {
            triT1LAslot                   LSSlotID,
            triT1LAport                   ThreePortID,
            triT1AvailableSeconds         DisplayString,
            triT1UnavailableSeconds       DisplayString,
            triT1LineAvail                DisplayString
        }

        triT1LAslot  OBJECT-TYPE
            SYNTAX  LSSlotID
            ACCESS  read-only
            STATUS  mandatory
            DESCRIPTION
                "3T1 slot index"
            ::= { triT1LineAvailEntry 1 }

        triT1LAport  OBJECT-TYPE
            SYNTAX  ThreePortID
            ACCESS  read-only
            STATUS  mandatory
            DESCRIPTION
                "Port 1 to 3, total 3 ports."
            ::= { triT1LineAvailEntry 2 }

        triT1AvailableSeconds  OBJECT-TYPE
            SYNTAX  DisplayString (SIZE(0..255))
            ACCESS  read-only
            STATUS  mandatory
            DESCRIPTION
                "Line Available Seconds"
            ::= { triT1LineAvailEntry 3 }

        triT1UnavailableSeconds  OBJECT-TYPE
            SYNTAX  DisplayString (SIZE(0..255))
            ACCESS  read-only
            STATUS  mandatory
            DESCRIPTION
                "Line Unavailable Seconds"
            ::= { triT1LineAvailEntry 4 }

        triT1LineAvail  OBJECT-TYPE
            SYNTAX  DisplayString (SIZE(0..255))
            ACCESS  read-only
            STATUS  mandatory
            DESCRIPTION
                "Line Available Percentage"
            ::= { triT1LineAvailEntry 5 }


--
--  Alarm Control Table
--

        triT1AlarmControlTable  OBJECT-TYPE
            SYNTAX  SEQUENCE OF TriT1AlarmControlEntry
            ACCESS  not-accessible
            STATUS  mandatory
            DESCRIPTION
                "The alarm control table."
            ::= { triT1card 14 }

        triT1AlarmControlEntry  OBJECT-TYPE
            SYNTAX  TriT1AlarmControlEntry
            ACCESS  not-accessible
            STATUS  mandatory
            DESCRIPTION
                "An entry in the DS1 alarm control table."
            INDEX { triT1ACslot , triT1ACport }
            ::= { triT1AlarmControlTable 1 }

        TriT1AlarmControlEntry ::= SEQUENCE  {
            triT1ACslot                   LSSlotID,
            triT1ACport                   ThreePortID,
            triT1YELline                  LsAlarmSeverity,
            triT1AISline                  LsAlarmSeverity,
            triT1LOSline                  LsAlarmSeverity,
            triT1LOFline                  LsAlarmSeverity,
            triT1BPVline                  LsAlarmSeverity,
            triT1ESSline                  LsAlarmSeverity,
            triT1UASline                  LsAlarmSeverity,
            triT1CSSline                  LsAlarmSeverity,
            triT1AISinsert                LsAlarmSeverity
        }

        triT1ACslot  OBJECT-TYPE
            SYNTAX  LSSlotID
            ACCESS  read-only
            STATUS  mandatory
            DESCRIPTION
                "3T1 slot index"
            ::= { triT1AlarmControlEntry 1 }

        triT1ACport  OBJECT-TYPE
            SYNTAX  ThreePortID
            ACCESS  read-only
            STATUS  mandatory
            DESCRIPTION
                "Port 1 to 3, total 3 ports."
            ::= { triT1AlarmControlEntry 2 }

        triT1YELline  OBJECT-TYPE
            SYNTAX  LsAlarmSeverity
            ACCESS  read-write
            STATUS  mandatory
            DESCRIPTION
                "YEL-Line State"
            ::= { triT1AlarmControlEntry 3 }

        triT1AISline  OBJECT-TYPE
            SYNTAX  LsAlarmSeverity
            ACCESS  read-write
            STATUS  mandatory
            DESCRIPTION
                "AIS-Line State"
            ::= { triT1AlarmControlEntry 4 }

        triT1LOSline  OBJECT-TYPE
            SYNTAX  LsAlarmSeverity
            ACCESS  read-write
            STATUS  mandatory
            DESCRIPTION
                "LOS-line State"
            ::= { triT1AlarmControlEntry 5 }

        triT1LOFline  OBJECT-TYPE
            SYNTAX  LsAlarmSeverity
            ACCESS  read-write
            STATUS  mandatory
            DESCRIPTION
                "LOF-Line State"
            ::= { triT1AlarmControlEntry 6 }

        triT1BPVline  OBJECT-TYPE
            SYNTAX  LsAlarmSeverity
            ACCESS  read-write
            STATUS  mandatory
            DESCRIPTION
                "BPV-Line State"
            ::= { triT1AlarmControlEntry 7 }

        triT1ESSline  OBJECT-TYPE
            SYNTAX  LsAlarmSeverity
            ACCESS  read-write
            STATUS  mandatory
            DESCRIPTION
                "ESS-Line State"
            ::= { triT1AlarmControlEntry 8 }

        triT1UASline  OBJECT-TYPE
            SYNTAX  LsAlarmSeverity
            ACCESS  read-write
            STATUS  mandatory
            DESCRIPTION
                "UAS-Line State"
            ::= { triT1AlarmControlEntry 9 }

        triT1CSSline  OBJECT-TYPE
            SYNTAX  LsAlarmSeverity
            ACCESS  read-write
            STATUS  mandatory
            DESCRIPTION
                "CS-Line State"
            ::= { triT1AlarmControlEntry 10 }

        triT1AISinsert  OBJECT-TYPE
            SYNTAX  LsAlarmSeverity
            ACCESS  read-write
            STATUS  mandatory
            DESCRIPTION
                "3T1 AIS insert"
            ::= { triT1AlarmControlEntry 11 }


--
--  Threshold Control Table
--

        triT1ThresholdCtrlTable  OBJECT-TYPE
            SYNTAX  SEQUENCE OF TriT1ThresholdCtrlEntry
            ACCESS  not-accessible
            STATUS  mandatory
            DESCRIPTION
                "The alarm control table."
            ::= { triT1card 15 }

        triT1ThresholdCtrlEntry  OBJECT-TYPE
            SYNTAX  TriT1ThresholdCtrlEntry
            ACCESS  not-accessible
            STATUS  mandatory
            DESCRIPTION
                "An entry in the DS1 threshold control table."
            INDEX { triT1TCslot , triT1TCport }
            ::= { triT1ThresholdCtrlTable 1 }

        TriT1ThresholdCtrlEntry ::= SEQUENCE  {
            triT1TCslot                   LSSlotID,
            triT1TCport                   ThreePortID,
            triT1ThresholdBPVline         INTEGER,
            triT1ThresholdESSline         INTEGER,
            triT1ThresholdUASline         INTEGER,
            triT1ThresholdCSSline         INTEGER,
            triT1ThresholdAISinsert       INTEGER
        }

        triT1TCslot  OBJECT-TYPE
            SYNTAX  LSSlotID
            ACCESS  read-only
            STATUS  mandatory
            DESCRIPTION
                "3T1 slot index"
            ::= { triT1ThresholdCtrlEntry 1 }

        triT1TCport  OBJECT-TYPE
            SYNTAX  ThreePortID
            ACCESS  read-only
            STATUS  mandatory
            DESCRIPTION
                "Port 1 to 3, total 3 ports."
            ::= { triT1ThresholdCtrlEntry 2 }

        triT1ThresholdBPVline  OBJECT-TYPE
            SYNTAX  INTEGER (5..9)
            ACCESS  read-write
            STATUS  mandatory
            DESCRIPTION
                " Threshold of BPV-Line: 10exp-N"
            ::= { triT1ThresholdCtrlEntry 3 }

        triT1ThresholdESSline  OBJECT-TYPE
            SYNTAX  INTEGER (1..900)
            ACCESS  read-write
            STATUS  mandatory
            DESCRIPTION
                " Threshold of ESS-Line "
            ::= { triT1ThresholdCtrlEntry 4 }

        triT1ThresholdUASline  OBJECT-TYPE
            SYNTAX  INTEGER (1..900)
            ACCESS  read-write
            STATUS  mandatory
            DESCRIPTION
                " Threshold of UAS-Line "
            ::= { triT1ThresholdCtrlEntry 5 }

        triT1ThresholdCSSline  OBJECT-TYPE
            SYNTAX  INTEGER (1..900)
            ACCESS  read-write
            STATUS  mandatory
            DESCRIPTION
                " Threshold of CS-Line "
            ::= { triT1ThresholdCtrlEntry 6 }

        triT1ThresholdAISinsert  OBJECT-TYPE
            SYNTAX  INTEGER (3..6)
            ACCESS  read-write
            STATUS  mandatory
            DESCRIPTION
                " Threshold of 3T1 AIS Insert: 10exp-N"
            ::= { triT1ThresholdCtrlEntry 7 }


--
-- Line Diagnostic Control Table
--

        triT1LineDiagCtrlTable  OBJECT-TYPE
            SYNTAX  SEQUENCE OF TriT1LineDiagCtrlEntry
            ACCESS  not-accessible
            STATUS  mandatory
            DESCRIPTION
                "The alarm control table."
            ::= { triT1card 16 }

        triT1LineDiagCtrlEntry  OBJECT-TYPE
            SYNTAX  TriT1LineDiagCtrlEntry
            ACCESS  not-accessible
            STATUS  mandatory
            DESCRIPTION
                "An entry in the DS1 threshold control table."
            INDEX { triT1DCslot , triT1DCport }
            ::= { triT1LineDiagCtrlTable 1 }

        TriT1LineDiagCtrlEntry ::= SEQUENCE  {
            triT1DCslot                   LSSlotID,
            triT1DCport                   ThreePortID,
            triT1LoopbackType             INTEGER,
            triT1LoopbackStatus           INTEGER,
            triT1QRSSControl              INTEGER,
            triT1QRSSStatus               INTEGER,
            triT1QRSSElapseSeconds        INTEGER,
            triT1QRSSErrorSeconds         INTEGER,
            triT1QRSSErrorCounts          INTEGER,
            triT1InbandLoopbackPeriod     INTEGER
        }

        triT1DCslot  OBJECT-TYPE
            SYNTAX  LSSlotID
            ACCESS  read-only
            STATUS  mandatory
            DESCRIPTION
                "3T1 slot index"
            ::= { triT1LineDiagCtrlEntry 1 }

        triT1DCport  OBJECT-TYPE
            SYNTAX  ThreePortID
            ACCESS  read-only
            STATUS  mandatory
            DESCRIPTION
                "Port 1 to 3, total 3 ports."
            ::= { triT1LineDiagCtrlEntry 2 }

        triT1LoopbackType  OBJECT-TYPE
            SYNTAX  INTEGER {
                    noLoopback(1),
                    localLoopback(2),
                    payloadLoopback(3),
                    lineLoopback(4),
                    remoteLlbInbandActive(5),
                    remotePlbAttActive(6),
                    remotePlbAnsiActive(7),
                    remoteLlbAnsiActive(8),
                    remoteLlbInbandDeactive(9),
                    remotePlbAttDeactive(10),
                    remotePlbAnsiDeactive(11),
                    remoteLlbAnsiDeactive(12)
                }
            ACCESS  read-write
            STATUS  mandatory
            DESCRIPTION
                "3T1 Loopback Type"
            ::= { triT1LineDiagCtrlEntry 3 }

        triT1LoopbackStatus  OBJECT-TYPE
            SYNTAX  INTEGER {
                    success(1),
                    fail(2),
                    loopbackNotActive(3)
                }
            ACCESS  read-only
            STATUS  mandatory
            DESCRIPTION
                "3T1 Loopback Status"
            ::= { triT1LineDiagCtrlEntry 4 }

        triT1QRSSControl  OBJECT-TYPE
            SYNTAX  INTEGER {
                    qrssDeactive(1),
                    qrssActiveFull(2),
                    qrssResetErrorCount(3),
                    qrssInjectError(4)
                }
            ACCESS  read-write
            STATUS  mandatory
            DESCRIPTION
                "3T1 QRSS Control"
            ::= { triT1LineDiagCtrlEntry 5 }

        triT1QRSSStatus  OBJECT-TYPE
            SYNTAX  INTEGER {
                    qrssSync(1),
                    qrssUnsync(2),
                    qrssNotActive(3)
                }
            ACCESS  read-only
            STATUS  mandatory
            DESCRIPTION
                "3T1 QRSS Status"
            ::= { triT1LineDiagCtrlEntry 6 }

        triT1QRSSElapseSeconds  OBJECT-TYPE
            SYNTAX  INTEGER
            ACCESS  read-only
            STATUS  mandatory
            DESCRIPTION
                "3T1 QRSS Elapse Seconds"
            ::= { triT1LineDiagCtrlEntry 7 }

        triT1QRSSErrorSeconds  OBJECT-TYPE
            SYNTAX  INTEGER
            ACCESS  read-only
            STATUS  mandatory
            DESCRIPTION
                "3T1 QRSS Error Seconds"
            ::= { triT1LineDiagCtrlEntry 8 }

        triT1QRSSErrorCounts  OBJECT-TYPE
            SYNTAX  INTEGER
            ACCESS  read-only
            STATUS  mandatory
            DESCRIPTION
                "3T1 QRSS Error Counts"
            ::= { triT1LineDiagCtrlEntry 9 }

        triT1InbandLoopbackPeriod  OBJECT-TYPE
            SYNTAX  INTEGER
            ACCESS  read-write
            STATUS  mandatory
            DESCRIPTION
                "period(in seconds) of TriT1 inband local, payload, or line loopback"
            ::= { triT1LineDiagCtrlEntry 10 }


--
--  Command Control Table
--

        triT1CommandControlTable  OBJECT-TYPE
            SYNTAX  SEQUENCE OF TriT1CommandControlEntry
            ACCESS  not-accessible
            STATUS  mandatory
            DESCRIPTION
                "The command control table."
            ::= { triT1card 17 }

        triT1CommandControlEntry  OBJECT-TYPE
            SYNTAX  TriT1CommandControlEntry
            ACCESS  not-accessible
            STATUS  mandatory
            DESCRIPTION
                "An entry in the command control table."
            INDEX { triT1CCslot , triT1CCport }
            ::= { triT1CommandControlTable 1 }

        TriT1CommandControlEntry ::= SEQUENCE  {
            triT1CCslot                   LSSlotID,
            triT1CCport                   ThreePortID,
            triT1AlarmQueueReset          INTEGER,
            triT1UserPerfReset            INTEGER,
            triT1AlarmHistoryReset        INTEGER,
            triT1PortReset                INTEGER,
            triT1PortLoadDefault          INTEGER
        }

        triT1CCslot  OBJECT-TYPE
            SYNTAX  LSSlotID
            ACCESS  read-only
            STATUS  mandatory
            DESCRIPTION
                "3T1 slot index"
            ::= { triT1CommandControlEntry 1 }

        triT1CCport  OBJECT-TYPE
            SYNTAX  ThreePortID
            ACCESS  read-only
            STATUS  mandatory
            DESCRIPTION
                "Port 1 to 3, total 3 ports."
            ::= { triT1CommandControlEntry 2 }

        triT1AlarmQueueReset    OBJECT-TYPE
            SYNTAX  INTEGER {
                    no(0),
                    reset(1)
                }
            ACCESS  read-write
            STATUS  mandatory
            DESCRIPTION
                "Command: Reset Alarm Queue "
            ::= { triT1CommandControlEntry 3 }

        triT1UserPerfReset    OBJECT-TYPE
            SYNTAX  INTEGER {
                    no(0),
                    reset(1)
                }
            ACCESS  read-write
            STATUS  mandatory
            DESCRIPTION
                "Command: Reset User Performance"
            ::= { triT1CommandControlEntry 4 }

        triT1AlarmHistoryReset    OBJECT-TYPE
            SYNTAX  INTEGER {
                    no(0),
                    reset(1)
                }
            ACCESS  read-write
            STATUS  mandatory
            DESCRIPTION
                "Command: Reset Alarm History"
            ::= { triT1CommandControlEntry 5 }

        triT1PortReset    OBJECT-TYPE
            SYNTAX  INTEGER {
                    no(0),
                    reset(1)
                }
            ACCESS  read-write
            STATUS  mandatory
            DESCRIPTION
                "Command: Reset TriT1 Port"
            ::= { triT1CommandControlEntry 6 }

        triT1PortLoadDefault    OBJECT-TYPE
            SYNTAX  INTEGER {
                    no(0),
                    loadDefault(1)
                }
            ACCESS  read-write
            STATUS  mandatory
            DESCRIPTION
                "Command: Load Default TriT1 Port"
            ::= { triT1CommandControlEntry 7 }


--
--  SYSTEM Information Table
--

        triT1SystemInfoTable  OBJECT-TYPE
            SYNTAX  SEQUENCE OF TriT1SystemInfoEntry
            ACCESS  not-accessible
            STATUS  mandatory
            DESCRIPTION
                "The system information table."
            ::= { triT1card 18 }

        triT1SystemInfoEntry  OBJECT-TYPE
            SYNTAX  TriT1SystemInfoEntry
            ACCESS  not-accessible
            STATUS  mandatory
            DESCRIPTION
                "An entry in the system information table."
            INDEX { triT1SIslot }
            ::= { triT1SystemInfoTable 1 }

        TriT1SystemInfoEntry ::= SEQUENCE  {
            triT1SIslot                   LSSlotID,
            triT1PROMVersion              DisplayString,
            triT1HardwareVersion          DisplayString
        }

        triT1SIslot  OBJECT-TYPE
            SYNTAX  LSSlotID
            ACCESS  read-only
            STATUS  mandatory
            DESCRIPTION
                "3T1 slot index"
            ::= { triT1SystemInfoEntry 1 }

        triT1PROMVersion  OBJECT-TYPE
            SYNTAX  DisplayString (SIZE (0..255) )
            ACCESS  read-only
            STATUS  mandatory
            DESCRIPTION
                " triT1 PROM Version"
            ::= { triT1SystemInfoEntry 2 }

        triT1HardwareVersion  OBJECT-TYPE
            SYNTAX  DisplayString (SIZE (0..255) )
            ACCESS  read-only
            STATUS  mandatory
            DESCRIPTION
                " triT1 Hardware Version"
            ::= { triT1SystemInfoEntry 3 }


--
--  TriT1 Customer Information Table
--

        triT1CustomerInfoTable  OBJECT-TYPE
            SYNTAX  SEQUENCE OF TriT1CustomerInfoEntry
            ACCESS  not-accessible
            STATUS  mandatory
            DESCRIPTION
                "The Customer Information table."
            ::= { triT1card 99 }

        triT1CustomerInfoEntry  OBJECT-TYPE
            SYNTAX  TriT1CustomerInfoEntry
            ACCESS  not-accessible
            STATUS  mandatory
            DESCRIPTION
                "An entry in the Customer Information table."
            INDEX { triT1CISlotIndex , triT1CIPortIndex }
            ::= { triT1CustomerInfoTable 1 }

        TriT1CustomerInfoEntry ::= SEQUENCE {
            triT1CISlotIndex              LSSlotID,
            triT1CIPortIndex              ThreePortID,
            triT1CICustomerInfo           DisplayString
        }

        triT1CISlotIndex    OBJECT-TYPE
            SYNTAX  LSSlotID
            ACCESS  read-only
            STATUS  mandatory
            DESCRIPTION
                "3T1 slot index"
            ::= { triT1CustomerInfoEntry 1 }

        triT1CIPortIndex    OBJECT-TYPE
            SYNTAX  ThreePortID
            ACCESS  read-only
            STATUS  mandatory
            DESCRIPTION
                "Port number"
            ::= { triT1CustomerInfoEntry 2 }

        triT1CICustomerInfo  OBJECT-TYPE
            SYNTAX  DisplayString (SIZE (0..64) )
            ACCESS  read-write
            STATUS  mandatory
            DESCRIPTION
                "Customer information"
            ::= { triT1CustomerInfoEntry 3 }


        triT1TotalCard   OBJECT-TYPE
            SYNTAX  INTEGER
            ACCESS  read-only
            STATUS  mandatory
            DESCRIPTION
                "Total cards of TriT1"
            ::= { triT1card 100 }


--======================================================================--
--======================================================================--
--  octDte card MIB
--======================================================================--
--======================================================================--


--
--      DTE Control Table
--

        dte8ConfigCtrlTable  OBJECT-TYPE
            SYNTAX  SEQUENCE OF Dte8ConfigCtrlEntry
            ACCESS  not-accessible
            STATUS  mandatory
            DESCRIPTION
                "8UDTE Configuration Control Table"
            ::= { octDte-card 1 }

        dte8ConfigCtrlEntry  OBJECT-TYPE
            SYNTAX  Dte8ConfigCtrlEntry
            ACCESS  not-accessible
            STATUS  mandatory
            DESCRIPTION
                "8UDTE configuration control entry"
            INDEX { dte8ccSlotIndex ,
                    dte8ccPortIndex }
            ::= { dte8ConfigCtrlTable 1 }

        Dte8ConfigCtrlEntry ::= SEQUENCE {
            dte8ccSlotIndex             LSSlotID,
            dte8ccPortIndex             PortID,
            dte8Interface               INTEGER,
            dte8DS0Rate                 INTEGER,
            dte8Oversampling            INTEGER,
            dte8OversamplingRate        INTEGER,
            dte8SupportDataRate         DisplayString,
            dte8RTSCTS                  INTEGER,
            dte8DTRDSR                  INTEGER
        }

        dte8ccSlotIndex  OBJECT-TYPE
            SYNTAX  LSSlotID
            ACCESS  read-only
            STATUS  mandatory
            DESCRIPTION
                "8UDTE slot index"
            ::= { dte8ConfigCtrlEntry 1 }

        dte8ccPortIndex  OBJECT-TYPE
            SYNTAX  PortID
            ACCESS  read-only
            STATUS  mandatory
            DESCRIPTION
                "Port 1~8"
            ::= { dte8ConfigCtrlEntry 2 }

        dte8Interface   OBJECT-TYPE
            SYNTAX  INTEGER {
                    rs232(1),
                    rs485(2),
                    rs422(3)
                }
            ACCESS  read-write
            STATUS  mandatory
            DESCRIPTION
                "8UDTE Interface Type"
            ::= { dte8ConfigCtrlEntry 3 }

        dte8DS0Rate   OBJECT-TYPE
            SYNTAX  INTEGER {
                    rate64k(1),
                    rate56k(2)
                }
            ACCESS  read-write
            STATUS  mandatory
            DESCRIPTION
                "8UDTE DS0 Sampling Rate"
            ::= { dte8ConfigCtrlEntry 4 }

        dte8Oversampling   OBJECT-TYPE
            SYNTAX  INTEGER (1..6)
            ACCESS  read-write
            STATUS  mandatory
            DESCRIPTION
                "8UDTE oversampling numver"
            ::= { dte8ConfigCtrlEntry 5 }

        dte8OversamplingRate   OBJECT-TYPE
            SYNTAX  INTEGER
            ACCESS  read-only
            STATUS  mandatory
            DESCRIPTION
                "8UDTE Oversampling Rate (Kbps)"
            ::= { dte8ConfigCtrlEntry 6 }

        dte8SupportDataRate   OBJECT-TYPE
            SYNTAX  DisplayString
            ACCESS  read-only
            STATUS  mandatory
            DESCRIPTION
                "8UDTE Supported Data Rate"
            ::= { dte8ConfigCtrlEntry 7 }

        dte8RTSCTS   OBJECT-TYPE
            SYNTAX  INTEGER {
                    active(1),
                    permanent(2),
                    na(3)
                }
            ACCESS  read-write
            STATUS  mandatory
            DESCRIPTION
                "8UDTE RTS/CTS control"
            ::= { dte8ConfigCtrlEntry 8 }

        dte8DTRDSR   OBJECT-TYPE
            SYNTAX  INTEGER {
                    active(1),
                    permanent(2),
                    na(3)
                }
            ACCESS  read-write
            STATUS  mandatory
            DESCRIPTION
                "8UDTE DTR/DSR control"
            ::= { dte8ConfigCtrlEntry 9 }



--
--  Alarm Control Table
--

        dte8AlarmControlTable  OBJECT-TYPE
            SYNTAX  SEQUENCE OF Dte8AlarmControlEntry
            ACCESS  not-accessible
            STATUS  mandatory
            DESCRIPTION
                "8UDTE alarm control table."
            ::= { octDte-card 3 }

        dte8AlarmControlEntry  OBJECT-TYPE
            SYNTAX  Dte8AlarmControlEntry
            ACCESS  not-accessible
            STATUS  mandatory
            DESCRIPTION
                "8UDTE alarm control entry."
            INDEX { dte8acSlotIndex ,
                    dte8acPortIndex }
            ::= { dte8AlarmControlTable 1 }

        Dte8AlarmControlEntry ::= SEQUENCE {
            dte8acSlotIndex             LSSlotID,
            dte8acPortIndex             PortID,
            dte8AlarmEnable             LsAlarmSeverity,
            dte8AlarmState              INTEGER,
            dte8AlarmCount              INTEGER,
            dte8ThrLOLCAlarmEnable      LsAlarmSeverity,
            dte8ThrLOLCState            INTEGER,
            dte8ThrLOLCAlarmCount       INTEGER,
            dte8ThrLOCHAlarmEnable      LsAlarmSeverity,
            dte8ThrLOCHState            INTEGER,
            dte8ThrLOCHAlarmCount       INTEGER,
            dte8ThrCREAlarmEnable       LsAlarmSeverity,
            dte8ThrCREState             INTEGER,
            dte8ThrCREAlarmCount        INTEGER,
            dte8ThrResetCounter         INTEGER
        }

        dte8acSlotIndex  OBJECT-TYPE
            SYNTAX  LSSlotID
            ACCESS  read-only
            STATUS  mandatory
            DESCRIPTION
                "8UDTE slot index"
            ::= { dte8AlarmControlEntry 1 }

        dte8acPortIndex  OBJECT-TYPE
            SYNTAX  PortID
            ACCESS  read-only
            STATUS  mandatory
            DESCRIPTION
                "Port 1~8"
            ::= { dte8AlarmControlEntry 2 }

        dte8AlarmEnable  OBJECT-TYPE
            SYNTAX  LsAlarmSeverity
            ACCESS  read-write
            STATUS  mandatory
            DESCRIPTION
                "DTE-Alarm State"
            ::= { dte8AlarmControlEntry 3 }

        dte8AlarmState  OBJECT-TYPE
            SYNTAX  INTEGER {
                    ok(1),
                    alarm(2),
                    disable(3)
                }
            ACCESS  read-only
            STATUS  mandatory
            DESCRIPTION
                " Alarm History Current State"
            ::= { dte8AlarmControlEntry 4 }

        dte8AlarmCount  OBJECT-TYPE
            SYNTAX  INTEGER
            ACCESS  read-only
            STATUS  mandatory
            DESCRIPTION
                " Alarm History Current Count "
            ::= { dte8AlarmControlEntry 5 }

        dte8ThrLOLCAlarmEnable  OBJECT-TYPE
            SYNTAX  LsAlarmSeverity
            ACCESS  read-write
            STATUS  mandatory
            DESCRIPTION
                "DTE-Alarm Loss Of Clock State"
            ::= { dte8AlarmControlEntry 6 }

        dte8ThrLOLCState  OBJECT-TYPE
            SYNTAX  INTEGER {
                    ok(1),
                    alarm(2),
                    disable(3)
                }
            ACCESS  read-only
            STATUS  mandatory
            DESCRIPTION
                " Alarm History Current State - Loss Of Clock"
            ::= { dte8AlarmControlEntry 7 }

        dte8ThrLOLCAlarmCount  OBJECT-TYPE
            SYNTAX  INTEGER
            ACCESS  read-only
            STATUS  mandatory
            DESCRIPTION
                " Alarm History Current Count - Loss Of Clock "
            ::= { dte8AlarmControlEntry 8 }

        dte8ThrLOCHAlarmEnable  OBJECT-TYPE
            SYNTAX  LsAlarmSeverity
            ACCESS  read-write
            STATUS  mandatory
            DESCRIPTION
                "DTE-Alarm Loss Of Channel State"
            ::= { dte8AlarmControlEntry 9 }

        dte8ThrLOCHState  OBJECT-TYPE
            SYNTAX  INTEGER {
                    ok(1),
                    alarm(2),
                    disable(3)
                }
            ACCESS  read-only
            STATUS  mandatory
            DESCRIPTION
                " Alarm History Current State - Loss Of Channel"
            ::= { dte8AlarmControlEntry 10 }

        dte8ThrLOCHAlarmCount  OBJECT-TYPE
            SYNTAX  INTEGER
            ACCESS  read-only
            STATUS  mandatory
            DESCRIPTION
                " Alarm History Current Count - Loss Of Channel "
            ::= { dte8AlarmControlEntry 11 }

        dte8ThrCREAlarmEnable  OBJECT-TYPE
            SYNTAX  LsAlarmSeverity
            ACCESS  read-write
            STATUS  mandatory
            DESCRIPTION
                "DTE-Alarm Clock Recovery Error State"
            ::= { dte8AlarmControlEntry 12 }

        dte8ThrCREState  OBJECT-TYPE
            SYNTAX  INTEGER {
                    ok(1),
                    alarm(2),
                    disable(3)
                }
            ACCESS  read-only
            STATUS  mandatory
            DESCRIPTION
                " Alarm History Current State - Clock Recovery Error"
            ::= { dte8AlarmControlEntry 13 }

        dte8ThrCREAlarmCount  OBJECT-TYPE
            SYNTAX  INTEGER
            ACCESS  read-only
            STATUS  mandatory
            DESCRIPTION
                " Alarm History Current Count - Clock Recovery Error "
            ::= { dte8AlarmControlEntry 14 }

        dte8ThrResetCounter  OBJECT-TYPE
            SYNTAX  INTEGER {
                    no(1),
                    reset(2)
                }
            ACCESS  read-write
            STATUS  mandatory
            DESCRIPTION
                "Reset DTE Through Clock alarm counter"
            ::= { dte8AlarmControlEntry 15 }


--
-- Line Diagnostic Control Table
--

        dte8DiagCtrlTable  OBJECT-TYPE
            SYNTAX  SEQUENCE OF Dte8DiagCtrlEntry
            ACCESS  not-accessible
            STATUS  mandatory
            DESCRIPTION
                "8UDTE Diagnostic Control Table."
            ::= { octDte-card 4 }

        dte8DiagCtrlEntry  OBJECT-TYPE
            SYNTAX  Dte8DiagCtrlEntry
            ACCESS  not-accessible
            STATUS  mandatory
            DESCRIPTION
                "8UDTE Diagnostic Control entry."
            INDEX { dte8dcSlotIndex ,
                    dte8dcPortIndex }
            ::= { dte8DiagCtrlTable 1 }

        Dte8DiagCtrlEntry ::= SEQUENCE {
            dte8dcSlotIndex             LSSlotID,
            dte8dcPortIndex             PortID,
            dte8LoopbackType            INTEGER,
            dte8LoopbackStatus          INTEGER
        }

        dte8dcSlotIndex  OBJECT-TYPE
            SYNTAX  LSSlotID
            ACCESS  read-only
            STATUS  mandatory
            DESCRIPTION
                "8UDTE slot index"
            ::= { dte8DiagCtrlEntry 1 }

        dte8dcPortIndex  OBJECT-TYPE
            SYNTAX  PortID
            ACCESS  read-only
            STATUS  mandatory
            DESCRIPTION
                "Port 1~8"
            ::= { dte8DiagCtrlEntry 2 }

        dte8LoopbackType  OBJECT-TYPE
            SYNTAX  INTEGER {
                    no-loopback(1),
                    loopback-To-DTE(2),
                    loopback-To-Line(3)
                }
            ACCESS  read-write
            STATUS  mandatory
            DESCRIPTION
                "DTE Loopback Type"
            ::= { dte8DiagCtrlEntry 3 }

        dte8LoopbackStatus  OBJECT-TYPE
            SYNTAX  INTEGER {
                    success(1),
                    fail(2),
                    loopback-not-active(3)
                }
            ACCESS  read-only
            STATUS  mandatory
            DESCRIPTION
                "DTE Loopback Status"
            ::= { dte8DiagCtrlEntry 4 }


--
--  Command Control Table
--

        dte8CommandInfoTable  OBJECT-TYPE
            SYNTAX  SEQUENCE OF Dte8CommandInfoEntry
            ACCESS  not-accessible
            STATUS  mandatory
            DESCRIPTION
                "The command control table."
            ::= { octDte-card 5 }

        dte8CommandInfoEntry  OBJECT-TYPE
            SYNTAX  Dte8CommandInfoEntry
            ACCESS  not-accessible
            STATUS  mandatory
            DESCRIPTION
                "An entry in the command control table."
            INDEX { dte8ciSlotIndex }
            ::= { dte8CommandInfoTable 1 }

        Dte8CommandInfoEntry ::= SEQUENCE {
            dte8ciSlotIndex             LSSlotID,
            dte8CardReset               INTEGER,
            dte8CardLoadDefault         INTEGER,
            dte8FWversion               DisplayString,
            dte8HWversion               DisplayString
        }

        dte8ciSlotIndex  OBJECT-TYPE
            SYNTAX  LSSlotID
            ACCESS  read-only
            STATUS  mandatory
            DESCRIPTION
                "8UDTE slot index"
            ::= { dte8CommandInfoEntry 1 }

        dte8CardReset    OBJECT-TYPE
            SYNTAX  INTEGER {
                    no(0),
                    reset(1)
                }
            ACCESS  read-write
            STATUS  mandatory
            DESCRIPTION
                "Command: Reset DTE Port"
            ::= { dte8CommandInfoEntry 2 }

        dte8CardLoadDefault    OBJECT-TYPE
            SYNTAX  INTEGER {
                    no(0),
                    loadDefault(1)
                }
            ACCESS  read-write
            STATUS  mandatory
            DESCRIPTION
                "Command: Load Default DTE Port"
            ::= { dte8CommandInfoEntry 3 }

        dte8FWversion  OBJECT-TYPE
            SYNTAX  DisplayString
            ACCESS  read-only
            STATUS  mandatory
            DESCRIPTION
                "8UDTE FW Version"
            ::= { dte8CommandInfoEntry 4 }

        dte8HWversion  OBJECT-TYPE
            SYNTAX  DisplayString
            ACCESS  read-only
            STATUS  mandatory
            DESCRIPTION
                "8UDTE HW Version"
            ::= { dte8CommandInfoEntry 5 }


--
--  DTE Status Table
--

        dte8StatusTable  OBJECT-TYPE
            SYNTAX  SEQUENCE OF Dte8StatusEntry
            ACCESS  not-accessible
            STATUS  mandatory
            DESCRIPTION
                "8UDTE status table."
            ::= { octDte-card 8 }

        dte8StatusEntry  OBJECT-TYPE
            SYNTAX  Dte8StatusEntry
            ACCESS  not-accessible
            STATUS  mandatory
            DESCRIPTION
                "8UDTE status entry."
            INDEX { dte8stSlotIndex ,
                    dte8stPortIndex }
            ::= { dte8StatusTable 1 }

        Dte8StatusEntry ::= SEQUENCE {
            dte8stSlotIndex             LSSlotID,
            dte8stPortIndex             PortID,
            dte8RTSloss                 INTEGER,
            dte8RTS                     INTEGER,
            dte8CTS                     INTEGER,
            dte8DSR                     INTEGER,
            dte8DTR                     INTEGER,
            dte8RxBytesCounter          Counter,
            dte8TxBytesCounter          Counter,
            dte8ResetCounter            INTEGER,
            dte8LOLC                    INTEGER,
            dte8LOCH                    INTEGER,
            dte8CRE                     INTEGER
        }

        dte8stSlotIndex  OBJECT-TYPE
            SYNTAX  LSSlotID
            ACCESS  read-only
            STATUS  mandatory
            DESCRIPTION
                "8UDTE slot index"
            ::= { dte8StatusEntry 1 }

        dte8stPortIndex  OBJECT-TYPE
            SYNTAX  PortID
            ACCESS  read-only
            STATUS  mandatory
            DESCRIPTION
                "Port 1~8"
            ::= { dte8StatusEntry 2 }

        dte8RTSloss  OBJECT-TYPE
            SYNTAX  INTEGER {
                    no(1),
                    yes(2)
                }
            ACCESS  read-only
            STATUS  mandatory
            DESCRIPTION
                " DTE RTS status "
            ::= { dte8StatusEntry 3 }

        dte8RTS  OBJECT-TYPE
            SYNTAX  INTEGER {
                    active(1),
                    deactive(2),
                    na(3)
                }
            ACCESS  read-only
            STATUS  mandatory
            DESCRIPTION
                " DTE RTS status "
            ::= { dte8StatusEntry 4 }

        dte8CTS  OBJECT-TYPE
            SYNTAX  INTEGER {
                    active(1),
                    deactive(2),
                    na(3)
                }
            ACCESS  read-only
            STATUS  mandatory
            DESCRIPTION
                " DTE CTS status "
            ::= { dte8StatusEntry 5 }

        dte8DSR  OBJECT-TYPE
            SYNTAX  INTEGER {
                    active(1),
                    deactive(2),
                    na(3)
                }
            ACCESS  read-only
            STATUS  mandatory
            DESCRIPTION
                " DTE DSR status "
            ::= { dte8StatusEntry 6 }

        dte8DTR  OBJECT-TYPE
            SYNTAX  INTEGER {
                    active(1),
                    deactive(2),
                    na(3)
                }
            ACCESS  read-only
            STATUS  mandatory
            DESCRIPTION
                " DTE DTR status "
            ::= { dte8StatusEntry 7 }

        dte8RxBytesCounter  OBJECT-TYPE
            SYNTAX  Counter
            ACCESS  read-only
            STATUS  mandatory
            DESCRIPTION
                " DTE Rx bytes counter "
            ::= { dte8StatusEntry 8 }

        dte8TxBytesCounter  OBJECT-TYPE
            SYNTAX  Counter
            ACCESS  read-only
            STATUS  mandatory
            DESCRIPTION
                " DTE Tx bytes counter "
            ::= { dte8StatusEntry 9 }

        dte8ResetCounter  OBJECT-TYPE
            SYNTAX  INTEGER {
                    no(1),
                    reset(2)
                }
            ACCESS  read-write
            STATUS  mandatory
            DESCRIPTION
                "Reset DTE bytes counter"
            ::= { dte8StatusEntry 10 }

        dte8LOLC  OBJECT-TYPE
            SYNTAX  INTEGER {
                    no(1),
                    yes(2)
                }
            ACCESS  read-only
            STATUS  mandatory
            DESCRIPTION
                " DTE Loss Of Clock status "
            ::= { dte8StatusEntry 11 }

        dte8LOCH  OBJECT-TYPE
            SYNTAX  INTEGER {
                    no(1),
                    yes(2)
                }
            ACCESS  read-only
            STATUS  mandatory
            DESCRIPTION
                " DTE Loss Of Channel status "
            ::= { dte8StatusEntry 12 }

        dte8CRE  OBJECT-TYPE
            SYNTAX  INTEGER {
                    no(1),
                    yes(2)
                }
            ACCESS  read-only
            STATUS  mandatory
            DESCRIPTION
                " DTE Clock Recovery Error status "
            ::= { dte8StatusEntry 13 }

--
--  Mode Setup Table
--

        dte8ModeSetupTable  OBJECT-TYPE
            SYNTAX  SEQUENCE OF Dte8ModeSetupEntry
            ACCESS  not-accessible
            STATUS  mandatory
            DESCRIPTION
                "8UDTE Card Mode Setup table."
            ::= { octDte-card 10 }

        dte8ModeSetupEntry  OBJECT-TYPE
            SYNTAX  Dte8ModeSetupEntry
            ACCESS  not-accessible
            STATUS  mandatory
            DESCRIPTION
                "8UDTE Card Mode Setup entry."
            INDEX { dte8ModeSlotIndex }
            ::= { dte8ModeSetupTable 1 }

        Dte8ModeSetupEntry ::= SEQUENCE {
            dte8ModeSlotIndex           LSSlotID,
            dte8CardMode                INTEGER
        }

        dte8ModeSlotIndex  OBJECT-TYPE
            SYNTAX  LSSlotID
            ACCESS  read-only
            STATUS  mandatory
            DESCRIPTION
                "8UDTE slot index"
            ::= { dte8ModeSetupEntry 1 }

        dte8CardMode  OBJECT-TYPE
            SYNTAX  INTEGER {
                    oversampling(1),
                    terminalServer(2),
                    omnibus(3),
                    terminalServerAdvanced(5),
                    omnibusAdvanced(9),
                    oversamplingAdvanced(17),
                    throughclock(33)
                }
            ACCESS  read-write
            STATUS  mandatory
            DESCRIPTION
                "8UDTE Card Mode"
            ::= { dte8ModeSetupEntry 2 }


--
--  Omnibus Group Setup Table
--

        dte8OmnibusSetupTable  OBJECT-TYPE
            SYNTAX  SEQUENCE OF Dte8OmnibusSetupEntry
            ACCESS  not-accessible
            STATUS  mandatory
            DESCRIPTION
                "8UDTE Omnibus Group Setup table."
            ::= { octDte-card 11 }

        dte8OmnibusSetupEntry  OBJECT-TYPE
            SYNTAX  Dte8OmnibusSetupEntry
            ACCESS  not-accessible
            STATUS  mandatory
            DESCRIPTION
                "8UDTE Omnibus Group Setup entry."
            INDEX { dte8OmnibusSlotIndex ,
                    dte8OmnibusPortIndex }
            ::= { dte8OmnibusSetupTable 1 }

        Dte8OmnibusSetupEntry ::= SEQUENCE {
            dte8OmnibusSlotIndex        LSSlotID,
            dte8OmnibusPortIndex        PortID,
            dte8OmnibusGroup            INTEGER
        }

        dte8OmnibusSlotIndex  OBJECT-TYPE
            SYNTAX  LSSlotID
            ACCESS  read-only
            STATUS  mandatory
            DESCRIPTION
                "8UDTE slot index"
            ::= { dte8OmnibusSetupEntry 1 }

        dte8OmnibusPortIndex  OBJECT-TYPE
            SYNTAX  PortID
            ACCESS  read-only
            STATUS  mandatory
            DESCRIPTION
                "Port 1~8"
            ::= { dte8OmnibusSetupEntry 2 }

        dte8OmnibusGroup  OBJECT-TYPE
            SYNTAX  INTEGER {
                    group1(1),
                    group2(2),
                    group3(3),
                    group4(4),
                    group5(5),
                    group6(6),
                    group7(7),
                    group8(8)
                }
            ACCESS  read-write
            STATUS  mandatory
            DESCRIPTION
                "8UDTE Omnibus Group"
            ::= { dte8OmnibusSetupEntry 3 }


--
--  Terminal Server DTE Control Table
--

        dte8TsDteTable  OBJECT-TYPE
            SYNTAX  SEQUENCE OF Dte8TsDteEntry
            ACCESS  not-accessible
            STATUS  mandatory
            DESCRIPTION
                "8UDTE Terminal Server DTE Control Table"
            ::= { octDte-card 12 }

        dte8TsDteEntry  OBJECT-TYPE
            SYNTAX  Dte8TsDteEntry
            ACCESS  not-accessible
            STATUS  mandatory
            DESCRIPTION
                "8UDTE Terminal Server DTE Control entry."
            INDEX { dte8TsDteSlotIndex ,
                    dte8TsDtePortIndex }
            ::= { dte8TsDteTable 1 }

        Dte8TsDteEntry ::= SEQUENCE {
            dte8TsDteSlotIndex            LSSlotID,
            dte8TsDtePortIndex            PortID,
            dte8TsDteInterface            INTEGER,
            dte8TsDteFrame                INTEGER,
            dte8TsDteBaudRate             INTEGER,
            dte8TsDteDataBit              INTEGER,
            dte8TsDteStopBit              INTEGER,
            dte8TsDteParityBit            INTEGER,
            dte8TsDteSwFlowControl        INTEGER,
            dte8TsDteFlowControlTime      INTEGER,
            dte8TsDteBufferSize           INTEGER,
            dte8TsDteBufferTimeout        INTEGER,
            dte8TsDteDuplex               INTEGER,
            dte8TsDteIdleDetect           INTEGER
        }

        dte8TsDteSlotIndex  OBJECT-TYPE
            SYNTAX  LSSlotID
            ACCESS  read-only
            STATUS  mandatory
            DESCRIPTION
                "8UDTE slot index"
            ::= { dte8TsDteEntry 1 }

        dte8TsDtePortIndex  OBJECT-TYPE
            SYNTAX  PortID
            ACCESS  read-only
            STATUS  mandatory
            DESCRIPTION
                "Port 1~8"
            ::= { dte8TsDteEntry 2 }

        dte8TsDteInterface   OBJECT-TYPE
            SYNTAX  INTEGER {
                    rs232(1),
                    rs485(2),
                    rs422(3)
                }
            ACCESS  read-write
            STATUS  mandatory
            DESCRIPTION
                "8UDTE Terminal Server DTE Interface Type"
            ::= { dte8TsDteEntry 3 }

        dte8TsDteFrame   OBJECT-TYPE
            SYNTAX  INTEGER {
                    slip(1),
                    rawdata(2)
                }
            ACCESS  read-only
            STATUS  mandatory
            DESCRIPTION
                "8UDTE Terminal Server DTE Frame Type"
            ::= { dte8TsDteEntry 4 }

        dte8TsDteBaudRate   OBJECT-TYPE
            SYNTAX  INTEGER {
                    rate38400(1),
                    rate19200(2),
                    rate9600(3),
                    rate4800(4),
                    rate2400(5),
                    rate1200(6),
                    rate600(7)
                }
            ACCESS  read-write
            STATUS  mandatory
            DESCRIPTION
                "8UDTE Terminal Server DTE baud rate"
            ::= { dte8TsDteEntry 5 }

        dte8TsDteDataBit   OBJECT-TYPE
            SYNTAX  INTEGER {
                    data8bits(1),
                    data7bits(2),
                    data6bits(3),
                    data5bits(4)
                }
            ACCESS  read-write
            STATUS  mandatory
            DESCRIPTION
                "8UDTE Terminal Server DTE Data bit"
            ::= { dte8TsDteEntry 6 }

        dte8TsDteStopBit   OBJECT-TYPE
            SYNTAX  INTEGER {
                    stop1bit(1),
                    stop2bits(2),
                    stop1dot5bits(3)
                }
            ACCESS  read-write
            STATUS  mandatory
            DESCRIPTION
                "8UDTE Terminal Server DTE Stop bit"
            ::= { dte8TsDteEntry 7 }

        dte8TsDteParityBit   OBJECT-TYPE
            SYNTAX  INTEGER {
                    none(1),
                    even(2),
                    odd(3)
                }
            ACCESS  read-write
            STATUS  mandatory
            DESCRIPTION
                "8UDTE Terminal Server DTE Parity check"
            ::= { dte8TsDteEntry 8 }

        dte8TsDteSwFlowControl   OBJECT-TYPE
            SYNTAX  INTEGER {
                    disable(1),
                    enable(2)
                }
            ACCESS  read-write
            STATUS  mandatory
            DESCRIPTION
                "8UDTE Terminal Server DTE Software flow control"
            ::= { dte8TsDteEntry 9 }

        dte8TsDteFlowControlTime   OBJECT-TYPE
            SYNTAX  INTEGER (1..15)
            ACCESS  read-write
            STATUS  mandatory
            DESCRIPTION
                "8UDTE Terminal Server DTE flow control time"
            ::= { dte8TsDteEntry 10 }

        dte8TsDteBufferSize   OBJECT-TYPE
            SYNTAX  INTEGER (1..2048)
            ACCESS  read-write
            STATUS  mandatory
            DESCRIPTION
                "8UDTE Terminal Server DTE Buffer Size"
            ::= { dte8TsDteEntry 11 }

        dte8TsDteBufferTimeout   OBJECT-TYPE
            SYNTAX  INTEGER (1..255)
            ACCESS  read-write
            STATUS  mandatory
            DESCRIPTION
                "8UDTE Terminal Server DTE Buffer Timeout"
            ::= { dte8TsDteEntry 12 }

        dte8TsDteDuplex   OBJECT-TYPE
            SYNTAX  INTEGER {
                    full(1),
                    half(2)
                }
            ACCESS  read-write
            STATUS  mandatory
            DESCRIPTION
                "8UDTE Terminal Server DTE Duplex"
            ::= { dte8TsDteEntry 13 }

        dte8TsDteIdleDetect   OBJECT-TYPE
            SYNTAX  INTEGER (1..255)
            ACCESS  read-write
            STATUS  mandatory
            DESCRIPTION
                "8UDTE Terminal Server DTE Idle Detect"
            ::= { dte8TsDteEntry 14 }


--
--  Terminal Server DTE IP Control Table
--

        dte8TsDteIpTable  OBJECT-TYPE
            SYNTAX  SEQUENCE OF Dte8TsDteIpEntry
            ACCESS  not-accessible
            STATUS  mandatory
            DESCRIPTION
                "8UDTE Terminal Server DTE IP Control Table"
            ::= { octDte-card 13 }

        dte8TsDteIpEntry  OBJECT-TYPE
            SYNTAX  Dte8TsDteIpEntry
            ACCESS  not-accessible
            STATUS  mandatory
            DESCRIPTION
                "8UDTE Terminal Server DTE IP Control entry."
            INDEX { dte8TsDteIpSlotIndex ,
                    dte8TsDteIpPortIndex }
            ::= { dte8TsDteIpTable 1 }

        Dte8TsDteIpEntry ::= SEQUENCE {
            dte8TsDteIpSlotIndex            LSSlotID,
            dte8TsDteIpPortIndex            PortID,
            dte8TsDteIpRole                 INTEGER,
            dte8TsDteIpLocalIP              IpAddress,
            dte8TsDteIpSubnetMask           IpAddress,
            dte8TsDteIpDestinationIP1       IpAddress,
            dte8TsDteIpDestinationIP2       IpAddress,
            dte8TsDteIpDestinationIP3       IpAddress,
            dte8TsDteIpDestinationIP4       IpAddress,
            dte8TsDteIpDestinationIP5       IpAddress,
            dte8TsDteIpDestinationIP6       IpAddress,
            dte8TsDteIpDestinationIP7       IpAddress,
            dte8TsDteIpDestinationIP8       IpAddress
        }

        dte8TsDteIpSlotIndex  OBJECT-TYPE
            SYNTAX  LSSlotID
            ACCESS  read-only
            STATUS  mandatory
            DESCRIPTION
                "8UDTE slot index"
            ::= { dte8TsDteIpEntry 1 }

        dte8TsDteIpPortIndex  OBJECT-TYPE
            SYNTAX  PortID
            ACCESS  read-only
            STATUS  mandatory
            DESCRIPTION
                "Port 1~8"
            ::= { dte8TsDteIpEntry 2 }

        dte8TsDteIpRole   OBJECT-TYPE
            SYNTAX  INTEGER {
                    server(1),
                    client(2)
                }
            ACCESS  read-write
            STATUS  mandatory
            DESCRIPTION
                "8UDTE Terminal Server DTE IP Role"
            ::= { dte8TsDteIpEntry 3 }

        dte8TsDteIpLocalIP   OBJECT-TYPE
            SYNTAX  IpAddress
            ACCESS  read-write
            STATUS  mandatory
            DESCRIPTION
                "8UDTE Terminal Server DTE IP Local IP"
            ::= { dte8TsDteIpEntry 4 }

        dte8TsDteIpSubnetMask   OBJECT-TYPE
            SYNTAX  IpAddress
            ACCESS  read-write
            STATUS  mandatory
            DESCRIPTION
                "8UDTE Terminal Server DTE IP SubnetMask"
            ::= { dte8TsDteIpEntry 5 }

        dte8TsDteIpDestinationIP1   OBJECT-TYPE
            SYNTAX  IpAddress
            ACCESS  read-write
            STATUS  mandatory
            DESCRIPTION
                "8UDTE Terminal Server DTE IP Destination IP 1"
            ::= { dte8TsDteIpEntry 6 }

        dte8TsDteIpDestinationIP2   OBJECT-TYPE
            SYNTAX  IpAddress
            ACCESS  read-write
            STATUS  mandatory
            DESCRIPTION
                "8UDTE Terminal Server DTE IP Destination IP 2"
            ::= { dte8TsDteIpEntry 7 }

        dte8TsDteIpDestinationIP3   OBJECT-TYPE
            SYNTAX  IpAddress
            ACCESS  read-write
            STATUS  mandatory
            DESCRIPTION
                "8UDTE Terminal Server DTE IP Destination IP 3"
            ::= { dte8TsDteIpEntry 8 }

        dte8TsDteIpDestinationIP4   OBJECT-TYPE
            SYNTAX  IpAddress
            ACCESS  read-write
            STATUS  mandatory
            DESCRIPTION
                "8UDTE Terminal Server DTE IP Destination IP 4"
            ::= { dte8TsDteIpEntry 9 }

        dte8TsDteIpDestinationIP5   OBJECT-TYPE
            SYNTAX  IpAddress
            ACCESS  read-write
            STATUS  mandatory
            DESCRIPTION
                "8UDTE Terminal Server DTE IP Destination IP 5"
            ::= { dte8TsDteIpEntry 10 }

        dte8TsDteIpDestinationIP6   OBJECT-TYPE
            SYNTAX  IpAddress
            ACCESS  read-write
            STATUS  mandatory
            DESCRIPTION
                "8UDTE Terminal Server DTE IP Destination IP 6"
            ::= { dte8TsDteIpEntry 11 }

        dte8TsDteIpDestinationIP7   OBJECT-TYPE
            SYNTAX  IpAddress
            ACCESS  read-write
            STATUS  mandatory
            DESCRIPTION
                "8UDTE Terminal Server DTE IP Destination IP 7"
            ::= { dte8TsDteIpEntry 12 }

        dte8TsDteIpDestinationIP8   OBJECT-TYPE
            SYNTAX  IpAddress
            ACCESS  read-write
            STATUS  mandatory
            DESCRIPTION
                "8UDTE Terminal Server DTE IP Destination IP 8"
            ::= { dte8TsDteIpEntry 13 }


--
--  Terminal Server Router Wan Setup Table
--

        dte8TsWanTable  OBJECT-TYPE
            SYNTAX  SEQUENCE OF Dte8TsWanEntry
            ACCESS  not-accessible
            STATUS  mandatory
            DESCRIPTION
                "8UDTE Terminal Server Router Wan Setup table."
            ::= { octDte-card 14 }

        dte8TsWanEntry  OBJECT-TYPE
            SYNTAX  Dte8TsWanEntry
            ACCESS  not-accessible
            STATUS  mandatory
            DESCRIPTION
                "8UDTE Terminal Server Router Wan Setup entry."
            INDEX { dte8TsWanSlotIndex ,
                    dte8TsWanNI }
            ::= { dte8TsWanTable 1 }

        Dte8TsWanEntry ::= SEQUENCE {
            dte8TsWanSlotIndex      LSSlotID,
            dte8TsWanNI             INTEGER,
            dte8TsWanIPAddress      IpAddress,
            dte8TsWanSubnetMask     IpAddress,
            dte8TsWanFrame          INTEGER,
            dte8TsWanRip1           INTEGER,
            dte8TsWanRip2           INTEGER
        }

        dte8TsWanSlotIndex  OBJECT-TYPE
            SYNTAX  LSSlotID
            ACCESS  read-only
            STATUS  mandatory
            DESCRIPTION
                "8UDTE slot index"
            ::= { dte8TsWanEntry 1 }

        dte8TsWanNI  OBJECT-TYPE
            SYNTAX  INTEGER {
                    wan-1(1),
                    wan-2(2),
                    wan-3(3),
                    wan-4(4),
                    wan-5(5),
                    wan-6(6),
                    wan-7(7),
                    wan-8(8),
                    wan-9(9),
                    wan-10(10),
                    wan-11(11),
                    wan-12(12),
                    wan-13(13),
                    wan-14(14),
                    wan-15(15),
                    wan-16(16),
                    wan-17(17),
                    wan-18(18),
                    wan-19(19),
                    wan-20(20),
                    wan-21(21),
                    wan-22(22),
                    wan-23(23),
                    wan-24(24),
                    wan-25(25),
                    wan-26(26),
                    wan-27(27),
                    wan-28(28),
                    wan-29(29),
                    wan-30(30),
                    wan-31(31),
                    wan-32(32),
                    wan-33(33),
                    wan-34(34),
                    wan-35(35),
                    wan-36(36),
                    wan-37(37),
                    wan-38(38),
                    wan-39(39),
                    wan-40(40),
                    wan-41(41),
                    wan-42(42),
                    wan-43(43),
                    wan-44(44),
                    wan-45(45),
                    wan-46(46),
                    wan-47(47),
                    wan-48(48),
                    wan-49(49),
                    wan-50(50),
                    wan-51(51),
                    wan-52(52),
                    wan-53(53),
                    wan-54(54),
                    wan-55(55),
                    wan-56(56),
                    wan-57(57),
                    wan-58(58),
                    wan-59(59),
                    wan-60(60),
                    wan-61(61),
                    wan-62(62),
                    wan-63(63),
                    wan-64(64)
                }
            ACCESS  read-only
            STATUS  mandatory
            DESCRIPTION
                "8UDTE Terminal Server Router Wan Index"
            ::= { dte8TsWanEntry 2 }

        dte8TsWanIPAddress  OBJECT-TYPE
            SYNTAX  IpAddress
            ACCESS  read-write
            STATUS  mandatory
            DESCRIPTION
                "8UDTE Terminal Server Router Wan IpAddress"
            ::= { dte8TsWanEntry 3 }

        dte8TsWanSubnetMask  OBJECT-TYPE
            SYNTAX  IpAddress
            ACCESS  read-write
            STATUS  mandatory
            DESCRIPTION
                "8UDTE Terminal Server Router Wan Subnet Mask"
            ::= { dte8TsWanEntry 4 }

        dte8TsWanFrame  OBJECT-TYPE
            SYNTAX  INTEGER {
                    hdlc(1),
                    ppp(2)
                }
            ACCESS  read-write
            STATUS  mandatory
            DESCRIPTION
                "8UDTE Terminal Server Router Wan Frame"
            ::= { dte8TsWanEntry 5 }

        dte8TsWanRip1  OBJECT-TYPE
            SYNTAX  INTEGER {
                    disable(1),
                    enable(2)
                }
            ACCESS  read-write
            STATUS  mandatory
            DESCRIPTION
                "8UDTE Terminal Server Router Wan RIP_I"
            ::= { dte8TsWanEntry 6 }

        dte8TsWanRip2  OBJECT-TYPE
            SYNTAX  INTEGER {
                    disable(1),
                    enable(2)
                }
            ACCESS  read-write
            STATUS  mandatory
            DESCRIPTION
                "8UDTE Terminal Server Router Wan RIP_II"
            ::= { dte8TsWanEntry 7 }


--
--  Terminal Server Static Router Display Table
--

        dte8TsStRouteDispTable  OBJECT-TYPE
            SYNTAX  SEQUENCE OF Dte8TsStRouteDispEntry
            ACCESS  not-accessible
            STATUS  mandatory
            DESCRIPTION
                "8UDTE Terminal Server Static Router Display table."
            ::= { octDte-card 15 }

        dte8TsStRouteDispEntry  OBJECT-TYPE
            SYNTAX  Dte8TsStRouteDispEntry
            ACCESS  not-accessible
            STATUS  mandatory
            DESCRIPTION
                "8UDTE Terminal Server Static Router Display entry."
            INDEX { dte8TsStRouteDispSlotIndex ,
                    dte8TsStRouteDispIndex }
            ::= { dte8TsStRouteDispTable 1 }

        Dte8TsStRouteDispEntry ::= SEQUENCE {
            dte8TsStRouteDispSlotIndex        LSSlotID,
            dte8TsStRouteDispIndex            INTEGER,
            dte8TsStRouteDispNetAddress       IpAddress,
            dte8TsStRouteDispNetMask          IpAddress,
            dte8TsStRouteDispGatewayIP        IpAddress,
            dte8TsStRouteDispNIAddress        IpAddress,
            dte8TsStRouteDispMetric           INTEGER
        }

        dte8TsStRouteDispSlotIndex  OBJECT-TYPE
            SYNTAX  LSSlotID
            ACCESS  read-only
            STATUS  mandatory
            DESCRIPTION
                "8UDTE slot index"
            ::= { dte8TsStRouteDispEntry 1 }

        dte8TsStRouteDispIndex  OBJECT-TYPE
            SYNTAX  INTEGER (1..64)
            ACCESS  read-only
            STATUS  mandatory
            DESCRIPTION
                "8UDTE Terminal Server Static Router Display Index(1-64)"
            ::= { dte8TsStRouteDispEntry 2 }

        dte8TsStRouteDispNetAddress  OBJECT-TYPE
            SYNTAX  IpAddress
            ACCESS  read-only
            STATUS  mandatory
            DESCRIPTION
                "8UDTE Terminal Server Static Router Display Net Address"
            ::= { dte8TsStRouteDispEntry 3 }

        dte8TsStRouteDispNetMask  OBJECT-TYPE
            SYNTAX  IpAddress
            ACCESS  read-only
            STATUS  mandatory
            DESCRIPTION
                "8UDTE Terminal Server Static Router Display Net Mask"
            ::= { dte8TsStRouteDispEntry 4 }

        dte8TsStRouteDispGatewayIP  OBJECT-TYPE
            SYNTAX  IpAddress
            ACCESS  read-only
            STATUS  mandatory
            DESCRIPTION
                "8UDTE Terminal Server Static Router Display Gateway Address"
            ::= { dte8TsStRouteDispEntry 5 }

        dte8TsStRouteDispNIAddress  OBJECT-TYPE
            SYNTAX  IpAddress
            ACCESS  read-only
            STATUS  mandatory
            DESCRIPTION
                "8UDTE Terminal Server Static Router Display NI Address"
            ::= { dte8TsStRouteDispEntry 6 }

        dte8TsStRouteDispMetric  OBJECT-TYPE
            SYNTAX  INTEGER (1..16)
            ACCESS  read-only
            STATUS  mandatory
            DESCRIPTION
                "8UDTE Terminal Server Static Router Display Metric"
            ::= { dte8TsStRouteDispEntry 7 }


--
--  Terminal Server Static Router Add Delete Table
--

        dte8TsStRouteAddDelTable  OBJECT-TYPE
            SYNTAX  SEQUENCE OF Dte8TsStRouteAddDelEntry
            ACCESS  not-accessible
            STATUS  mandatory
            DESCRIPTION
                "8UDTE Terminal Server Static Router Add Delete table."
            ::= { octDte-card 16 }

        dte8TsStRouteAddDelEntry  OBJECT-TYPE
            SYNTAX  Dte8TsStRouteAddDelEntry
            ACCESS  not-accessible
            STATUS  mandatory
            DESCRIPTION
                "8UDTE Terminal Server Static Router Add Delete entry."
            INDEX { dte8TsStRouteAddDelSlotIndex }
            ::= { dte8TsStRouteAddDelTable 1 }

        Dte8TsStRouteAddDelEntry ::= SEQUENCE {
            dte8TsStRouteAddDelSlotIndex       LSSlotID,
            dte8TsStRouteAddDelNetAddress      IpAddress,
            dte8TsStRouteAddDelNetMask         IpAddress,
            dte8TsStRouteAddDelGatewayIP       IpAddress,
            dte8TsStRouteAddDelNIAddress       IpAddress,
            dte8TsStRouteAddDelMetric          INTEGER,
            dte8TsStRouteAddDelCmd             INTEGER
        }

        dte8TsStRouteAddDelSlotIndex  OBJECT-TYPE
            SYNTAX  LSSlotID
            ACCESS  read-only
            STATUS  mandatory
            DESCRIPTION
                "8UDTE slot index"
            ::= { dte8TsStRouteAddDelEntry 1 }

        dte8TsStRouteAddDelNetAddress  OBJECT-TYPE
            SYNTAX  IpAddress
            ACCESS  read-write
            STATUS  mandatory
            DESCRIPTION
                "8UDTE Terminal Server Static Router Add Delete Net Address"
            ::= { dte8TsStRouteAddDelEntry 2 }

        dte8TsStRouteAddDelNetMask  OBJECT-TYPE
            SYNTAX  IpAddress
            ACCESS  read-write
            STATUS  mandatory
            DESCRIPTION
                "8UDTE Terminal Server Static Router Add Delete Net Mask"
            ::= { dte8TsStRouteAddDelEntry 3 }

        dte8TsStRouteAddDelGatewayIP  OBJECT-TYPE
            SYNTAX  IpAddress
            ACCESS  read-write
            STATUS  mandatory
            DESCRIPTION
                "8UDTE Terminal Server Static Router Add Delete Gateway Address"
            ::= { dte8TsStRouteAddDelEntry 4 }

        dte8TsStRouteAddDelNIAddress  OBJECT-TYPE
            SYNTAX  IpAddress
            ACCESS  read-write
            STATUS  mandatory
            DESCRIPTION
                "8UDTE Terminal Server Static Router Add Delete NI Address"
            ::= { dte8TsStRouteAddDelEntry 5 }

        dte8TsStRouteAddDelMetric  OBJECT-TYPE
            SYNTAX  INTEGER (1..16)
            ACCESS  read-write
            STATUS  mandatory
            DESCRIPTION
                "8UDTE Terminal Server Static Router Add Delete Metric"
            ::= { dte8TsStRouteAddDelEntry 6 }

        dte8TsStRouteAddDelCmd  OBJECT-TYPE
            SYNTAX  INTEGER {
                    noAction(1),
                    add(2),
                    delete(3)
                }
            ACCESS  read-write
            STATUS  mandatory
            DESCRIPTION
                "8UDTE Terminal Server Static Router Add Delete Command"
            ::= { dte8TsStRouteAddDelEntry 7 }


--
--  Terminal Server Map Setup Table
--

        dte8TsMapTable  OBJECT-TYPE
            SYNTAX  SEQUENCE OF Dte8TsMapEntry
            ACCESS  not-accessible
            STATUS  mandatory
            DESCRIPTION
                "8UDTE Terminal Server Map Setup table."
            ::= { octDte-card 17 }

        dte8TsMapEntry  OBJECT-TYPE
            SYNTAX  Dte8TsMapEntry
            ACCESS  not-accessible
            STATUS  mandatory
            DESCRIPTION
                "8UDTE Terminal Server Map Setup entry."
            INDEX { dte8TsMapSlotIndex ,
                    dte8TsMapVirtualPort ,
                    dte8TsMapTSIndex }
            ::= { dte8TsMapTable 1 }

        Dte8TsMapEntry ::= SEQUENCE {
            dte8TsMapSlotIndex        LSSlotID,
            dte8TsMapVirtualPort      INTEGER,
            dte8TsMapTSIndex          TimeslotID,
            dte8TsMapOption           INTEGER
        }

        dte8TsMapSlotIndex  OBJECT-TYPE
            SYNTAX  LSSlotID
            ACCESS  read-only
            STATUS  mandatory
            DESCRIPTION
                "8UDTE slot index"
            ::= { dte8TsMapEntry 1 }

        dte8TsMapVirtualPort  OBJECT-TYPE
            SYNTAX  INTEGER {
                    virtualPort1(1),
                    virtualPort2(2)
                }
            ACCESS  read-only
            STATUS  mandatory
            DESCRIPTION
                "8UDTE Terminal Server Map Virtual Port"
            ::= { dte8TsMapEntry 2 }

        dte8TsMapTSIndex  OBJECT-TYPE
            SYNTAX  TimeslotID
            ACCESS  read-only
            STATUS  mandatory
            DESCRIPTION
                "8UDTE Terminal Server Map Time Slot"
            ::= { dte8TsMapEntry 3 }

        dte8TsMapOption  OBJECT-TYPE
            SYNTAX  INTEGER {
                    idle(1),
                    wan1(2),
                    wan2(3),
                    wan3(4),
                    wan4(5),
                    wan5(6),
                    wan6(7),
                    wan7(8),
                    wan8(9),
                    wan9(10),
                    wan10(11),
                    wan11(12),
                    wan12(13),
                    wan13(14),
                    wan14(15),
                    wan15(16),
                    wan16(17),
                    wan17(18),
                    wan18(19),
                    wan19(20),
                    wan20(21),
                    wan21(22),
                    wan22(23),
                    wan23(24),
                    wan24(25),
                    wan25(26),
                    wan26(27),
                    wan27(28),
                    wan28(29),
                    wan29(30),
                    wan30(31),
                    wan31(32),
                    wan32(33),
                    wan33(34),
                    wan34(35),
                    wan35(36),
                    wan36(37),
                    wan37(38),
                    wan38(39),
                    wan39(40),
                    wan40(41),
                    wan41(42),
                    wan42(43),
                    wan43(44),
                    wan44(45),
                    wan45(46),
                    wan46(47),
                    wan47(48),
                    wan48(49),
                    wan49(50),
                    wan50(51),
                    wan51(52),
                    wan52(53),
                    wan53(54),
                    wan54(55),
                    wan55(56),
                    wan56(57),
                    wan57(58),
                    wan58(59),
                    wan59(60),
                    wan60(61),
                    wan61(62),
                    wan62(63),
                    wan63(64),
                    wan64(65)
                }
            ACCESS  read-write
            STATUS  mandatory
            DESCRIPTION
                "8UDTE Terminal Server Map Option"
            ::= { dte8TsMapEntry 4 }


--
--  Omnibus DTE Control Table
--

        dte8OmDteTable  OBJECT-TYPE
            SYNTAX  SEQUENCE OF Dte8OmDteEntry
            ACCESS  not-accessible
            STATUS  mandatory
            DESCRIPTION
                "8UDTE Omnibus DTE Setup Table"
            ::= { octDte-card 21 }

        dte8OmDteEntry  OBJECT-TYPE
            SYNTAX  Dte8OmDteEntry
            ACCESS  not-accessible
            STATUS  mandatory
            DESCRIPTION
                "8UDTE Omnibus DTE Setup entry."
            INDEX { dte8OmDteSlotIndex ,
                    dte8OmDtePortIndex }
            ::= { dte8OmDteTable 1 }

        Dte8OmDteEntry ::= SEQUENCE {
            dte8OmDteSlotIndex         LSSlotID,
            dte8OmDtePortIndex         PortID,
            dte8OmDteInterface         INTEGER,
            dte8OmDteDataID            INTEGER,
            dte8OmDteBaudRate          INTEGER,
            dte8OmDteDataBit           INTEGER,
            dte8OmDteStopBit           INTEGER,
            dte8OmDteParityBit         INTEGER,
            dte8OmDteRole              INTEGER,
            dte8OmDteHwFlowControl     INTEGER,
            dte8OmDteONTimer           INTEGER,
            dte8OmDteOFFTimer          INTEGER,
            dte8OmDteBufferSize        INTEGER,
            dte8OmDteBufferTimeout     INTEGER,
            dte8OmDteDuplex            INTEGER,
            dte8OmDteIdleDetect        INTEGER
        }

        dte8OmDteSlotIndex  OBJECT-TYPE
            SYNTAX  LSSlotID
            ACCESS  read-only
            STATUS  mandatory
            DESCRIPTION
                "8UDTE slot index"
            ::= { dte8OmDteEntry 1 }

        dte8OmDtePortIndex  OBJECT-TYPE
            SYNTAX  PortID
            ACCESS  read-only
            STATUS  mandatory
            DESCRIPTION
                "Port 1~8"
            ::= { dte8OmDteEntry 2 }

        dte8OmDteInterface   OBJECT-TYPE
            SYNTAX  INTEGER {
                    rs232(1),
                    rs485(2),
                    rs422(3)
                }
            ACCESS  read-write
            STATUS  mandatory
            DESCRIPTION
                "8UDTE Omnibus DTE Interface Type"
            ::= { dte8OmDteEntry 3 }

        dte8OmDteDataID   OBJECT-TYPE
            SYNTAX  INTEGER (1..8)
            ACCESS  read-write
            STATUS  mandatory
            DESCRIPTION
                "8UDTE Omnibus DTE Data ID"
            ::= { dte8OmDteEntry 4 }

        dte8OmDteBaudRate   OBJECT-TYPE
            SYNTAX  INTEGER {
                    rate38400(1),
                    rate19200(2),
                    rate9600(3),
                    rate4800(4),
                    rate2400(5),
                    rate1200(6),
                    rate600(7)
                }
            ACCESS  read-write
            STATUS  mandatory
            DESCRIPTION
                "8UDTE Omnibus DTE baud rate"
            ::= { dte8OmDteEntry 5 }

        dte8OmDteDataBit   OBJECT-TYPE
            SYNTAX  INTEGER {
                    data8bits(1),
                    data7bits(2),
                    data6bits(3),
                    data5bits(4)
                }
            ACCESS  read-write
            STATUS  mandatory
            DESCRIPTION
                "8UDTE Omnibus DTE Data Bit"
            ::= { dte8OmDteEntry 6 }

        dte8OmDteStopBit   OBJECT-TYPE
            SYNTAX  INTEGER {
                    stop1bit(1),
                    stop2bits(2),
                    stop1dot5bits(3)
                }
            ACCESS  read-write
            STATUS  mandatory
            DESCRIPTION
                "8UDTE Omnibus DTE Stop Bit"
            ::= { dte8OmDteEntry 7 }

        dte8OmDteParityBit   OBJECT-TYPE
            SYNTAX  INTEGER {
                    none(1),
                    even(2),
                    odd(3)
                }
            ACCESS  read-write
            STATUS  mandatory
            DESCRIPTION
                "8UDTE Omnibus DTE Parity check"
            ::= { dte8OmDteEntry 8 }

        dte8OmDteRole   OBJECT-TYPE
            SYNTAX  INTEGER {
                    slave(1),
                    master(2)
                }
            ACCESS  read-write
            STATUS  mandatory
            DESCRIPTION
                "8UDTE Omnibus DTE Role"
            ::= { dte8OmDteEntry 9 }

        dte8OmDteHwFlowControl   OBJECT-TYPE
            SYNTAX  INTEGER {
                    disable(1),
                    enable(2)
                }
            ACCESS  read-write
            STATUS  mandatory
            DESCRIPTION
                "8UDTE Omnibus DTE Hardware flow control"
            ::= { dte8OmDteEntry 10 }

        dte8OmDteONTimer   OBJECT-TYPE
            SYNTAX  INTEGER (0..60)
            ACCESS  read-write
            STATUS  mandatory
            DESCRIPTION
                "8UDTE Omnibus DTE ON Timer"
            ::= { dte8OmDteEntry 11 }

        dte8OmDteOFFTimer   OBJECT-TYPE
            SYNTAX  INTEGER (0..60)
            ACCESS  read-write
            STATUS  mandatory
            DESCRIPTION
                "8UDTE Omnibus DTE OFF Timer"
            ::= { dte8OmDteEntry 12 }

        dte8OmDteBufferSize   OBJECT-TYPE
            SYNTAX  INTEGER (1..2048)
            ACCESS  read-write
            STATUS  mandatory
            DESCRIPTION
                "8UDTE Omnibus DTE Buffer Size"
            ::= { dte8OmDteEntry 13 }

        dte8OmDteBufferTimeout   OBJECT-TYPE
            SYNTAX  INTEGER (1..255)
            ACCESS  read-write
            STATUS  mandatory
            DESCRIPTION
                "8UDTE Omnibus DTE Buffer Timeout"
            ::= { dte8OmDteEntry 14 }

        dte8OmDteDuplex   OBJECT-TYPE
            SYNTAX  INTEGER {
                    full(1),
                    half(2)
                }
            ACCESS  read-write
            STATUS  mandatory
            DESCRIPTION
                "8UDTE Omnibus DTE Duplex"
            ::= { dte8OmDteEntry 15 }

        dte8OmDteIdleDetect   OBJECT-TYPE
            SYNTAX  INTEGER (1..255)
            ACCESS  read-write
            STATUS  mandatory
            DESCRIPTION
                "8UDTE Omnibus DTE Idle Detect"
            ::= { dte8OmDteEntry 16 }
--
--  Omnibus Map Table
--

        dte8OmMapTable  OBJECT-TYPE
            SYNTAX  SEQUENCE OF Dte8OmMapEntry
            ACCESS  not-accessible
            STATUS  mandatory
            DESCRIPTION
                "8UDTE Omnibus Map table."
            ::= { octDte-card 22 }

        dte8OmMapEntry  OBJECT-TYPE
            SYNTAX  Dte8OmMapEntry
            ACCESS  not-accessible
            STATUS  mandatory
            DESCRIPTION
                "8UDTE Omnibus Map entry."
            INDEX { dte8OmMapSlotIndex ,
                    dte8OmMapVirtualPort ,
                    dte8OmMapTSIndex }
            ::= { dte8OmMapTable 1 }

        Dte8OmMapEntry ::= SEQUENCE {
            dte8OmMapSlotIndex         LSSlotID,
            dte8OmMapVirtualPort       INTEGER,
            dte8OmMapTSIndex           TimeslotID,
            dte8OmMapOption            INTEGER
        }

        dte8OmMapSlotIndex  OBJECT-TYPE
            SYNTAX  LSSlotID
            ACCESS  read-only
            STATUS  mandatory
            DESCRIPTION
                "8UDTE slot index"
            ::= { dte8OmMapEntry 1 }

        dte8OmMapVirtualPort  OBJECT-TYPE
            SYNTAX  INTEGER {
                    virtualPort1(1),
                    virtualPort2(2)
                }
            ACCESS  read-only
            STATUS  mandatory
            DESCRIPTION
                "8UDTE Omnibus Map Virtual Port"
            ::= { dte8OmMapEntry 2 }

        dte8OmMapTSIndex  OBJECT-TYPE
            SYNTAX  TimeslotID
            ACCESS  read-only
            STATUS  mandatory
            DESCRIPTION
                "8UDTE Omnibus Map Time Slot"
            ::= { dte8OmMapEntry 3 }

        dte8OmMapOption  OBJECT-TYPE
            SYNTAX  INTEGER {
                    idle(1),
                    bg1west(2),
                    bg2west(3),
                    bg3west(4),
                    bg4west(5),
                    bg5west(6),
                    bg6west(7),
                    bg7west(8),
                    bg8west(9),
                    bg1east(10),
                    bg2east(11),
                    bg3east(12),
                    bg4east(13),
                    bg5east(14),
                    bg6east(15),
                    bg7east(16),
                    bg8east(17)
                }
            ACCESS  read-write
            STATUS  mandatory
            DESCRIPTION
                "8UDTE Omnibus Map Option"
            ::= { dte8OmMapEntry 4 }


--
--      Oversampling advanced DTE Control Table
--

        dte8OvaConfigCtrlTable  OBJECT-TYPE
            SYNTAX  SEQUENCE OF Dte8OvaConfigCtrlEntry
            ACCESS  not-accessible
            STATUS  mandatory
            DESCRIPTION
                "8UDTE Oversampling Advanced Configuration Control Table"
            ::= { octDte-card 30 }

        dte8OvaConfigCtrlEntry  OBJECT-TYPE
            SYNTAX  Dte8OvaConfigCtrlEntry
            ACCESS  not-accessible
            STATUS  mandatory
            DESCRIPTION
                "8UDTE Oversampling Advanced configuration control entry"
            INDEX { dte8OvaccSlotIndex , dte8OvaccPortIndex }
            ::= { dte8OvaConfigCtrlTable 1 }

        Dte8OvaConfigCtrlEntry ::= SEQUENCE {
            dte8OvaccSlotIndex             LSSlotID,
            dte8OvaccPortIndex             PortID,
            dte8OvaInterface               INTEGER,
            dte8OvaDS0Rate                 INTEGER,
            dte8OvaOversampling            INTEGER,
            dte8OvaOversamplingRate        INTEGER,
            dte8OvaSupportDataRate         DisplayString,
            dte8OvaDteBaudRate             INTEGER,
            dte8OvaDteDataBit              INTEGER,
            dte8OvaDteStopBit              INTEGER,
            dte8OvaDteParityBit            INTEGER,
            dte8OvaDteDuplex               INTEGER,
            dte8OvaDteIdleDetect           INTEGER,
            dte8OvaRTSCTS                  INTEGER,
            dte8OvaDTRDSR                  INTEGER
        }

        dte8OvaccSlotIndex  OBJECT-TYPE
            SYNTAX  LSSlotID
            ACCESS  read-only
            STATUS  mandatory
            DESCRIPTION
                "8UDTE slot index"
            ::= { dte8OvaConfigCtrlEntry 1 }

        dte8OvaccPortIndex  OBJECT-TYPE
            SYNTAX  PortID
            ACCESS  read-only
            STATUS  mandatory
            DESCRIPTION
                "Port 1~8"
            ::= { dte8OvaConfigCtrlEntry 2 }

        dte8OvaInterface   OBJECT-TYPE
            SYNTAX  INTEGER {
                    rs232(1),
                    rs485(2),
                    rs422(3)
                }
            ACCESS  read-write
            STATUS  mandatory
            DESCRIPTION
                "8UDTE Oversampling Advanced Interface Type"
            ::= { dte8OvaConfigCtrlEntry 3 }

        dte8OvaDS0Rate   OBJECT-TYPE
            SYNTAX  INTEGER {
                    rate64k(1),
                    rate56k(2)
                }
            ACCESS  read-write
            STATUS  mandatory
            DESCRIPTION
                "8UDTE Oversampling Advanced DS0 Sampling Rate"
            ::= { dte8OvaConfigCtrlEntry 4 }

        dte8OvaOversampling   OBJECT-TYPE
            SYNTAX  INTEGER (1..6)
            ACCESS  read-write
            STATUS  mandatory
            DESCRIPTION
                "8UDTE Oversampling Advanced oversampling numver"
            ::= { dte8OvaConfigCtrlEntry 5 }

        dte8OvaOversamplingRate   OBJECT-TYPE
            SYNTAX  INTEGER
            ACCESS  read-only
            STATUS  mandatory
            DESCRIPTION
                "8UDTE Oversampling Advanced Oversampling Rate (Kbps)"
            ::= { dte8OvaConfigCtrlEntry 6 }

        dte8OvaSupportDataRate   OBJECT-TYPE
            SYNTAX  DisplayString
            ACCESS  read-only
            STATUS  mandatory
            DESCRIPTION
                "8UDTE Oversampling Advanced Supported Data Rate"
            ::= { dte8OvaConfigCtrlEntry 7 }

        dte8OvaDteBaudRate   OBJECT-TYPE
            SYNTAX  INTEGER {
                    rate110(1),
                    rate150(2),
                    rate200(3),
                    rate300(4),
                    rate600(5),
                    rate1200(6),
                    rate2400(7),
                    rate4800(8),
                    rate9600(9),
                    rate19200(10),
                    rate28800(11),
                    rate38400(12),
                    rate57600(13),
                    rate115200(14),
                    rate128000(15),
                    rate230400(16)
                }
            ACCESS  read-write
            STATUS  mandatory
            DESCRIPTION
                "8UDTE Oversampling Advanced DTE baud rate"
            ::= { dte8OvaConfigCtrlEntry 8 }

        dte8OvaDteDataBit   OBJECT-TYPE
            SYNTAX  INTEGER {
                    data8bits(1),
                    data7bits(2),
                    data6bits(3),
                    data5bits(4)
                }
            ACCESS  read-write
            STATUS  mandatory
            DESCRIPTION
                "8UDTE Oversampling Advanced DTE Data bit"
            ::= { dte8OvaConfigCtrlEntry 9 }

        dte8OvaDteStopBit   OBJECT-TYPE
            SYNTAX  INTEGER {
                    stop1bit(1),
                    stop2bits(2)
                }
            ACCESS  read-write
            STATUS  mandatory
            DESCRIPTION
                "8UDTEOversampling Advanced  DTE Stop bit"
            ::= { dte8OvaConfigCtrlEntry 10 }

        dte8OvaDteParityBit   OBJECT-TYPE
            SYNTAX  INTEGER {
                    none(1),
                    even(2),
                    odd(3)
                }
            ACCESS  read-write
            STATUS  mandatory
            DESCRIPTION
                "8UDTE Oversampling Advanced DTE Parity check"
            ::= { dte8OvaConfigCtrlEntry 11 }

        dte8OvaDteDuplex   OBJECT-TYPE
            SYNTAX  INTEGER {
                    full(1),
                    half(2)
                }
            ACCESS  read-write
            STATUS  mandatory
            DESCRIPTION
                "8UDTE Oversampling Advanced DTE Duplex"
            ::= { dte8OvaConfigCtrlEntry 12 }

        dte8OvaDteIdleDetect   OBJECT-TYPE
            SYNTAX  INTEGER (1..255)
            ACCESS  read-write
            STATUS  mandatory
            DESCRIPTION
                "8UDTE Oversampling Advanced DTE Idle Detect"
            ::= { dte8OvaConfigCtrlEntry 13 }


        dte8OvaRTSCTS   OBJECT-TYPE
            SYNTAX  INTEGER {
                    active(1),
                    permanent(2),
                    na(3)
                }
            ACCESS  read-write
            STATUS  mandatory
            DESCRIPTION
                "8UDTE Oversampling Advanced RTS/CTS control"
            ::= { dte8OvaConfigCtrlEntry 14 }

        dte8OvaDTRDSR   OBJECT-TYPE
            SYNTAX  INTEGER {
                    active(1),
                    permanent(2),
                    na(3)
                }
            ACCESS  read-write
            STATUS  mandatory
            DESCRIPTION
                "8UDTE Oversampling Advanced DTR/DSR control"
            ::= { dte8OvaConfigCtrlEntry 15 }

--
--      Through Clock DTE Control Table
--

        dte8ThrConfigCtrlTable  OBJECT-TYPE
            SYNTAX  SEQUENCE OF Dte8ThrConfigCtrlEntry
            ACCESS  not-accessible
            STATUS  mandatory
            DESCRIPTION
                "8UDTE Through Clock Configuration Control Table"
            ::= { octDte-card 50 }

        dte8ThrConfigCtrlEntry  OBJECT-TYPE
            SYNTAX  Dte8ThrConfigCtrlEntry
            ACCESS  not-accessible
            STATUS  mandatory
            DESCRIPTION
                "8UDTE Through Clock configuration control entry"
            INDEX { dte8ThrccSlotIndex , dte8ThrccPortIndex }
            ::= { dte8ThrConfigCtrlTable 1 }

        Dte8ThrConfigCtrlEntry ::= SEQUENCE {
            dte8ThrccSlotIndex             LSSlotID,
            dte8ThrccPortIndex             PortID,
            dte8ThrInterface               INTEGER,
            dte8ThrBaudRate                INTEGER,
            dte8ThrClkInputInverse         INTEGER,
            dte8ThrClkOutputInverse        INTEGER,
            dte8ThrPCMDataInverse          INTEGER
        }

        dte8ThrccSlotIndex  OBJECT-TYPE
            SYNTAX  LSSlotID
            ACCESS  read-only
            STATUS  mandatory
            DESCRIPTION
                "8UDTE slot index"
            ::= { dte8ThrConfigCtrlEntry 1 }

        dte8ThrccPortIndex  OBJECT-TYPE
            SYNTAX  PortID
            ACCESS  read-only
            STATUS  mandatory
            DESCRIPTION
                "Port 1~8"
            ::= { dte8ThrConfigCtrlEntry 2 }

        dte8ThrInterface   OBJECT-TYPE
            SYNTAX  INTEGER {
                    rs232(1)
--                    rs485(2),
--                    rs422(3)
                }
            ACCESS  read-only
            STATUS  mandatory
            DESCRIPTION
                "8UDTE Through Clock Interface Type"
            ::= { dte8ThrConfigCtrlEntry 3 }

        dte8ThrBaudRate   OBJECT-TYPE
            SYNTAX  INTEGER (1..38400)
            ACCESS  read-write
            STATUS  mandatory
            DESCRIPTION
                "8UDTE Through Clock baud rate"
            ::= { dte8ThrConfigCtrlEntry 4 }

        dte8ThrClkInputInverse   OBJECT-TYPE
            SYNTAX  INTEGER {
                    off(1),
                    on(2)
                }
            ACCESS  read-write
            STATUS  mandatory
            DESCRIPTION
                "8UDTE Through Clock clock input inverse"
            ::= { dte8ThrConfigCtrlEntry 5 }

        dte8ThrClkOutputInverse   OBJECT-TYPE
            SYNTAX  INTEGER {
                    off(1),
                    on(2)
                }
            ACCESS  read-write
            STATUS  mandatory
            DESCRIPTION
                "8UDTE Through Clock clock output inverse"
            ::= { dte8ThrConfigCtrlEntry 6 }

        dte8ThrPCMDataInverse   OBJECT-TYPE
            SYNTAX  INTEGER {
                    off(1),
                    on(2)
                }
            ACCESS  read-write
            STATUS  mandatory
            DESCRIPTION
                "8UDTE Through Clock PCM data inverse"
            ::= { dte8ThrConfigCtrlEntry 7 }

        dte8TotalCard   OBJECT-TYPE
            SYNTAX  INTEGER
            ACCESS  read-only
            STATUS  mandatory
            DESCRIPTION
                "Total cards of 8UDTE"
            ::= { octDte-card 100 }


--======================================================================--
--======================================================================--
--  rs232a-card MIB
--======================================================================--
--======================================================================--

--
--  RS232A Configuration
--

        rs232aConfigTable  OBJECT-TYPE
            SYNTAX  SEQUENCE OF Rs232aConfigEntry
            ACCESS  not-accessible
            STATUS  mandatory
            DESCRIPTION
                "The RS232A Interface Configuration table."
            ::= { rs232a-card 1 }

        rs232aConfigEntry  OBJECT-TYPE
            SYNTAX  Rs232aConfigEntry
            ACCESS  not-accessible
            STATUS  mandatory
            DESCRIPTION
                "An entry in the RS232A Configuration table."
            INDEX { rsCfgSlotIndex , rsCfgPortIndex }
            ::= { rs232aConfigTable 1 }

        Rs232aConfigEntry ::= SEQUENCE {
            rsCfgSlotIndex                LSSlotID,
            rsCfgPortIndex                SixPortID,
            rsCfgMux                      INTEGER,
            rsCfgSyncMode                 INTEGER,
            rsCfgRate                     INTEGER,
            rsCfgBitPosition              INTEGER,
            rsCfgClockPolarity            INTEGER,
            rsCfgDataPolarity             INTEGER,
            rsCfgRTS                      INTEGER,
            rsCfgTTM                      INTEGER,
            rsCfgInterface                INTEGER,
            rsCfgBitPosition0Used         INTEGER,
            rsCfgBitPosition1Used         INTEGER,
            rsCfgBitPosition2Used         INTEGER,
            rsCfgBitPosition3Used         INTEGER,
            rsCfgBitPosition4Used         INTEGER,
            rsCfgBitPosition5Used         INTEGER,
            rsCfgBitPosition6Used         INTEGER,
            rsCfgBitPosition7Used         INTEGER,
            rsCfgWarrning                 DisplayString
        }

        rsCfgSlotIndex  OBJECT-TYPE
            SYNTAX  LSSlotID
            ACCESS  read-only
            STATUS  mandatory
            DESCRIPTION
                "RS232A slot index"
            ::= { rs232aConfigEntry 1 }

        rsCfgPortIndex  OBJECT-TYPE
            SYNTAX  SixPortID
            ACCESS  read-only
            STATUS  mandatory
            DESCRIPTION
                "Port 1 to 6, Total 6 ports"
            ::= { rs232aConfigEntry 2 }

        rsCfgMux  OBJECT-TYPE
            SYNTAX  INTEGER {
                    nonMux(1),
                    mux(2)
                }
            ACCESS  read-write
            STATUS  mandatory
            DESCRIPTION
                "RS232A MUX mode"
            ::= { rs232aConfigEntry 3 }


        rsCfgSyncMode  OBJECT-TYPE
            SYNTAX  INTEGER {
                    async8(1),
                    async9(2),
                    async10(3),
                    async11(4),
                    async12(5),
                    sync(6)
                }
            ACCESS  read-write
            STATUS  mandatory
            DESCRIPTION
                "RS232A Sync mode"
            ::= { rs232aConfigEntry 4 }

        rsCfgRate  OBJECT-TYPE
            SYNTAX  INTEGER {
                    r0-6K(1),
                    r1-2K(2),
                    r2-4K(3),
                    r4-8K(4),
                    r9-6K(5),
                    r19-2K(6),
                    r38-4K(7),
                    r48K(8),
                    r64K(9)
                }
            ACCESS  read-write
            STATUS  mandatory
            DESCRIPTION
                "RS232A Base Rate"
            ::= { rs232aConfigEntry 5 }

        rsCfgBitPosition  OBJECT-TYPE
            SYNTAX  INTEGER {
                    position-0(1),
                    position-1(2),
                    position-2(3),
                    position-3(4),
                    position-4(5),
                    position-5(6),
                    position-6(7),
                    position-7(8)
                }
            ACCESS  read-write
            STATUS  mandatory
            DESCRIPTION
                "RS232A Bit position"
            ::= { rs232aConfigEntry 6 }

        rsCfgClockPolarity  OBJECT-TYPE
            SYNTAX  INTEGER {
                    clockNormal(1),
                    clockInverted(2),
                    na(3)
                }
            ACCESS  read-write
            STATUS  mandatory
            DESCRIPTION
                "RS232A Clock Polarity"
            ::= { rs232aConfigEntry 7 }

        rsCfgDataPolarity  OBJECT-TYPE
            SYNTAX  INTEGER {
                    dataNormal(1),
                    dataInverted(2),
                    na(3)
                }
            ACCESS  read-write
            STATUS  mandatory
            DESCRIPTION
                "RS232A Data Polarity"
            ::= { rs232aConfigEntry 8 }

        rsCfgRTS  OBJECT-TYPE
            SYNTAX  INTEGER {
                    rtsActive(1),
                    rtsPermanent(2)
                }
            ACCESS  read-write
            STATUS  mandatory
            DESCRIPTION
                "RS232A RTS Mode"
            ::= {  rs232aConfigEntry 9 }

        rsCfgTTM  OBJECT-TYPE
            SYNTAX  INTEGER {
                    ttmOff(1),
                    ttmOn(2),
                    na(3)
                }
            ACCESS  read-write
            STATUS  mandatory
            DESCRIPTION
                "RS232A TTM Mode"
            ::= { rs232aConfigEntry 10 }

        rsCfgInterface  OBJECT-TYPE
            SYNTAX  INTEGER {
                    db44(1),
                    rj45(2),
                    na(3)
                }
            ACCESS  read-only
            STATUS  mandatory
            DESCRIPTION
                "RS232A Interface Type"
            ::= { rs232aConfigEntry 11 }

        rsCfgBitPosition0Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "RS232A Bits 0 Stream Position Used"
            ::= { rs232aConfigEntry 12 }

        rsCfgBitPosition1Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "RS232A Bits 1 Stream Position Used"
            ::= { rs232aConfigEntry 13 }

        rsCfgBitPosition2Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "RS232A Bits 2 Stream Position Used"
            ::= { rs232aConfigEntry 14 }

        rsCfgBitPosition3Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "RS232A Bits 3 Stream Position Used"
            ::= { rs232aConfigEntry 15 }

        rsCfgBitPosition4Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "RS232A Bits 4 Stream Position Used"
            ::= { rs232aConfigEntry 16 }

        rsCfgBitPosition5Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "RS232A Bits 5 Stream Position Used"
            ::= { rs232aConfigEntry 17 }

        rsCfgBitPosition6Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "RS232A Bits 6 Stream Position Used"
            ::= { rs232aConfigEntry 18 }

        rsCfgBitPosition7Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "RS232A Bits 7 Stream Position Used"
            ::= { rs232aConfigEntry 19 }

        rsCfgWarrning  OBJECT-TYPE
            SYNTAX  DisplayString (SIZE (0..70) )
            ACCESS  read-only
            STATUS  mandatory
            DESCRIPTION
                "RS232A map setup warning"
            ::= { rs232aConfigEntry 20 }


--
--  RS232A Status
--

        rs232aStatusTable  OBJECT-TYPE
            SYNTAX  SEQUENCE OF Rs232aStatusEntry
            ACCESS  not-accessible
            STATUS  mandatory
            DESCRIPTION
                "The RS232A Status table."
            ::= { rs232a-card 2 }

        rs232aStatusEntry  OBJECT-TYPE
            SYNTAX  Rs232aStatusEntry
            ACCESS  not-accessible
            STATUS  mandatory
            DESCRIPTION
                "An entry in the RS232A Status table."
            INDEX { rs232aStatusSlotIndex , rs232aStatusPortIndex }
            ::= { rs232aStatusTable 1 }

        Rs232aStatusEntry ::= SEQUENCE {
            rs232aStatusSlotIndex         LSSlotID,
            rs232aStatusPortIndex         SixPortID,
            rs232aStatusS1                INTEGER,
            rs232aStatusS3                INTEGER,
            rs232aStatusS4                INTEGER,
            rs232aStatusS6                INTEGER,
            rs232aStatusS8                INTEGER,
            rs232aStatusS9                INTEGER,
            rs232aStatusE4                INTEGER,
            rs232aStatusE5                INTEGER,
            rs232aStatusE6                INTEGER,
            rs232aStatusX                 INTEGER,
            rs232aStatusDteCTS            INTEGER,
            rs232aStatusDteDCD            INTEGER,
            rs232aStatusRTSloss           INTEGER,
            rs232aStatusEXTCLKloss        INTEGER,
            rs232aStatusDSRstatus         INTEGER,
            rs232aStatusCTSstatus         INTEGER,
            rs232aStatusDCDstatus         INTEGER,
            rs232aStatusDTRstatus         INTEGER,
            rs232aStatusRTSstatus         INTEGER,
            rs232aStatusRemoteAlarm       INTEGER,
            rs232aStatusRemoteS1          INTEGER,
            rs232aStatusRemoteS3          INTEGER,
            rs232aStatusRemoteS4          INTEGER,
            rs232aStatusRemoteS6          INTEGER,
            rs232aStatusRemoteS8          INTEGER,
            rs232aStatusRemoteS9          INTEGER,
            rs232aStatusRemoteE4          INTEGER,
            rs232aStatusRemoteE5          INTEGER,
            rs232aStatusRemoteE6          INTEGER,
            rs232aStatusRemoteX           INTEGER
        }

        rs232aStatusSlotIndex  OBJECT-TYPE
            SYNTAX  LSSlotID
            ACCESS  read-only
            STATUS  mandatory
            DESCRIPTION
                "RS232A slot index"
            ::= { rs232aStatusEntry 1 }

        rs232aStatusPortIndex  OBJECT-TYPE
            SYNTAX  SixPortID
            ACCESS  read-only
            STATUS  mandatory
            DESCRIPTION
                "Port 1 to 6, Total 6 ports"
            ::= { rs232aStatusEntry 2 }

        rs232aStatusS1  OBJECT-TYPE
            SYNTAX  INTEGER {
                    off(1),
                    on(2),
                    rts(3),
                    dtr(4),
                    dsr(5),
                    na(14)
                }
            ACCESS  read-write
            STATUS  mandatory
            DESCRIPTION
                "RS232A Status bit S1"
            ::= { rs232aStatusEntry 3 }

        rs232aStatusS3  OBJECT-TYPE
            SYNTAX  INTEGER {
                    off(1),
                    on(2),
                    rts(3),
                    dtr(4),
                    dsr(5),
                    na(14)
                }
            ACCESS  read-write
            STATUS  mandatory
            DESCRIPTION
                "RS232A Status bit S3"
            ::= { rs232aStatusEntry 4 }

        rs232aStatusS4  OBJECT-TYPE
            SYNTAX  INTEGER {
                    off(1),
                    on(2),
                    rts(3),
                    dtr(4),
                    dsr(5),
                    na(14)
                }
            ACCESS  read-write
            STATUS  mandatory
            DESCRIPTION
                "RS232A Status bit S4"
            ::= { rs232aStatusEntry 5 }

        rs232aStatusS6  OBJECT-TYPE
            SYNTAX  INTEGER {
                    off(1),
                    on(2),
                    rts(3),
                    dtr(4),
                    dsr(5),
                    na(14)
                }
            ACCESS  read-write
            STATUS  mandatory
            DESCRIPTION
                "RS232A Status bit S6"
            ::= { rs232aStatusEntry 6 }

        rs232aStatusS8  OBJECT-TYPE
            SYNTAX  INTEGER {
                    off(1),
                    on(2),
                    rts(3),
                    dtr(4),
                    dsr(5),
                    na(14)
                }
            ACCESS  read-write
            STATUS  mandatory
            DESCRIPTION
                "RS232A Status bit S8"
            ::= { rs232aStatusEntry 7 }

        rs232aStatusS9  OBJECT-TYPE
            SYNTAX  INTEGER {
                    off(1),
                    on(2),
                    rts(3),
                    dtr(4),
                    dsr(5),
                    na(14)
                }
            ACCESS  read-write
            STATUS  mandatory
            DESCRIPTION
                "RS232A Status bit S9"
            ::= { rs232aStatusEntry 8 }

        rs232aStatusE4  OBJECT-TYPE
            SYNTAX  INTEGER {
                    off(1),
                    on(2),
                    na(14)
                }
            ACCESS  read-write
            STATUS  mandatory
            DESCRIPTION
                "RS232A Status bit E4"
            ::= { rs232aStatusEntry 9 }

        rs232aStatusE5  OBJECT-TYPE
            SYNTAX  INTEGER {
                    off(1),
                    on(2),
                    na(14)
                }
            ACCESS  read-write
            STATUS  mandatory
            DESCRIPTION
                "RS232A Status bit E5"
            ::= { rs232aStatusEntry 10 }

        rs232aStatusE6  OBJECT-TYPE
            SYNTAX  INTEGER {
                    off(1),
                    on(2),
                    na(14)
                }
            ACCESS  read-write
            STATUS  mandatory
            DESCRIPTION
                "RS232A Status bit E6"
            ::= { rs232aStatusEntry 11 }

        rs232aStatusX  OBJECT-TYPE
            SYNTAX  INTEGER {
                    off(1),
                    on(2),
                    rtswithFrameSYNC(12),
                    frameSYNC(13),
                    na(14)
                }
            ACCESS  read-write
            STATUS  mandatory
            DESCRIPTION
                "RS232A Status bit X"
            ::= { rs232aStatusEntry 12 }

        rs232aStatusDteCTS  OBJECT-TYPE
            SYNTAX  INTEGER {
                    off(1),
                    on(2),
                    rts(3),
                    remote-S1(6),
                    remote-S3(7),
                    remote-S4(8),
                    remote-S6(9),
                    remote-S8(10),
                    remote-S9(11)
                }
            ACCESS  read-write
            STATUS  mandatory
            DESCRIPTION
                "RS232A Status bit DTE CTS"
            ::= { rs232aStatusEntry 13 }

        rs232aStatusDteDCD  OBJECT-TYPE
            SYNTAX  INTEGER {
                    off(1),
                    on(2),
                    rts(3),
                    remote-S1(6),
                    remote-S3(7),
                    remote-S4(8),
                    remote-S6(9),
                    remote-S8(10),
                    remote-S9(11)
                }
            ACCESS  read-write
            STATUS  mandatory
            DESCRIPTION
                "RS232A Status bit DTE DCD"
            ::= { rs232aStatusEntry 14 }

        rs232aStatusRTSloss  OBJECT-TYPE
            SYNTAX  INTEGER {
                    no(1),
                    yes(2),
                    na(3)
                }
            ACCESS  read-only
            STATUS  mandatory
            DESCRIPTION
                "RS232A RTS loss"
            ::= { rs232aStatusEntry 15 }

        rs232aStatusEXTCLKloss  OBJECT-TYPE
            SYNTAX  INTEGER {
                    no(1),
                    yes(2),
                    na(3)
                }
            ACCESS  read-only
            STATUS  mandatory
            DESCRIPTION
                "RS232A EXT-CLK loss"
            ::= { rs232aStatusEntry 16 }

        rs232aStatusDSRstatus  OBJECT-TYPE
            SYNTAX  INTEGER {
                    no(1),
                    yes(2),
                    na(3)
                }
            ACCESS  read-only
            STATUS  mandatory
            DESCRIPTION
                "RS232A DSR"
            ::= { rs232aStatusEntry 17 }

        rs232aStatusCTSstatus  OBJECT-TYPE
            SYNTAX  INTEGER {
                    no(1),
                    yes(2),
                    na(3)
                }
            ACCESS  read-only
            STATUS  mandatory
            DESCRIPTION
                "RS232A CTS"
            ::= { rs232aStatusEntry 18 }

        rs232aStatusDCDstatus  OBJECT-TYPE
            SYNTAX  INTEGER {
                    no(1),
                    yes(2),
                    na(3)
                }
            ACCESS  read-only
            STATUS  mandatory
            DESCRIPTION
                "RS232A DCD"
            ::= { rs232aStatusEntry 19 }

        rs232aStatusDTRstatus  OBJECT-TYPE
            SYNTAX  INTEGER {
                    no(1),
                    yes(2),
                    na(3)
                }
            ACCESS  read-only
            STATUS  mandatory
            DESCRIPTION
                "RS232A DTR"
            ::= { rs232aStatusEntry 20 }

        rs232aStatusRTSstatus  OBJECT-TYPE
            SYNTAX  INTEGER {
                    no(1),
                    yes(2),
                    na(3)
                }
            ACCESS  read-only
            STATUS  mandatory
            DESCRIPTION
                "RS232A RTS"
            ::= { rs232aStatusEntry 21 }

        rs232aStatusRemoteAlarm  OBJECT-TYPE
            SYNTAX  INTEGER {
                    no(1),
                    yes(2),
                    na(3)
                }
            ACCESS  read-only
            STATUS  mandatory
            DESCRIPTION
                "RS232A RTS"
            ::= { rs232aStatusEntry 22 }

        rs232aStatusRemoteS1  OBJECT-TYPE
            SYNTAX  INTEGER {
                    off(1),
                    on(2),
                    na(14)
                }
            ACCESS  read-only
            STATUS  mandatory
            DESCRIPTION
                "RS232A remote status bit S1"
            ::= { rs232aStatusEntry 23 }

        rs232aStatusRemoteS3  OBJECT-TYPE
            SYNTAX  INTEGER {
                    off(1),
                    on(2),
                    na(14)
                }
            ACCESS  read-only
            STATUS  mandatory
            DESCRIPTION
                "RS232A remote status bit S3"
            ::= { rs232aStatusEntry 24 }

        rs232aStatusRemoteS4  OBJECT-TYPE
            SYNTAX  INTEGER {
                    off(1),
                    on(2),
                    na(14)
                }
            ACCESS  read-only
            STATUS  mandatory
            DESCRIPTION
                "RS232A remote status bit S4"
            ::= { rs232aStatusEntry 25 }

        rs232aStatusRemoteS6  OBJECT-TYPE
            SYNTAX  INTEGER {
                    off(1),
                    on(2),
                    na(14)
                }
            ACCESS  read-only
            STATUS  mandatory
            DESCRIPTION
                "RS232A remote status bit S6"
            ::= { rs232aStatusEntry 26 }

        rs232aStatusRemoteS8  OBJECT-TYPE
            SYNTAX  INTEGER {
                    off(1),
                    on(2),
                    na(14)
                }
            ACCESS  read-only
            STATUS  mandatory
            DESCRIPTION
                "RS232A remote status bit S8"
            ::= { rs232aStatusEntry 27 }

        rs232aStatusRemoteS9  OBJECT-TYPE
            SYNTAX  INTEGER {
                    off(1),
                    on(2),
                    na(14)
                }
            ACCESS  read-only
            STATUS  mandatory
            DESCRIPTION
                "RS232A remote status bit S9"
            ::= { rs232aStatusEntry 28 }

        rs232aStatusRemoteE4  OBJECT-TYPE
            SYNTAX  INTEGER {
                    off(1),
                    on(2),
                    na(14)
                }
            ACCESS  read-only
            STATUS  mandatory
            DESCRIPTION
                "RS232A remote status bit E4"
            ::= { rs232aStatusEntry 29 }

        rs232aStatusRemoteE5  OBJECT-TYPE
            SYNTAX  INTEGER {
                    off(1),
                    on(2),
                    na(14)
                }
            ACCESS  read-only
            STATUS  mandatory
            DESCRIPTION
                "RS232A remote status bit E5"
            ::= { rs232aStatusEntry 30 }

        rs232aStatusRemoteE6  OBJECT-TYPE
            SYNTAX  INTEGER {
                    off(1),
                    on(2),
                    na(14)
                }
            ACCESS  read-only
            STATUS  mandatory
            DESCRIPTION
                "RS232A remote status bit E6"
            ::= { rs232aStatusEntry 31 }

        rs232aStatusRemoteX  OBJECT-TYPE
            SYNTAX  INTEGER {
                    off(1),
                    on(2),
                    na(14)
                }
            ACCESS  read-only
            STATUS  mandatory
            DESCRIPTION
                "RS232A remote status bit X"
            ::= { rs232aStatusEntry 32 }

--
--  Alarm Control Table
--

        rs232aAlarmControlTable  OBJECT-TYPE
            SYNTAX  SEQUENCE OF Rs232aAlarmControlEntry
            ACCESS  not-accessible
            STATUS  mandatory
            DESCRIPTION
                "The RS232A alarm control table."
            ::= { rs232a-card 3 }

        rs232aAlarmControlEntry  OBJECT-TYPE
            SYNTAX  Rs232aAlarmControlEntry
            ACCESS  not-accessible
            STATUS  mandatory
            DESCRIPTION
                "An entry in the RS232A alarm control table."
            INDEX { rs232aAlarmSlotIndex , rs232aAlarmPortIndex }
            ::= { rs232aAlarmControlTable 1 }

        Rs232aAlarmControlEntry ::= SEQUENCE {
            rs232aAlarmSlotIndex           LSSlotID,
            rs232aAlarmPortIndex           SixPortID,
            rs232aAlarmSetup               LsAlarmSeverity
        }

        rs232aAlarmSlotIndex  OBJECT-TYPE
            SYNTAX  LSSlotID
            ACCESS  read-only
            STATUS  mandatory
            DESCRIPTION
                "RS232A slot index"
            ::= { rs232aAlarmControlEntry 1 }

        rs232aAlarmPortIndex  OBJECT-TYPE
            SYNTAX  SixPortID
            ACCESS  read-only
            STATUS  mandatory
            DESCRIPTION
                "Port 1 to 6, Total 6 ports"
            ::= { rs232aAlarmControlEntry 2 }

        rs232aAlarmSetup  OBJECT-TYPE
            SYNTAX  LsAlarmSeverity
            ACCESS  read-write
            STATUS  mandatory
            DESCRIPTION
                "Alarm is enabled or not"
            ::= { rs232aAlarmControlEntry 3 }


--
--  Alarm History Table
--

        rs232aAlmHistoryTable  OBJECT-TYPE
            SYNTAX  SEQUENCE OF Rs232aAlmHistoryEntry
            ACCESS  not-accessible
            STATUS  mandatory
            DESCRIPTION
                " Key: rs232aAlmHistoryUnitIndex "
            ::= { rs232a-card 4 }

        rs232aAlmHistoryEntry  OBJECT-TYPE
            SYNTAX  Rs232aAlmHistoryEntry
            ACCESS  not-accessible
            STATUS  mandatory
            DESCRIPTION
                " "
            INDEX { rs232aAlmHisSlotIndex , rs232aAlmHisPortIndex }
            ::= { rs232aAlmHistoryTable 1 }

        Rs232aAlmHistoryEntry ::= SEQUENCE {
            rs232aAlmHisSlotIndex      LSSlotID,
            rs232aAlmHisPortIndex      SixPortID,
            rs232aAlmHistoryState          INTEGER,
            rs232aAlmHistoryCount          Counter,
            rs232aAlmHistoryEnable         LsAlarmSeverity
        }

        rs232aAlmHisSlotIndex  OBJECT-TYPE
            SYNTAX  LSSlotID
            ACCESS  read-only
            STATUS  mandatory
            DESCRIPTION
                "RS232A slot index"
            ::= { rs232aAlmHistoryEntry 1 }

        rs232aAlmHisPortIndex  OBJECT-TYPE
            SYNTAX  SixPortID
            ACCESS  read-only
            STATUS  mandatory
            DESCRIPTION
                "Port 1 to 6, Total 6 ports"
            ::= { rs232aAlmHistoryEntry 2 }

        rs232aAlmHistoryState  OBJECT-TYPE
            SYNTAX  INTEGER {
                    ok(1),
                    alarm(2),
                    disable(3),
                    na(4)
                }
            ACCESS  read-only
            STATUS  mandatory
            DESCRIPTION
                " Alarm Current State"
            ::= { rs232aAlmHistoryEntry 3 }

        rs232aAlmHistoryCount  OBJECT-TYPE
            SYNTAX  Counter
            ACCESS  read-only
            STATUS  mandatory
            DESCRIPTION
                " Alarm Count which happened "
            ::= { rs232aAlmHistoryEntry 4 }

        rs232aAlmHistoryEnable  OBJECT-TYPE
            SYNTAX  LsAlarmSeverity
            ACCESS  read-only
            STATUS  mandatory
            DESCRIPTION
                "Alarm is enabled or not"
            ::= { rs232aAlmHistoryEntry 5 }


--
-- Diagnostic Control Table
--

        rs232aDiagControlTable  OBJECT-TYPE
            SYNTAX  SEQUENCE OF Rs232aDiagControlEntry
            ACCESS  not-accessible
            STATUS  mandatory
            DESCRIPTION
                ""
            ::= { rs232a-card 5 }

        rs232aDiagControlEntry  OBJECT-TYPE
            SYNTAX  Rs232aDiagControlEntry
            ACCESS  not-accessible
            STATUS  mandatory
            DESCRIPTION
                ""
            INDEX { rs232aDiagCtrlSlotIndex , rs232aDiagCtrlPortIndex }
            ::= { rs232aDiagControlTable 1 }

        Rs232aDiagControlEntry ::= SEQUENCE {
            rs232aDiagCtrlSlotIndex     LSSlotID,
            rs232aDiagCtrlPortIndex     SixPortID,
            rs232aNearLoopback             INTEGER
        }

        rs232aDiagCtrlSlotIndex  OBJECT-TYPE
            SYNTAX  LSSlotID
            ACCESS  read-only
            STATUS  mandatory
            DESCRIPTION
                "RS232A slot index"
            ::= { rs232aDiagControlEntry 1 }

        rs232aDiagCtrlPortIndex  OBJECT-TYPE
            SYNTAX  SixPortID
            ACCESS  read-only
            STATUS  mandatory
            DESCRIPTION
                "Port 1 to 6, Total 6 ports"
            ::= { rs232aDiagControlEntry 2 }

        rs232aNearLoopback  OBJECT-TYPE
            SYNTAX  INTEGER {
                    noLoopback(1),
                    toDTE(2),
                    toLocal(3)
                }
            ACCESS  read-write
            STATUS  mandatory
            DESCRIPTION
                "RS232A Loopback Type"
            ::= { rs232aDiagControlEntry 3 }

--
-- Card Control Table
--

        rs232aCardControlTable  OBJECT-TYPE
            SYNTAX  SEQUENCE OF Rs232aCardControlEntry
            ACCESS  not-accessible
            STATUS  mandatory
            DESCRIPTION
                "The RS232A Card control table."
            ::= { rs232a-card 6 }

        rs232aCardControlEntry  OBJECT-TYPE
            SYNTAX  Rs232aCardControlEntry
            ACCESS  not-accessible
            STATUS  mandatory
            DESCRIPTION
                "An entry in the RS232A Card control table."
            INDEX { rs232aCardIndex }
            ::= { rs232aCardControlTable 1 }

        Rs232aCardControlEntry ::= SEQUENCE {
            rs232aCardIndex                LSSlotID,
            rs232aReset                    INTEGER,
            rs232aLoadDefault              INTEGER
        }

        rs232aCardIndex  OBJECT-TYPE
            SYNTAX  LSSlotID
            ACCESS  read-only
            STATUS  mandatory
            DESCRIPTION
                "RS232A slot index"
            ::= { rs232aCardControlEntry 1 }

        rs232aReset  OBJECT-TYPE
            SYNTAX  INTEGER {
                    na(1),
                    reset(2)
                }
            ACCESS  read-write
            STATUS  mandatory
            DESCRIPTION
                "Reset rs232a card"
            ::= { rs232aCardControlEntry 2 }

        rs232aLoadDefault  OBJECT-TYPE
            SYNTAX  INTEGER {
                    na(1),
                    default(2)
                }
            ACCESS  read-write
            STATUS  mandatory
            DESCRIPTION
                "Load default"
            ::= { rs232aCardControlEntry 3 }

--
--  RS232A System Information Table
--

        rs232aSystemInfoTable  OBJECT-TYPE
            SYNTAX  SEQUENCE OF Rs232aSystemInfoEntry
            ACCESS  not-accessible
            STATUS  mandatory
            DESCRIPTION
                "The RS232A system information table."
            ::= { rs232a-card 7}

        rs232aSystemInfoEntry  OBJECT-TYPE
            SYNTAX  Rs232aSystemInfoEntry
            ACCESS  not-accessible
            STATUS  mandatory
            DESCRIPTION
                "An entry in the RS232A system information table."
            INDEX { rs232aSISlotIndex }
            ::= { rs232aSystemInfoTable 1 }

        Rs232aSystemInfoEntry ::= SEQUENCE {
            rs232aSISlotIndex            LSSlotID,
            rs232aPROMVersion            DisplayString,
            rs232aHardwareVersion        DisplayString,
            rs232aFpgaVersion            DisplayString,
            rs232aBank1Version           DisplayString,
            rs232aBank2Version           DisplayString,
            rs232aActiveBank             INTEGER
        }

        rs232aSISlotIndex  OBJECT-TYPE
            SYNTAX  LSSlotID
            ACCESS  read-only
            STATUS  mandatory
            DESCRIPTION
                "RS232A slot index"
            ::= { rs232aSystemInfoEntry 1 }

        rs232aPROMVersion  OBJECT-TYPE
            SYNTAX  DisplayString (SIZE (0..30) )
            ACCESS  read-only
            STATUS  mandatory
            DESCRIPTION
                " RS232A PROM Version"
            ::= { rs232aSystemInfoEntry 2 }

        rs232aHardwareVersion  OBJECT-TYPE
            SYNTAX  DisplayString (SIZE (0..30) )
            ACCESS  read-only
            STATUS  mandatory
            DESCRIPTION
                " RS232A Hardware Version"
            ::= { rs232aSystemInfoEntry 3 }

        rs232aFpgaVersion  OBJECT-TYPE
            SYNTAX  DisplayString (SIZE (0..30))
            ACCESS  read-only
            STATUS  mandatory
            DESCRIPTION
                "FPGA Version"
            ::= { rs232aSystemInfoEntry 4 }

        rs232aBank1Version    OBJECT-TYPE
            SYNTAX  DisplayString (SIZE (0..30))
            ACCESS  read-only
            STATUS  mandatory
            DESCRIPTION
                "Bank-1 Version"
            ::= { rs232aSystemInfoEntry 5 }

        rs232aBank2Version    OBJECT-TYPE
            SYNTAX  DisplayString (SIZE (0..30))
            ACCESS  read-only
            STATUS  mandatory
            DESCRIPTION
                "Bank-2 Version"
            ::= { rs232aSystemInfoEntry 6}

        rs232aActiveBank    OBJECT-TYPE
            SYNTAX  INTEGER{
                    bank-1(1),
                    bank-2(2)
                }
            ACCESS  read-only
            STATUS  mandatory
            DESCRIPTION
                "Active Bank 1/2"
            ::= { rs232aSystemInfoEntry 7 }

        rs232aTotalCard   OBJECT-TYPE
            SYNTAX  INTEGER
            ACCESS  read-only
            STATUS  mandatory
            DESCRIPTION
                "Total cards of RS232A"
            ::= { rs232a-card 100 }


--======================================================================--
--======================================================================--
--  TTA-card MIB
--======================================================================--
--======================================================================--

    ttaSysConfigTable                  OBJECT IDENTIFIER ::= { tta-card 1 }
--
--  In & Out Table
--

    ttaInOutTable         OBJECT IDENTIFIER ::= { ttaSysConfigTable 1 }

--
--  In & Out 1 Table
--

        ttaInOut1Table  OBJECT-TYPE
            SYNTAX  SEQUENCE OF TtaInOut1Entry
            ACCESS  not-accessible
            STATUS  mandatory
            DESCRIPTION
                " The TTA In and Out 1 Table "
            ::= { ttaInOutTable 1 }

        ttaInOut1Entry  OBJECT-TYPE
            SYNTAX  TtaInOut1Entry
            ACCESS  not-accessible
            STATUS  mandatory
            DESCRIPTION
                " An entry in the TTA In and Out 1 Table "
            INDEX { ttaInOut1SlotIndex , ttaInOut1PortIndex }
            ::= { ttaInOut1Table 1 }

        TtaInOut1Entry ::= SEQUENCE {
            ttaInOut1SlotIndex      LSSlotID,
            ttaInOut1PortIndex      FourPortID,
            ttaInOut1PreTripTimer   INTEGER,
            ttaInOut1TripHoldTimer  INTEGER,
            ttaInOut1DebounceTimer  INTEGER
        }

        ttaInOut1SlotIndex  OBJECT-TYPE
            SYNTAX  LSSlotID
            ACCESS  read-only
            STATUS  mandatory
            DESCRIPTION
                "TTA slot"
            ::= { ttaInOut1Entry 1 }

        ttaInOut1PortIndex  OBJECT-TYPE
            SYNTAX  FourPortID
            ACCESS  read-only
            STATUS  mandatory
            DESCRIPTION
                " Port 1 to 4, Total 4 ports "
            ::= { ttaInOut1Entry 2 }

        ttaInOut1PreTripTimer  OBJECT-TYPE
            SYNTAX  INTEGER (1..30)
            ACCESS  read-write
            STATUS  mandatory
            DESCRIPTION
                " PRE-TRIP Timer (ms)(1-30) "
            ::= { ttaInOut1Entry 3 }

        ttaInOut1TripHoldTimer  OBJECT-TYPE
            SYNTAX  INTEGER (1..256)
            ACCESS  read-write
            STATUS  mandatory
            DESCRIPTION
                " TRIP-HOLD Timer (ms)(1-256) "
            ::= { ttaInOut1Entry 4 }

        ttaInOut1DebounceTimer  OBJECT-TYPE
            SYNTAX  INTEGER (1..3)
            ACCESS  read-write
            STATUS  mandatory
            DESCRIPTION
                " Debounce Timer (ms)(1-3) "
            ::= { ttaInOut1Entry 5 }

--
--  In & Out 2 Table
--

        ttaInOut2Table  OBJECT-TYPE
            SYNTAX  SEQUENCE OF TtaInOut2Entry
            ACCESS  not-accessible
            STATUS  mandatory
            DESCRIPTION
                " The TTA In and Out 2 Table1 "
            ::= { ttaInOutTable 2 }

        ttaInOut2Entry  OBJECT-TYPE
            SYNTAX  TtaInOut2Entry
            ACCESS  not-accessible
            STATUS  mandatory
            DESCRIPTION
                " An entry in the TTA In and Out 2 Table "
            INDEX { ttaInOut2SlotIndex }
            ::= { ttaInOut2Table 1 }

        TtaInOut2Entry ::= SEQUENCE {
            ttaInOut2SlotIndex      LSSlotID,
--            ttaInOut2InOutInv       INTEGER,
            ttaInOut2IrigTimeStp    INTEGER,
            ttaInOut2PickUpNum      INTEGER,
            ttaInOut2DataDropTmr    INTEGER
--            ttaInOut2GlobalLoopbk   INTEGER

    }

        ttaInOut2SlotIndex  OBJECT-TYPE
            SYNTAX  LSSlotID
            ACCESS  read-only
            STATUS  mandatory
            DESCRIPTION
                "TTA slot"
            ::= { ttaInOut2Entry 1 }

--        ttaInOut2InOutInv  OBJECT-TYPE
--            SYNTAX  INTEGER {
--                    disable(1),
--                    enable(2)
--                }
--            ACCESS  read-write
--            STATUS  mandatory
--            DESCRIPTION
--                " Input & Output Inverter "
--            ::= { ttaInOut2Entry 2 }

        ttaInOut2IrigTimeStp  OBJECT-TYPE
            SYNTAX  INTEGER {
                    disable(1),
                    enable(2)
                }
            ACCESS  read-write
            STATUS  mandatory
            DESCRIPTION
                " IRIG Time Setup "
            ::= { ttaInOut2Entry 3 }

        ttaInOut2PickUpNum  OBJECT-TYPE
            SYNTAX  INTEGER (1..255)
            ACCESS  read-write
            STATUS  mandatory
            DESCRIPTION
                " Pick Up Number (times)(1-255) "
            ::= { ttaInOut2Entry 4 }

        ttaInOut2DataDropTmr  OBJECT-TYPE
            SYNTAX  INTEGER (5..1000)
            ACCESS  read-write
            STATUS  mandatory
            DESCRIPTION
                " Data Drop Timer (ms)(5-1000) "
            ::= { ttaInOut2Entry 5 }

--        ttaInOut2GlobalLoopbk  OBJECT-TYPE
--            SYNTAX  INTEGER {
--                    disable(1),
--                    enable(2)
--                }
--            ACCESS  read-write
--            STATUS  mandatory
--            DESCRIPTION
--                " Global Loopback "
--            ::= { ttaInOut2Entry 6 }


     ttaNewInOut1Table  OBJECT-TYPE
            SYNTAX  SEQUENCE OF TtaNewInOut1Entry
            ACCESS  not-accessible
            STATUS  mandatory
            DESCRIPTION
                " The TTA NewIn and Out 1 Table "
            ::= { ttaInOutTable 3 }

        ttaNewInOut1Entry  OBJECT-TYPE
            SYNTAX  TtaNewInOut1Entry
            ACCESS  not-accessible
            STATUS  mandatory
            DESCRIPTION
                " An entry in the TTA In and Out 1 Table "
            INDEX { ttaNewInOut1Slot , ttaNewInOut1Port }
            ::= { ttaNewInOut1Table 1 }

        TtaNewInOut1Entry ::= SEQUENCE {
            ttaNewInOut1Slot      LSSlotID,
            ttaNewInOut1Port      FourPortID,
            ttaNewInOut1InSup     INTEGER,
            ttaNewInOut1InSigLimit   INTEGER,
            ttaNewInOut1InSigExtend  INTEGER,
            ttaNewInOut1OutPerTrip    INTEGER,
            ttaNewInOut1OutSigLimit   INTEGER,
            ttaNewInOut1OutSigExtend  INTEGER
        }

        ttaNewInOut1Slot  OBJECT-TYPE
            SYNTAX  LSSlotID
            ACCESS  read-only
            STATUS  mandatory
            DESCRIPTION
            "TTA slot"
            ::= { ttaNewInOut1Entry 1 }

        ttaNewInOut1Port  OBJECT-TYPE
            SYNTAX  FourPortID
            ACCESS  read-only
            STATUS  mandatory
            DESCRIPTION
                " Port 1 to 4, Total 4 ports "
            ::= { ttaNewInOut1Entry 2 }

        ttaNewInOut1InSup     OBJECT-TYPE
            SYNTAX  INTEGER (1..30)
            ACCESS  read-write
            STATUS  mandatory
            DESCRIPTION
                " Input Suppression (ms)(0-255) "
            ::= { ttaNewInOut1Entry 3 }

        ttaNewInOut1InSigLimit   OBJECT-TYPE
            SYNTAX  INTEGER (1..30)
            ACCESS  read-write
            STATUS  mandatory
            DESCRIPTION
                " Input Signal Limit (ms)(0-4095) "
            ::= { ttaNewInOut1Entry 4 }

        ttaNewInOut1InSigExtend  OBJECT-TYPE
            SYNTAX  INTEGER (1..256)
            ACCESS  read-write
            STATUS  mandatory
            DESCRIPTION
                " Input Signal Extend (ms)(0-255) "
            ::= { ttaNewInOut1Entry 5 }

        ttaNewInOut1OutPerTrip    OBJECT-TYPE
            SYNTAX  INTEGER (1..3)
            ACCESS  read-write
            STATUS  mandatory
            DESCRIPTION
                " Pre Trip Timer (ms)(1-30) "
            ::= { ttaNewInOut1Entry 6 }

        ttaNewInOut1OutSigLimit   OBJECT-TYPE
            SYNTAX  INTEGER (1..3)
            ACCESS  read-write
            STATUS  mandatory
            DESCRIPTION
                " Output Signal Limit (ms)(0-4095) "
            ::= { ttaNewInOut1Entry 7 }

        ttaNewInOut1OutSigExtend  OBJECT-TYPE
            SYNTAX  INTEGER (1..3)
            ACCESS  read-write
            STATUS  mandatory
            DESCRIPTION
                " Output Signal Extend (ms)(0-255) "
            ::= { ttaNewInOut1Entry 8 }


--
--  NEW In & Out 2 Table
--

        ttaNewInOut2Table  OBJECT-TYPE
            SYNTAX  SEQUENCE OF TtaNewInOut2Entry
            ACCESS  not-accessible
            STATUS  mandatory
            DESCRIPTION
                " The TTA New In and Out 2 Table1 "
            ::= { ttaInOutTable 4 }

        ttaNewInOut2Entry  OBJECT-TYPE
            SYNTAX  TtaNewInOut2Entry
            ACCESS  not-accessible
            STATUS  mandatory
            DESCRIPTION
                " An entry in the TTA NewIn and Out 2 Table "
            INDEX { ttaNewInOut2Slot}
            ::= { ttaNewInOut2Table 1 }

        TtaNewInOut2Entry ::= SEQUENCE {
            ttaNewInOut2Slot         LSSlotID,
            ttaNewInOut2InOutMode       INTEGER,
            ttaNewInOut2IrigTimeStp    INTEGER,
            ttaNewInOut2PickUpNum      INTEGER,
            ttaNewInOut2DataDropTmr    INTEGER

         }

        ttaNewInOut2Slot  OBJECT-TYPE
            SYNTAX  LSSlotID
            ACCESS  read-only
            STATUS  mandatory
            DESCRIPTION
            "TTA slot"
            ::= { ttaNewInOut2Entry 1 }

        ttaNewInOut2InOutMode  OBJECT-TYPE
           SYNTAX  INTEGER {
                    one-to-one(1),
                    four-to-one(2)
                }
            ACCESS  read-write
            STATUS  mandatory
            DESCRIPTION
                " Input & Output Inverter "
           ::= { ttaNewInOut2Entry 2 }

        ttaNewInOut2IrigTimeStp  OBJECT-TYPE
            SYNTAX  INTEGER {
                    disable(1),
                    enable(2)
                }
            ACCESS  read-write
            STATUS  mandatory
            DESCRIPTION
                " IRIG Time Setup "
            ::= { ttaNewInOut2Entry 3 }

        ttaNewInOut2PickUpNum  OBJECT-TYPE
            SYNTAX  INTEGER (1..255)
            ACCESS  read-write
            STATUS  mandatory
            DESCRIPTION
                " Pick Up Number (times)(1-255) "
            ::= { ttaNewInOut2Entry 4 }

        ttaNewInOut2DataDropTmr  OBJECT-TYPE
            SYNTAX  INTEGER (5..1000)
            ACCESS  read-write
            STATUS  mandatory
            DESCRIPTION
                " Data Drop Timer (ms)(5-1000) "
            ::= { ttaNewInOut2Entry 5 }

--
--  Alarm Delay Min/Max Times Table
--

        ttaAlarmDelayTable  OBJECT-TYPE
            SYNTAX  SEQUENCE OF TtaAlarmDelayEntry
            ACCESS  not-accessible
            STATUS  mandatory
            DESCRIPTION
                " The Alarm Delay Min/Max Times Table "
            ::= { ttaSysConfigTable 2 }

        ttaAlarmDelayEntry  OBJECT-TYPE
            SYNTAX  TtaAlarmDelayEntry
            ACCESS  not-accessible
            STATUS  mandatory
            DESCRIPTION
                " An entry in the Alarm Delay Min/Max Times Table "
            INDEX { ttaAlarmDelaySlotIndex , ttaAlarmDelayPortIndex }
            ::= { ttaAlarmDelayTable 1 }

        TtaAlarmDelayEntry ::= SEQUENCE {
            ttaAlarmDelaySlotIndex      LSSlotID,
            ttaAlarmDelayPortIndex      FourPortID,
            ttaAlarmDelayUpper          INTEGER,
            ttaAlarmDelayLower          INTEGER,
            ttaAlarmDelayLocUserId      INTEGER,
            ttaAlarmDelayReUserId       INTEGER
        }

        ttaAlarmDelaySlotIndex  OBJECT-TYPE
            SYNTAX  LSSlotID
            ACCESS  read-only
            STATUS  mandatory
            DESCRIPTION
                "TTA slot"
            ::= { ttaAlarmDelayEntry 1 }

        ttaAlarmDelayPortIndex  OBJECT-TYPE
            SYNTAX  FourPortID
            ACCESS  read-only
            STATUS  mandatory
            DESCRIPTION
                " Port 1 to 4, Total 4 ports "
            ::= { ttaAlarmDelayEntry 2 }

        ttaAlarmDelayUpper  OBJECT-TYPE
            SYNTAX  INTEGER (0..1000000)
            ACCESS  read-write
            STATUS  mandatory
            DESCRIPTION
                " Upper (us)(0-1000000) "
            ::= { ttaAlarmDelayEntry 3 }

        ttaAlarmDelayLower  OBJECT-TYPE
            SYNTAX  INTEGER (0..1000000)
            ACCESS  read-write
            STATUS  mandatory
            DESCRIPTION
                " Lower (us)(0-1000000) "
            ::= { ttaAlarmDelayEntry 4 }

        ttaAlarmDelayLocUserId  OBJECT-TYPE
            SYNTAX  INTEGER (0..127)
            ACCESS  read-write
            STATUS  mandatory
            DESCRIPTION
                " Local User ID (0-127) "
            ::= { ttaAlarmDelayEntry 5 }

        ttaAlarmDelayReUserId  OBJECT-TYPE
            SYNTAX  INTEGER (0..127)
            ACCESS  read-write
            STATUS  mandatory
            DESCRIPTION
                " Remote User ID (0-127) "
            ::= { ttaAlarmDelayEntry 6 }

--
--Transfer Trip Input Rating Table
--

        ttaTrTripInputTable         OBJECT-TYPE
            SYNTAX  SEQUENCE OF TtaTrTripInputEntry
            ACCESS  not-accessible
            STATUS  mandatory
            DESCRIPTION
                " The Transfer Trip Input Rating Table "
            ::= { ttaSysConfigTable 3 }

        ttaTrTripInputEntry     OBJECT-TYPE
            SYNTAX  TtaTrTripInputEntry
            ACCESS  not-accessible
            STATUS  mandatory
            DESCRIPTION
                " An entry in the Transfer Trip Input Rating Table "
            INDEX { ttaTrTripInputSlotIndex , ttaTrTripInputPortIndex }
            ::= { ttaTrTripInputTable 1 }

        TtaTrTripInputEntry ::= SEQUENCE {
            ttaTrTripInputSlotIndex       LSSlotID,
            ttaTrTripInputPortIndex       FourPortID,
            ttaTrTripInputMaxDCInput      INTEGER
        }

        ttaTrTripInputSlotIndex  OBJECT-TYPE
            SYNTAX  LSSlotID
            ACCESS  read-only
            STATUS  mandatory
            DESCRIPTION
                "TTA slot"
            ::= { ttaTrTripInputEntry 1 }

        ttaTrTripInputPortIndex  OBJECT-TYPE
            SYNTAX  FourPortID
            ACCESS  read-only
            STATUS  mandatory
            DESCRIPTION
                " Port 1 to 4, Total 4 ports "
            ::= { ttaTrTripInputEntry 2 }

        ttaTrTripInputMaxDCInput  OBJECT-TYPE
            SYNTAX  INTEGER {
                    power24V(1),
                    power48V(2),
                    power125V(3),
                    power250V(4)
                }
            ACCESS  read-write
            STATUS  mandatory
            DESCRIPTION
                " Max. DC Input (V) "
            ::= { ttaTrTripInputEntry 3 }

--
--  Multi-channel Table
--

        ttaMultiChTable  OBJECT-TYPE
            SYNTAX  SEQUENCE OF TtaMultiChEntry
            ACCESS  not-accessible
            STATUS  mandatory
            DESCRIPTION
                " The TTA Multi-channel Table "
            ::= { ttaSysConfigTable 4 }

        ttaMultiChEntry  OBJECT-TYPE
            SYNTAX  TtaMultiChEntry
            ACCESS  not-accessible
            STATUS  mandatory
            DESCRIPTION
                " An entry in the TTA Multi-channel Table "
            INDEX { ttaMultiChSlotIndex , ttaMultiChPortIndex }
            ::= { ttaMultiChTable 1 }

        TtaMultiChEntry ::= SEQUENCE {
            ttaMultiChSlotIndex      LSSlotID,
            ttaMultiChPortIndex      FourPortID,
            ttaMultiChNoOfTS         INTEGER
        }

        ttaMultiChSlotIndex  OBJECT-TYPE
            SYNTAX  LSSlotID
            ACCESS  read-only
            STATUS  mandatory
            DESCRIPTION
                "TTA slot"
            ::= { ttaMultiChEntry 1 }

        ttaMultiChPortIndex  OBJECT-TYPE
            SYNTAX  FourPortID
            ACCESS  read-only
            STATUS  mandatory
            DESCRIPTION
                " Port 1 to 4, Total 4 ports "
            ::= { ttaMultiChEntry 2 }

        ttaMultiChNoOfTS  OBJECT-TYPE
            SYNTAX  INTEGER (1..3)
            ACCESS  read-write
            STATUS  mandatory
            DESCRIPTION
                " # of TS (1-3)"
            ::= { ttaMultiChEntry 3 }

--
--  Channel Lost Detection Table
--

        ttaChLostDetTable  OBJECT-TYPE
            SYNTAX  SEQUENCE OF TtaChLostDetEntry
            ACCESS  not-accessible
            STATUS  mandatory
            DESCRIPTION
                " The Channel Lost Detection Table "
            ::= { ttaSysConfigTable 5 }

        ttaChLostDetEntry  OBJECT-TYPE
            SYNTAX  TtaChLostDetEntry
            ACCESS  not-accessible
            STATUS  mandatory
            DESCRIPTION
                " An entry in the TTA Channel Lost Detection Table "
            INDEX { ttaChLostDetSlotIndex , ttaChLostDetPortIndex }
            ::= { ttaChLostDetTable 1 }

        TtaChLostDetEntry ::= SEQUENCE {
            ttaChLostDetSlotIndex      LSSlotID,
            ttaChLostDetPortIndex      FourPortID,
            ttaChLostDetLostDet        INTEGER
        }

        ttaChLostDetSlotIndex  OBJECT-TYPE
            SYNTAX  LSSlotID
            ACCESS  read-only
            STATUS  mandatory
            DESCRIPTION
                "TTA slot"
            ::= { ttaChLostDetEntry 1 }

        ttaChLostDetPortIndex  OBJECT-TYPE
            SYNTAX  FourPortID
            ACCESS  read-only
            STATUS  mandatory
            DESCRIPTION
                " Port 1 to 4, Total 4 ports "
            ::= { ttaChLostDetEntry 2 }

        ttaChLostDetLostDet  OBJECT-TYPE
            SYNTAX  INTEGER {
                    disable(1),
                    enable(2)
                }
            ACCESS  read-write
            STATUS  mandatory
            DESCRIPTION
                " Lost Detection "
            ::= { ttaChLostDetEntry 3 }

--
--  CH. Lost Relay One Shot Timer Table
--

        ttaOneShotTable  OBJECT-TYPE
            SYNTAX  SEQUENCE OF TtaOneShotEntry
            ACCESS  not-accessible
            STATUS  mandatory
            DESCRIPTION
                " The TTA CH. Lost Relay One Shot Timer Table "
            ::= { ttaSysConfigTable 6 }

        ttaOneShotEntry  OBJECT-TYPE
            SYNTAX  TtaOneShotEntry
            ACCESS  not-accessible
            STATUS  mandatory
            DESCRIPTION
                " An entry in the TTA CH. Lost Relay One Shot Timer Table "
            INDEX { ttaOneShotSlotIndex , ttaOneShotPortIndex }
            ::= { ttaOneShotTable 1 }

        TtaOneShotEntry ::= SEQUENCE {
            ttaOneShotSlotIndex      LSSlotID,
            ttaOneShotPortIndex      FourPortID,
            ttaOneShotOneShotPer     INTEGER
        }

        ttaOneShotSlotIndex  OBJECT-TYPE
            SYNTAX  LSSlotID
            ACCESS  read-only
            STATUS  mandatory
            DESCRIPTION
                "TTA slot"
            ::= { ttaOneShotEntry 1 }

        ttaOneShotPortIndex  OBJECT-TYPE
            SYNTAX  FourPortID
            ACCESS  read-only
            STATUS  mandatory
            DESCRIPTION
                " Port 1 to 4, Total 4 ports "
            ::= { ttaOneShotEntry 2 }

        ttaOneShotOneShotPer  OBJECT-TYPE
            SYNTAX  INTEGER (0..1023)
            ACCESS  read-write
            STATUS  mandatory
            DESCRIPTION
                " One Shot Period (ms)(0-1023) "
            ::= { ttaOneShotEntry 3 }

--
--  Alarm Relay Control Table
--

    ttaAlmRlyCtrlTable         OBJECT IDENTIFIER ::= { ttaSysConfigTable 7 }

--
--  Alarm Relay Control 1 Table
--

        ttaAlmRlyCtrl1Table  OBJECT-TYPE
            SYNTAX  SEQUENCE OF TtaAlmRlyCtrl1Entry
            ACCESS  not-accessible
            STATUS  mandatory
            DESCRIPTION
                " The TTA Alarm Relay Control 1 Table "
            ::= { ttaAlmRlyCtrlTable 1 }

        ttaAlmRlyCtrl1Entry  OBJECT-TYPE
            SYNTAX  TtaAlmRlyCtrl1Entry
            ACCESS  not-accessible
            STATUS  mandatory
            DESCRIPTION
                " An entry in the TTA Alarm Relay Control 1 Table "
            INDEX { ttaAlmRlyCtrl1SlotIndex , ttaAlmRlyCtrl1PortIndex }
            ::= { ttaAlmRlyCtrl1Table 1 }

        TtaAlmRlyCtrl1Entry ::= SEQUENCE {
            ttaAlmRlyCtrl1SlotIndex      LSSlotID,
            ttaAlmRlyCtrl1PortIndex      INTEGER,
            ttaAlmRlyCtrl1Status         LsAlarmSeverity,
            ttaAlmRlyCtrl1Clean          INTEGER
        }

        ttaAlmRlyCtrl1SlotIndex  OBJECT-TYPE
            SYNTAX  LSSlotID
            ACCESS  read-only
            STATUS  mandatory
            DESCRIPTION
                "TTA slot"
            ::= { ttaAlmRlyCtrl1Entry 1 }

        ttaAlmRlyCtrl1PortIndex  OBJECT-TYPE
            SYNTAX  INTEGER {
                    p1Of1(1),
                    p1Of2(2),
                    p2Of1(3),
                    p2Of2(4),
                    p3Of1(5),
                    p3Of2(6),
                    p4Of1(7),
                    p4Of2(8)
                }
            ACCESS  read-only
            STATUS  mandatory
            DESCRIPTION
                " Port p1Of1 to p4Of2, Total 8 ports "
            ::= { ttaAlmRlyCtrl1Entry 2 }

        ttaAlmRlyCtrl1Status  OBJECT-TYPE
            SYNTAX  LsAlarmSeverity
            ACCESS  read-write
            STATUS  mandatory
            DESCRIPTION
                " Status "
            ::= { ttaAlmRlyCtrl1Entry 3 }

        ttaAlmRlyCtrl1Clean  OBJECT-TYPE
            SYNTAX  INTEGER {
                    enable(1),
                    disable(2)
                }
            ACCESS  read-write
            STATUS  mandatory
            DESCRIPTION
                " Clean "
            ::= { ttaAlmRlyCtrl1Entry 4 }

--
--  Alarm Relay Control 2 Table
--

        ttaAlmRlyCtrl2Table  OBJECT-TYPE
            SYNTAX  SEQUENCE OF TtaAlmRlyCtrl2Entry
            ACCESS  not-accessible
            STATUS  mandatory
            DESCRIPTION
                " The TTA Alarm Relay Control 2 Table "
            ::= { ttaAlmRlyCtrlTable 2 }

        ttaAlmRlyCtrl2Entry  OBJECT-TYPE
            SYNTAX  TtaAlmRlyCtrl2Entry
            ACCESS  not-accessible
            STATUS  mandatory
            DESCRIPTION
                " An entry in the TTA Alarm Relay Control 2 Table "
            INDEX { ttaRlySlotIndex }
            ::= { ttaAlmRlyCtrl2Table 1 }

        TtaAlmRlyCtrl2Entry ::= SEQUENCE {
            ttaRlySlotIndex            LSSlotID,
            ttaRlyCardAlmRlyStatus     LsAlarmSeverity,
            ttaRlyCardAlmRlyClean      INTEGER
        }

        ttaRlySlotIndex  OBJECT-TYPE
            SYNTAX  LSSlotID
            ACCESS  read-only
            STATUS  mandatory
            DESCRIPTION
                "TTA slot"
            ::= { ttaAlmRlyCtrl2Entry 1 }

        ttaRlyCardAlmRlyStatus  OBJECT-TYPE
            SYNTAX  LsAlarmSeverity
            ACCESS  read-write
            STATUS  mandatory
            DESCRIPTION
                " Card Alarm Relay Status "
            ::= { ttaAlmRlyCtrl2Entry 2 }

        ttaRlyCardAlmRlyClean  OBJECT-TYPE
            SYNTAX  INTEGER {
                    enable(1),
                    disable(2)
                }
            ACCESS  read-write
            STATUS  mandatory
            DESCRIPTION
                " Card Alarm Relay Clean "
            ::= { ttaAlmRlyCtrl2Entry 3 }

--
--  PCM Rx Threshold Table
--

        ttaRxThrTable  OBJECT-TYPE
            SYNTAX  SEQUENCE OF TtaRxThrEntry
            ACCESS  not-accessible
            STATUS  mandatory
            DESCRIPTION
                " The PCM Rx Threshold Table "
            ::= { ttaSysConfigTable 8 }

        ttaRxThrEntry  OBJECT-TYPE
            SYNTAX  TtaRxThrEntry
            ACCESS  not-accessible
            STATUS  mandatory
            DESCRIPTION
                " An entry in the TTA PCM Rx Threshold Table "
            INDEX { ttaRxThrSlotIndex , ttaRxThrChIndex }
            ::= { ttaRxThrTable 1 }

        TtaRxThrEntry ::= SEQUENCE {
            ttaRxThrSlotIndex      LSSlotID,
            ttaRxThrChIndex        INTEGER,
            ttaRxThrRxThreshold    INTEGER
        }

        ttaRxThrSlotIndex  OBJECT-TYPE
            SYNTAX  LSSlotID
            ACCESS  read-only
            STATUS  mandatory
            DESCRIPTION
                "TTA slot"
            ::= { ttaRxThrEntry 1 }

        ttaRxThrChIndex  OBJECT-TYPE
            SYNTAX  INTEGER {
                    p1-1(1),
                    p1-2(2),
                    p1-3(3),
                    p2-1(4),
                    p2-2(5),
                    p2-3(6),
                    p3-1(7),
                    p3-2(8),
                    p3-3(9),
                    p4-1(10),
                    p4-2(11),
                    p4-3(12)
                }
            ACCESS  read-only
            STATUS  mandatory
            DESCRIPTION
                " Channel p1-1 to p4-3, Total 12 channels "
            ::= { ttaRxThrEntry 2 }

        ttaRxThrRxThreshold  OBJECT-TYPE
            SYNTAX  INTEGER (1..255)
            ACCESS  read-write
            STATUS  mandatory
            DESCRIPTION
                " PCM Rx Threshold (frame)(1-255) "
            ::= { ttaRxThrEntry 3 }

--
-- Trip Output  OR Table
--

        ttaORTripOutputTable         OBJECT-TYPE
            SYNTAX  SEQUENCE OF TtaORTripOutputEntry
            ACCESS  not-accessible
            STATUS  mandatory
            DESCRIPTION
                " The Trip Output OR Table "
            ::= { ttaSysConfigTable 9 }

        ttaORTripOutputEntry     OBJECT-TYPE
            SYNTAX  TtaORTripOutputEntry
            ACCESS  not-accessible
            STATUS  mandatory
            DESCRIPTION
                " An entry in the Transfer Trip Input Rating Table "
            INDEX { ttaORTripOutputSlot , ttaORTripOutputPort }
            ::= { ttaORTripOutputTable 1 }

        TtaORTripOutputEntry ::= SEQUENCE {
            ttaORTripOutputSlot       LSSlotID,
            ttaORTripOutputPort       FourPortID,
            ttaORTripOutputIn1        INTEGER,
            ttaORTripOutputIn2        INTEGER,
            ttaORTripOutputIn3        INTEGER,
            ttaORTripOutputIn4        INTEGER,
            ttaORTripOutputIn1Delay1  INTEGER,
            ttaORTripOutputIn2Delay1  INTEGER,
            ttaORTripOutputIn3Delay1  INTEGER,
            ttaORTripOutputIn4Delay1  INTEGER,
            ttaORTripOutputIn1Delay2  INTEGER,
            ttaORTripOutputIn2Delay2  INTEGER,
            ttaORTripOutputIn3Delay2  INTEGER,
            ttaORTripOutputIn4Delay2  INTEGER,
            ttaORTripOutputRx1        INTEGER,
            ttaORTripOutputRx2        INTEGER,
            ttaORTripOutputRx3        INTEGER,
            ttaORTripOutputRx4        INTEGER,
            ttaORTripOutputRx1Inv        INTEGER,
            ttaORTripOutputRx2Inv        INTEGER,
            ttaORTripOutputRx3Inv        INTEGER,
            ttaORTripOutputRx4Inv        INTEGER
        }

        ttaORTripOutputSlot  OBJECT-TYPE
            SYNTAX  LSSlotID
            ACCESS  read-only
            STATUS  mandatory
            DESCRIPTION
            "TTA slot"
            ::= { ttaORTripOutputEntry 1 }

        ttaORTripOutputPort  OBJECT-TYPE
            SYNTAX  FourPortID
            ACCESS  read-only
            STATUS  mandatory
            DESCRIPTION
                " Port 1 to 4, Total 4 ports "
            ::= { ttaORTripOutputEntry 2 }

        ttaORTripOutputIn1  OBJECT-TYPE
            SYNTAX  INTEGER {
                    disable(1),
                    enable(2)
                }
            ACCESS  read-write
            STATUS  mandatory
            DESCRIPTION
                " In 1 "
            ::= { ttaORTripOutputEntry 3 }

        ttaORTripOutputIn2  OBJECT-TYPE
            SYNTAX  INTEGER {
                    disable(1),
                    enable(2)
                }
            ACCESS  read-write
            STATUS  mandatory
            DESCRIPTION
                " In 2 "
            ::= { ttaORTripOutputEntry 4 }

        ttaORTripOutputIn3  OBJECT-TYPE
            SYNTAX  INTEGER {
                    disable(1),
                    enable(2)
                }
            ACCESS  read-write
            STATUS  mandatory
            DESCRIPTION
                " In 3"
            ::= { ttaORTripOutputEntry 5 }

        ttaORTripOutputIn4  OBJECT-TYPE
            SYNTAX  INTEGER {
                    disable(1),
                    enable(2)
                }
            ACCESS  read-write
            STATUS  mandatory
            DESCRIPTION
                " In 4"
            ::= { ttaORTripOutputEntry 6 }

        ttaORTripOutputIn1Delay1  OBJECT-TYPE
            SYNTAX  INTEGER {
                    disable(1),
                    enable(2)
                }
            ACCESS  read-write
            STATUS  mandatory
            DESCRIPTION
                " In Delay1"
            ::= { ttaORTripOutputEntry 7 }

        ttaORTripOutputIn2Delay1  OBJECT-TYPE
            SYNTAX  INTEGER {
                    disable(1),
                    enable(2)
                }
            ACCESS  read-write
            STATUS  mandatory
            DESCRIPTION
                " In 2 Delay1"
            ::= { ttaORTripOutputEntry 8 }

        ttaORTripOutputIn3Delay1  OBJECT-TYPE
            SYNTAX  INTEGER {
                    disable(1),
                    enable(2)
                }
            ACCESS  read-write
            STATUS  mandatory
            DESCRIPTION
                " In 3 Delay1"
            ::= { ttaORTripOutputEntry 9 }

        ttaORTripOutputIn4Delay1  OBJECT-TYPE
            SYNTAX  INTEGER {
                    disable(1),
                    enable(2)
                }
            ACCESS  read-write
            STATUS  mandatory
            DESCRIPTION
                " In 4 Delay1"
            ::= { ttaORTripOutputEntry 10}

       ttaORTripOutputIn1Delay2  OBJECT-TYPE
            SYNTAX  INTEGER {
                    disable(1),
                    enable(2)
                }
            ACCESS  read-write
            STATUS  mandatory
            DESCRIPTION
                " In Delay2"
            ::= { ttaORTripOutputEntry 11 }

        ttaORTripOutputIn2Delay2  OBJECT-TYPE
            SYNTAX  INTEGER {
                    disable(1),
                    enable(2)
                }
            ACCESS  read-write
            STATUS  mandatory
            DESCRIPTION
                " In 2 Delay2"
            ::= { ttaORTripOutputEntry 12 }

        ttaORTripOutputIn3Delay2  OBJECT-TYPE
            SYNTAX  INTEGER {
                    disable(1),
                    enable(2)
                }
            ACCESS  read-write
            STATUS  mandatory
            DESCRIPTION
                " In 3 Delay2"
            ::= { ttaORTripOutputEntry 13 }

        ttaORTripOutputIn4Delay2  OBJECT-TYPE
            SYNTAX  INTEGER {
                    disable(1),
                    enable(2)
                }
            ACCESS  read-write
            STATUS  mandatory
            DESCRIPTION
                " In 4 Delay2"
            ::= { ttaORTripOutputEntry 14}


        ttaORTripOutputRx1  OBJECT-TYPE
            SYNTAX  INTEGER {
                    disable(1),
                    enable(2)
                }
            ACCESS  read-write
            STATUS  mandatory
            DESCRIPTION
                " Rx 1 "
            ::= { ttaORTripOutputEntry 15}

        ttaORTripOutputRx2  OBJECT-TYPE
            SYNTAX  INTEGER {
                    disable(1),
                    enable(2)
                }
            ACCESS  read-write
            STATUS  mandatory
            DESCRIPTION
                " Rx 2 "
            ::= { ttaORTripOutputEntry 16}

        ttaORTripOutputRx3  OBJECT-TYPE
            SYNTAX  INTEGER {
                    disable(1),
                    enable(2)
                }
            ACCESS  read-write
            STATUS  mandatory
            DESCRIPTION
                " Rx 3 "
            ::= { ttaORTripOutputEntry 17}

        ttaORTripOutputRx4  OBJECT-TYPE
            SYNTAX  INTEGER {
                    disable(1),
                    enable(2)
                }
            ACCESS  read-write
            STATUS  mandatory
            DESCRIPTION
                " Rx 4 "
            ::= { ttaORTripOutputEntry 18}

        ttaORTripOutputRx1Inv  OBJECT-TYPE
            SYNTAX  INTEGER {
                    disable(1),
                    enable(2)
                }
            ACCESS  read-write
            STATUS  mandatory
            DESCRIPTION
                " Rx 1 inverse"
            ::= { ttaORTripOutputEntry 19}

        ttaORTripOutputRx2Inv  OBJECT-TYPE
            SYNTAX  INTEGER {
                    disable(1),
                    enable(2)
                }
            ACCESS  read-write
            STATUS  mandatory
            DESCRIPTION
                " Rx 2 inverse"
            ::= { ttaORTripOutputEntry 20}

        ttaORTripOutputRx3Inv  OBJECT-TYPE
            SYNTAX  INTEGER {
                    disable(1),
                    enable(2)
                }
            ACCESS  read-write
            STATUS  mandatory
            DESCRIPTION
                " Rx 3 inverse"
            ::= { ttaORTripOutputEntry 21}

        ttaORTripOutputRx4Inv  OBJECT-TYPE
            SYNTAX  INTEGER {
                    disable(1),
                    enable(2)
                }
            ACCESS  read-write
            STATUS  mandatory
            DESCRIPTION
                " Rx 4 inverse"
            ::= { ttaORTripOutputEntry 22}

--
-- Trip Output AND Table
--

        ttaANDTripOutputTable         OBJECT-TYPE
            SYNTAX  SEQUENCE OF TtaANDTripOutputEntry
            ACCESS  not-accessible
            STATUS  mandatory
            DESCRIPTION
                " The Trip Output AND Table "
            ::= { ttaSysConfigTable 10 }

        ttaANDTripOutputEntry     OBJECT-TYPE
            SYNTAX  TtaANDTripOutputEntry
            ACCESS  not-accessible
            STATUS  mandatory
            DESCRIPTION
                " An entry in the Transfer Trip Input Rating Table "
            INDEX { ttaANDTripOutputSlot , ttaANDTripOutputPort }
            ::= { ttaANDTripOutputTable 1 }

        TtaANDTripOutputEntry ::= SEQUENCE {
            ttaANDTripOutputSlot       LSSlotID,
            ttaANDTripOutputPort       FourPortID,
            ttaANDTripOutputIn1        INTEGER,
            ttaANDTripOutputIn2        INTEGER,
            ttaANDTripOutputIn3        INTEGER,
            ttaANDTripOutputIn4        INTEGER,
            ttaANDTripOutputIn1Delay1  INTEGER,
            ttaANDTripOutputIn2Delay1  INTEGER,
            ttaANDTripOutputIn3Delay1  INTEGER,
            ttaANDTripOutputIn4Delay1  INTEGER,
            ttaANDTripOutputIn1Delay2  INTEGER,
            ttaANDTripOutputIn2Delay2  INTEGER,
            ttaANDTripOutputIn3Delay2  INTEGER,
            ttaANDTripOutputIn4Delay2  INTEGER,
            ttaANDTripOutputRx1        INTEGER,
            ttaANDTripOutputRx2        INTEGER,
            ttaANDTripOutputRx3        INTEGER,
            ttaANDTripOutputRx4        INTEGER,
            ttaANDTripOutputRx1Inv        INTEGER,
            ttaANDTripOutputRx2Inv        INTEGER,
            ttaANDTripOutputRx3Inv        INTEGER,
            ttaANDTripOutputRx4Inv        INTEGER
        }

        ttaANDTripOutputSlot  OBJECT-TYPE
            SYNTAX  LSSlotID
            ACCESS  read-only
            STATUS  mandatory
            DESCRIPTION
            "TTA slot"
            ::= { ttaANDTripOutputEntry 1 }

        ttaANDTripOutputPort  OBJECT-TYPE
            SYNTAX  FourPortID
            ACCESS  read-only
            STATUS  mandatory
            DESCRIPTION
                " Port 1 to 4, Total 4 ports "
            ::= { ttaANDTripOutputEntry 2 }

        ttaANDTripOutputIn1  OBJECT-TYPE
            SYNTAX  INTEGER {
                    disable(1),
                    enable(2)
                }
            ACCESS  read-write
            STATUS  mandatory
            DESCRIPTION
                " In 1 "
            ::= { ttaANDTripOutputEntry 3 }

        ttaANDTripOutputIn2  OBJECT-TYPE
            SYNTAX  INTEGER {
                    disable(1),
                    enable(2)
                }
            ACCESS  read-write
            STATUS  mandatory
            DESCRIPTION
                " In 2 "
            ::= { ttaANDTripOutputEntry 4 }

        ttaANDTripOutputIn3  OBJECT-TYPE
            SYNTAX  INTEGER {
                    disable(1),
                    enable(2)
                }
            ACCESS  read-write
            STATUS  mandatory
            DESCRIPTION
                " In 3"
            ::= { ttaANDTripOutputEntry 5 }

        ttaANDTripOutputIn4  OBJECT-TYPE
            SYNTAX  INTEGER {
                    disable(1),
                    enable(2)
                }
            ACCESS  read-write
            STATUS  mandatory
            DESCRIPTION
                " In 4"
            ::= { ttaANDTripOutputEntry 6 }

        ttaANDTripOutputIn1Delay1  OBJECT-TYPE
            SYNTAX  INTEGER {
                    disable(1),
                    enable(2)
                }
            ACCESS  read-write
            STATUS  mandatory
            DESCRIPTION
                " In Delay1"
            ::= { ttaANDTripOutputEntry 7 }

        ttaANDTripOutputIn2Delay1  OBJECT-TYPE
            SYNTAX  INTEGER {
                    disable(1),
                    enable(2)
                }
            ACCESS  read-write
            STATUS  mandatory
            DESCRIPTION
                " In 2 Delay1"
            ::= { ttaANDTripOutputEntry 8 }

        ttaANDTripOutputIn3Delay1  OBJECT-TYPE
            SYNTAX  INTEGER {
                    disable(1),
                    enable(2)
                }
            ACCESS  read-write
            STATUS  mandatory
            DESCRIPTION
                " In 3 Delay1"
            ::= { ttaANDTripOutputEntry 9 }

        ttaANDTripOutputIn4Delay1  OBJECT-TYPE
            SYNTAX  INTEGER {
                    disable(1),
                    enable(2)
                }
            ACCESS  read-write
            STATUS  mandatory
            DESCRIPTION
                " In 4 Delay1"
            ::= { ttaANDTripOutputEntry 10}

       ttaANDTripOutputIn1Delay2  OBJECT-TYPE
            SYNTAX  INTEGER {
                    disable(1),
                    enable(2)
                }
            ACCESS  read-write
            STATUS  mandatory
            DESCRIPTION
                " In Delay2"
            ::= { ttaANDTripOutputEntry 11 }

        ttaANDTripOutputIn2Delay2  OBJECT-TYPE
            SYNTAX  INTEGER {
                    disable(1),
                    enable(2)
                }
            ACCESS  read-write
            STATUS  mandatory
            DESCRIPTION
                " In 2 Delay2"
            ::= { ttaANDTripOutputEntry 12 }

        ttaANDTripOutputIn3Delay2  OBJECT-TYPE
            SYNTAX  INTEGER {
                    disable(1),
                    enable(2)
                }
            ACCESS  read-write
            STATUS  mandatory
            DESCRIPTION
                " In 3 Delay2"
            ::= { ttaANDTripOutputEntry 13 }

        ttaANDTripOutputIn4Delay2  OBJECT-TYPE
            SYNTAX  INTEGER {
                    disable(1),
                    enable(2)
                }
            ACCESS  read-write
            STATUS  mandatory
            DESCRIPTION
                " In 4 Delay2"
            ::= { ttaANDTripOutputEntry 14}


        ttaANDTripOutputRx1  OBJECT-TYPE
            SYNTAX  INTEGER {
                    disable(1),
                    enable(2)
                }
            ACCESS  read-write
            STATUS  mandatory
            DESCRIPTION
                " Rx 1 "
            ::= { ttaANDTripOutputEntry 15}

        ttaANDTripOutputRx2  OBJECT-TYPE
            SYNTAX  INTEGER {
                    disable(1),
                    enable(2)
                }
            ACCESS  read-write
            STATUS  mandatory
            DESCRIPTION
                " Rx 2 "
            ::= { ttaANDTripOutputEntry 16}

        ttaANDTripOutputRx3  OBJECT-TYPE
            SYNTAX  INTEGER {
                    disable(1),
                    enable(2)
                }
            ACCESS  read-write
            STATUS  mandatory
            DESCRIPTION
                " Rx 3 "
            ::= { ttaANDTripOutputEntry 17}

        ttaANDTripOutputRx4  OBJECT-TYPE
            SYNTAX  INTEGER {
                    disable(1),
                    enable(2)
                }
            ACCESS  read-write
            STATUS  mandatory
            DESCRIPTION
                " Rx 4 "
            ::= { ttaANDTripOutputEntry 18}

        ttaANDTripOutputRx1Inv  OBJECT-TYPE
            SYNTAX  INTEGER {
                    disable(1),
                    enable(2)
                }
            ACCESS  read-write
            STATUS  mandatory
            DESCRIPTION
                " Rx 1 inverse"
            ::= { ttaANDTripOutputEntry 19}

        ttaANDTripOutputRx2Inv  OBJECT-TYPE
            SYNTAX  INTEGER {
                    disable(1),
                    enable(2)
                }
            ACCESS  read-write
            STATUS  mandatory
            DESCRIPTION
                " Rx 2 inverse"
            ::= { ttaANDTripOutputEntry 20}

        ttaANDTripOutputRx3Inv  OBJECT-TYPE
            SYNTAX  INTEGER {
                    disable(1),
                    enable(2)
                }
            ACCESS  read-write
            STATUS  mandatory
            DESCRIPTION
                " Rx 3 inverse"
            ::= { ttaANDTripOutputEntry 21}

        ttaANDTripOutputRx4Inv  OBJECT-TYPE
            SYNTAX  INTEGER {
                    disable(1),
                    enable(2)
                }
            ACCESS  read-write
            STATUS  mandatory
            DESCRIPTION
                " Rx 4 inverse"
            ::= { ttaANDTripOutputEntry 22}


--
--  Input Delay Min/Max Times Table
--

        ttaInputDelayTable  OBJECT-TYPE
            SYNTAX  SEQUENCE OF TtaInputDelayEntry
            ACCESS  not-accessible
            STATUS  mandatory
            DESCRIPTION
                " The Input Delay Min/Max Times Table "
            ::= { ttaSysConfigTable 11 }

        ttaInputDelayEntry  OBJECT-TYPE
            SYNTAX  TtaInputDelayEntry
            ACCESS  not-accessible
            STATUS  mandatory
            DESCRIPTION
                " An entry in the Input Delay Min/Max Times Table "
            INDEX { ttaInputDelaySlot , ttaInputDelayPort }
            ::= { ttaInputDelayTable 1 }

            TtaInputDelayEntry ::= SEQUENCE {
            ttaInputDelaySlot      LSSlotID,
            ttaInputDelayPort      FourPortID,
            ttaInputDelay1         INTEGER,
            ttaInputDelay2         INTEGER
        }

        ttaInputDelaySlot  OBJECT-TYPE
            SYNTAX  LSSlotID
            ACCESS  read-only
            STATUS  mandatory
            DESCRIPTION
            "TTA slot"
            ::= { ttaInputDelayEntry 1 }

        ttaInputDelayPort  OBJECT-TYPE
            SYNTAX  FourPortID
            ACCESS  read-only
            STATUS  mandatory
            DESCRIPTION
                " Port 1 to 4, Total 4 ports "
            ::= { ttaInputDelayEntry 2 }

        ttaInputDelay1 OBJECT-TYPE
            SYNTAX  INTEGER (0..65535)
            ACCESS  read-write
            STATUS  mandatory
            DESCRIPTION
                " Input Delay 1 (0-65535) "
            ::= { ttaInputDelayEntry 3 }

        ttaInputDelay2 OBJECT-TYPE
            SYNTAX  INTEGER (0..65535)
            ACCESS  read-write
            STATUS  mandatory
            DESCRIPTION
               " Input Delay 2 (0-65535) "
            ::= { ttaInputDelayEntry 4 }


    ttaAlarmTable                  OBJECT IDENTIFIER ::= { tta-card 2 }
--
--Alarm Trap Debounce Time Table
--

--        ttaAlmTrapDbTimeTable         OBJECT-TYPE
--            SYNTAX  SEQUENCE OF TtaAlmTrapDbTimeEntry
--            ACCESS  not-accessible
--            STATUS  mandatory
--            DESCRIPTION
--                " The TTA Alarm Trap Debounce Time Table "
--            ::= { ttaAlarmTable  1 }

--        ttaAlmTrapDbTimeEntry     OBJECT-TYPE
--            SYNTAX  TtaAlmTrapDbTimeEntry
--            ACCESS  not-accessible
--            STATUS  mandatory
--            DESCRIPTION
--                " An entry in the Alarm Trap Debounce Time Table "
--            INDEX  {ttaAlmTrapDbTimeSlotIndex }
--            ::= { ttaAlmTrapDbTimeTable 1 }

--        TtaAlmTrapDbTimeEntry ::= SEQUENCE {
--            ttaAlmTrapDbTimeSlotIndex       LSSlotID,
--            ttaAlmTrapDbTimeAlmTrapDbTime   INTEGER
--        }

--        ttaAlmTrapDbTimeSlotIndex  OBJECT-TYPE
--            SYNTAX  LSSlotID
--            ACCESS  read-only
--            STATUS  mandatory
--            DESCRIPTION
--                "TTA slot"
--            ::= { ttaAlmTrapDbTimeEntry 1 }

--        ttaAlmTrapDbTimeAlmTrapDbTime  OBJECT-TYPE
--            SYNTAX  INTEGER (0..2500)
--            ACCESS  read-write
--            STATUS  mandatory
--            DESCRIPTION
--                " Alarm Trap Debounce Time "
--            ::= { ttaAlmTrapDbTimeEntry 2 }

--
--  Alarm Setup Table
--

        ttaAlarmSetupTable  OBJECT-TYPE
            SYNTAX  SEQUENCE OF TtaAlarmSetupEntry
            ACCESS  not-accessible
            STATUS  mandatory
            DESCRIPTION
                " The TTA Alarm Setup Table "
            ::= { ttaAlarmTable 1 }

        ttaAlarmSetupEntry  OBJECT-TYPE
            SYNTAX  TtaAlarmSetupEntry
            ACCESS  not-accessible
            STATUS  mandatory
            DESCRIPTION
                " An entry in the TTA Alarm Setup Table "
            INDEX { ttaAlarmSlotIndex }
            ::= { ttaAlarmSetupTable 1 }

        TtaAlarmSetupEntry ::= SEQUENCE {
            ttaAlarmSlotIndex           LSSlotID,
            ttaAlarmInputTrigger        LsAlarmSeverity,
            ttaAlarmOutputTrigger       LsAlarmSeverity,
            ttaAlarmRTTimeRange         LsAlarmSeverity,
            ttaAlarmLocalChLost         LsAlarmSeverity,
            ttaAlarmRemoteChLost        LsAlarmSeverity,
            ttaAlarmIrigLoss            LsAlarmSeverity,
            ttaAlarmTestTrigger         LsAlarmSeverity,
            ttaAlarmTestResponse        LsAlarmSeverity
        }

        ttaAlarmSlotIndex  OBJECT-TYPE
            SYNTAX  LSSlotID
            ACCESS  read-only
            STATUS  mandatory
            DESCRIPTION
                "TTA slot"
            ::= { ttaAlarmSetupEntry 1 }

        ttaAlarmInputTrigger  OBJECT-TYPE
            SYNTAX  LsAlarmSeverity
            ACCESS  read-write
            STATUS  mandatory
            DESCRIPTION
                " Alarm is enabled or not "
            ::= { ttaAlarmSetupEntry 2 }

        ttaAlarmOutputTrigger  OBJECT-TYPE
            SYNTAX  LsAlarmSeverity
            ACCESS  read-write
            STATUS  mandatory
            DESCRIPTION
                " Alarm is enabled or not "
            ::= { ttaAlarmSetupEntry 3 }

        ttaAlarmRTTimeRange  OBJECT-TYPE
            SYNTAX  LsAlarmSeverity
            ACCESS  read-write
            STATUS  mandatory
            DESCRIPTION
                " Alarm is enabled or not "
            ::= { ttaAlarmSetupEntry 4 }

        ttaAlarmLocalChLost  OBJECT-TYPE
            SYNTAX  LsAlarmSeverity
            ACCESS  read-write
            STATUS  mandatory
            DESCRIPTION
                " Alarm is enabled or not "
            ::= { ttaAlarmSetupEntry 5 }

        ttaAlarmRemoteChLost  OBJECT-TYPE
            SYNTAX  LsAlarmSeverity
            ACCESS  read-write
            STATUS  mandatory
            DESCRIPTION
                " Alarm is enabled or not "
            ::= { ttaAlarmSetupEntry 6 }

        ttaAlarmIrigLoss  OBJECT-TYPE
            SYNTAX  LsAlarmSeverity
            ACCESS  read-write
            STATUS  mandatory
            DESCRIPTION
                " Alarm is enabled or not "
            ::= { ttaAlarmSetupEntry 7 }

        ttaAlarmTestTrigger  OBJECT-TYPE
            SYNTAX  LsAlarmSeverity
            ACCESS  read-write
            STATUS  mandatory
            DESCRIPTION
                " Alarm is enabled or not "
            ::= { ttaAlarmSetupEntry 8 }

        ttaAlarmTestResponse  OBJECT-TYPE
            SYNTAX  LsAlarmSeverity
            ACCESS  read-write
            STATUS  mandatory
            DESCRIPTION
                " Alarm is enabled or not "
            ::= { ttaAlarmSetupEntry 9 }

--
--  Alarm Queue Table
--

        ttaAlmQueueTable  OBJECT-TYPE
            SYNTAX  SEQUENCE OF TtaAlmQueueEntry
            ACCESS  not-accessible
            STATUS  mandatory
            DESCRIPTION
                " The TTA Alarm Queue Table "
            ::= { ttaAlarmTable 2 }

        ttaAlmQueueEntry  OBJECT-TYPE
            SYNTAX  TtaAlmQueueEntry
            ACCESS  not-accessible
            STATUS  mandatory
            DESCRIPTION
                " An entry in the TTA Alarm Queue Table "
            INDEX { ttaAlmQueueIndex }
            ::= { ttaAlmQueueTable 1 }

        TtaAlmQueueEntry ::= SEQUENCE {
            ttaAlmQueueIndex          INTEGER (1..40),
            ttaAlmQueueString         DisplayString (SIZE(0..255)),
            ttaAlmQueueType           AlarmNum,
            ttaAlmQueueSlot           CardID,
            ttaAlmQueuePort           LsAlarmPort,
            ttaAlmQueueSeverity       LsAlarmSeverityDisp
        }

        ttaAlmQueueIndex  OBJECT-TYPE
            SYNTAX  INTEGER (1..40)
            ACCESS  read-only
            STATUS  mandatory
            DESCRIPTION
                "Select Alarm Queue Index (1-40)"
            ::= { ttaAlmQueueEntry 1 }

        ttaAlmQueueString  OBJECT-TYPE
            SYNTAX  DisplayString (SIZE(0..255))
            ACCESS  read-only
            STATUS  mandatory
            DESCRIPTION
                " Alarm Queue String "
            ::= { ttaAlmQueueEntry 2 }

        ttaAlmQueueType  OBJECT-TYPE
            SYNTAX  AlarmNum
            ACCESS  read-only
            STATUS  mandatory
            DESCRIPTION
                " Alarm type "
            ::= { ttaAlmQueueEntry 3 }

        ttaAlmQueueSlot  OBJECT-TYPE
            SYNTAX  CardID
            ACCESS  read-only
            STATUS  mandatory
            DESCRIPTION
                "Alarm Slot"
            ::= { ttaAlmQueueEntry 4 }

        ttaAlmQueuePort  OBJECT-TYPE
            SYNTAX  LsAlarmPort
            ACCESS  read-only
            STATUS  mandatory
            DESCRIPTION
                "Alarm Port"
            ::= { ttaAlmQueueEntry 5 }

        ttaAlmQueueSeverity  OBJECT-TYPE
            SYNTAX  LsAlarmSeverityDisp
            ACCESS  read-only
            STATUS  mandatory
            DESCRIPTION
                " Alarm Severity "
            ::= { ttaAlmQueueEntry 6 }


    ttaSysStatusTable                  OBJECT IDENTIFIER ::= { tta-card 3 }

--
--Delay Time Table
--

    ttaDelayTimeTable         OBJECT IDENTIFIER ::= { ttaSysStatusTable 1 }

--
--One Way Delay Measurement
--

        ttaOneWayDelayTable         OBJECT-TYPE
            SYNTAX  SEQUENCE OF TtaOneWayDelayEntry
            ACCESS  not-accessible
            STATUS  mandatory
            DESCRIPTION
                " The One Way Delay Measurement Table "
            ::= { ttaDelayTimeTable  1 }

        ttaOneWayDelayEntry     OBJECT-TYPE
            SYNTAX  TtaOneWayDelayEntry
            ACCESS  not-accessible
            STATUS  mandatory
            DESCRIPTION
                " An entry in the One Way Delay Measurement Table "
            INDEX { ttaOneWayDelaySlotIndex , ttaOneWayDelayChIndex }
            ::= { ttaOneWayDelayTable 1 }

        TtaOneWayDelayEntry ::= SEQUENCE {
            ttaOneWayDelaySlotIndex       LSSlotID,
            ttaOneWayDelayChIndex         INTEGER,
            ttaOneWayDelayMax             DisplayString (SIZE(0..255)),
            ttaOneWayDelayMin             DisplayString (SIZE(0..255)),
            ttaOneWayDelayInbound         DisplayString (SIZE(0..255)),
            ttaOneWayDelayOutbound        DisplayString (SIZE(0..255))
        }

        ttaOneWayDelaySlotIndex  OBJECT-TYPE
            SYNTAX  LSSlotID
            ACCESS  read-only
            STATUS  mandatory
            DESCRIPTION
                "TTA slot"
            ::= { ttaOneWayDelayEntry 1 }

        ttaOneWayDelayChIndex  OBJECT-TYPE
            SYNTAX  INTEGER {
                    p1-1(1),
                    p1-2(2),
                    p1-3(3),
                    p2-1(4),
                    p2-2(5),
                    p2-3(6),
                    p3-1(7),
                    p3-2(8),
                    p3-3(9),
                    p4-1(10),
                    p4-2(11),
                    p4-3(12)
                }
            ACCESS  read-only
            STATUS  mandatory
            DESCRIPTION
                " Channel p1-1 to p4-3, Total 12 channels "
            ::= { ttaOneWayDelayEntry 2 }

        ttaOneWayDelayMax  OBJECT-TYPE
            SYNTAX  DisplayString (SIZE(0..255))
            ACCESS  read-only
            STATUS  mandatory
            DESCRIPTION
                " Max (ms) "
            ::= { ttaOneWayDelayEntry 3 }

        ttaOneWayDelayMin  OBJECT-TYPE
            SYNTAX  DisplayString (SIZE(0..255))
            ACCESS  read-only
            STATUS  mandatory
            DESCRIPTION
                " Min (ms) "
            ::= { ttaOneWayDelayEntry 4 }

        ttaOneWayDelayInbound  OBJECT-TYPE
            SYNTAX  DisplayString (SIZE(0..255))
            ACCESS  read-only
            STATUS  mandatory
            DESCRIPTION
                " Inbound (ms) "
            ::= { ttaOneWayDelayEntry 5 }

        ttaOneWayDelayOutbound  OBJECT-TYPE
            SYNTAX  DisplayString (SIZE(0..255))
            ACCESS  read-only
            STATUS  mandatory
            DESCRIPTION
                " Outbound (ms) "
            ::= { ttaOneWayDelayEntry 6 }

--
--R-Trip Delay Measurement
--

        ttaRTripDelayTable         OBJECT-TYPE
            SYNTAX  SEQUENCE OF TtaRTripDelayEntry
            ACCESS  not-accessible
            STATUS  mandatory
            DESCRIPTION
                " The R-Trip Delay Measurement Table "
            ::= { ttaDelayTimeTable 2 }

        ttaRTripDelayEntry     OBJECT-TYPE
            SYNTAX  TtaRTripDelayEntry
            ACCESS  not-accessible
            STATUS  mandatory
            DESCRIPTION
                " An entry in the R-Trip Delay Measurement Table "
            INDEX { ttaRTripDelaySlotIndex , ttaRTripDelayChIndex }
            ::= { ttaRTripDelayTable 1 }

        TtaRTripDelayEntry ::= SEQUENCE {
            ttaRTripDelaySlotIndex       LSSlotID,
            ttaRTripDelayChIndex         INTEGER,
            ttaRTripDelayMax             DisplayString (SIZE(0..255)),
            ttaRTripDelayMin             DisplayString (SIZE(0..255)),
            ttaRTripDelayInbound         DisplayString (SIZE(0..255)),
            ttaRTripDelayOutbound        DisplayString (SIZE(0..255))
        }

        ttaRTripDelaySlotIndex  OBJECT-TYPE
            SYNTAX  LSSlotID
            ACCESS  read-only
            STATUS  mandatory
            DESCRIPTION
                "TTA slot"
            ::= { ttaRTripDelayEntry 1 }

        ttaRTripDelayChIndex  OBJECT-TYPE
            SYNTAX  INTEGER {
                    p1-1(1),
                    p1-2(2),
                    p1-3(3),
                    p2-1(4),
                    p2-2(5),
                    p2-3(6),
                    p3-1(7),
                    p3-2(8),
                    p3-3(9),
                    p4-1(10),
                    p4-2(11),
                    p4-3(12)
                }
            ACCESS  read-only
            STATUS  mandatory
            DESCRIPTION
                " Channel p1-1 to p4-3, Total 12 channels "
            ::= { ttaRTripDelayEntry 2 }

        ttaRTripDelayMax  OBJECT-TYPE
            SYNTAX  DisplayString (SIZE(0..255))
            ACCESS  read-only
            STATUS  mandatory
            DESCRIPTION
                " Max (ms) "
            ::= { ttaRTripDelayEntry 3 }

        ttaRTripDelayMin  OBJECT-TYPE
            SYNTAX  DisplayString (SIZE(0..255))
            ACCESS  read-only
            STATUS  mandatory
            DESCRIPTION
                " Min (ms) "
            ::= { ttaRTripDelayEntry 4 }

        ttaRTripDelayInbound  OBJECT-TYPE
            SYNTAX  DisplayString (SIZE(0..255))
            ACCESS  read-only
            STATUS  mandatory
            DESCRIPTION
                " Inbound (ms) "
            ::= { ttaRTripDelayEntry 5 }

        ttaRTripDelayOutbound  OBJECT-TYPE
            SYNTAX  DisplayString (SIZE(0..255))
            ACCESS  read-only
            STATUS  mandatory
            DESCRIPTION
                " Outbound (ms) "
            ::= { ttaRTripDelayEntry 6 }

--
--Transfer Trip Status Table
--

        ttaTrTripStaTable         OBJECT-TYPE
            SYNTAX  SEQUENCE OF TtaTrTripStaEntry
            ACCESS  not-accessible
            STATUS  mandatory
            DESCRIPTION
                " The Transfer Trip Status Table "
            ::= { ttaSysStatusTable  2 }

        ttaTrTripStaEntry     OBJECT-TYPE
            SYNTAX  TtaTrTripStaEntry
            ACCESS  not-accessible
            STATUS  mandatory
            DESCRIPTION
                " An entry in the Transfer Trip Status Table "
            INDEX { ttaTrTripStaSlotIndex , ttaTrTripStaPortIndex }
            ::= { ttaTrTripStaTable 1 }

        TtaTrTripStaEntry ::= SEQUENCE {
            ttaTrTripStaSlotIndex       LSSlotID,
            ttaTrTripStaPortIndex       FourPortID,
            ttaTrTripStaInput           INTEGER,
            ttaTrTripStaOutput          INTEGER
        }

        ttaTrTripStaSlotIndex  OBJECT-TYPE
            SYNTAX  LSSlotID
            ACCESS  read-only
            STATUS  mandatory
            DESCRIPTION
                "TTA slot"
            ::= { ttaTrTripStaEntry 1 }

        ttaTrTripStaPortIndex  OBJECT-TYPE
            SYNTAX  FourPortID
            ACCESS  read-only
            STATUS  mandatory
            DESCRIPTION
                " Port 1 to 4, Total 4 ports "
            ::= { ttaTrTripStaEntry 2 }

        ttaTrTripStaInput  OBJECT-TYPE
            SYNTAX  INTEGER{
                    offOpen(1),
                    onClose(2)
                }
            ACCESS  read-only
            STATUS  mandatory
            DESCRIPTION
                " Input "
            ::= { ttaTrTripStaEntry 3 }

        ttaTrTripStaOutput  OBJECT-TYPE
            SYNTAX  INTEGER{
                    offOpen(1),
                    onClose(2)
                }
            ACCESS  read-only
            STATUS  mandatory
            DESCRIPTION
                " Output "
            ::= { ttaTrTripStaEntry 4 }

--
--Remote Alarm Indication Table
--

        ttaReAlarmIndTable         OBJECT-TYPE
            SYNTAX  SEQUENCE OF TtaReAlarmIndEntry
            ACCESS  not-accessible
            STATUS  mandatory
            DESCRIPTION
                " The Remote Alarm Indication Table "
            ::= { ttaSysStatusTable  3 }

        ttaReAlarmIndEntry     OBJECT-TYPE
            SYNTAX  TtaReAlarmIndEntry
            ACCESS  not-accessible
            STATUS  mandatory
            DESCRIPTION
                " An entry in the Remote Alarm Indication Table "
            INDEX { ttaReAlarmIndSlotIndex , ttaReAlarmIndChIndex }
            ::= { ttaReAlarmIndTable 1 }

        TtaReAlarmIndEntry ::= SEQUENCE {
            ttaReAlarmIndSlotIndex       LSSlotID,
            ttaReAlarmIndChIndex         INTEGER,
            ttaReAlarmIndStatus          INTEGER
        }

        ttaReAlarmIndSlotIndex  OBJECT-TYPE
            SYNTAX  LSSlotID
            ACCESS  read-only
            STATUS  mandatory
            DESCRIPTION
                "TTA slot"
            ::= { ttaReAlarmIndEntry 1 }

        ttaReAlarmIndChIndex  OBJECT-TYPE
            SYNTAX  INTEGER {
                    p1-1(1),
                    p1-2(2),
                    p1-3(3),
                    p2-1(4),
                    p2-2(5),
                    p2-3(6),
                    p3-1(7),
                    p3-2(8),
                    p3-3(9),
                    p4-1(10),
                    p4-2(11),
                    p4-3(12)
                }
            ACCESS  read-only
            STATUS  mandatory
            DESCRIPTION
                " Channel p1-1 to p4-3, Total 12 channels "
            ::= { ttaReAlarmIndEntry 2 }

        ttaReAlarmIndStatus  OBJECT-TYPE
            SYNTAX  INTEGER{
                    no(1),
                    yes(2),
                    na(3)
                }
            ACCESS  read-only
            STATUS  mandatory
            DESCRIPTION
                " Status "
            ::= { ttaReAlarmIndEntry 3 }

--
--  IRIG Status Table
--

        ttaIrigStatusTable  OBJECT-TYPE
            SYNTAX  SEQUENCE OF TtaIrigStatusEntry
            ACCESS  not-accessible
            STATUS  mandatory
            DESCRIPTION
                " The TTA IRIG Status Table "
            ::= { ttaSysStatusTable 4 }

        ttaIrigStatusEntry  OBJECT-TYPE
            SYNTAX  TtaIrigStatusEntry
            ACCESS  not-accessible
            STATUS  mandatory
            DESCRIPTION
                " An entry in the TTA IRIG Status Table "
            INDEX { ttaIrigSlotIndex }
            ::= { ttaIrigStatusTable 1 }

        TtaIrigStatusEntry ::= SEQUENCE {
            ttaIrigSlotIndex           LSSlotID,
            ttaIrigSyncUnsync          INTEGER,
            ttaIrigIrigTime            DisplayString (SIZE(0..255))
        }

        ttaIrigSlotIndex  OBJECT-TYPE
            SYNTAX  LSSlotID
            ACCESS  read-only
            STATUS  mandatory
            DESCRIPTION
                "TTA slot"
            ::= { ttaIrigStatusEntry 1 }

        ttaIrigSyncUnsync  OBJECT-TYPE
            SYNTAX  INTEGER{
                    unsync(1),
                    sync(2)
                }
            ACCESS  read-only
            STATUS  mandatory
            DESCRIPTION
                " IRIG is Sync or not "
            ::= { ttaIrigStatusEntry 2 }

        ttaIrigIrigTime  OBJECT-TYPE
            SYNTAX  DisplayString (SIZE(0..255))
            ACCESS  read-only
            STATUS  mandatory
            DESCRIPTION
                " IRIG Time "
            ::= { ttaIrigStatusEntry 3 }

--
--Channel Status Table
--

        ttaChStatusTable         OBJECT-TYPE
            SYNTAX  SEQUENCE OF TtaChStatusEntry
            ACCESS  not-accessible
            STATUS  mandatory
            DESCRIPTION
                " The Channel Status Table "
            ::= { ttaSysStatusTable  5 }

        ttaChStatusEntry     OBJECT-TYPE
            SYNTAX  TtaChStatusEntry
            ACCESS  not-accessible
            STATUS  mandatory
            DESCRIPTION
                " An entry in the Channel Status Table "
            INDEX { ttaChStatusSlotIndex , ttaChStatusChIndex }
            ::= { ttaChStatusTable 1 }

        TtaChStatusEntry ::= SEQUENCE {
            ttaChStatusSlotIndex       LSSlotID,
            ttaChStatusChIndex         INTEGER,
            ttaChStatusPickUpCnt       INTEGER,
            ttaChStatusCrcErrCnt       INTEGER,
            ttaChStatusIdStatus        INTEGER
        }

        ttaChStatusSlotIndex  OBJECT-TYPE
            SYNTAX  LSSlotID
            ACCESS  read-only
            STATUS  mandatory
            DESCRIPTION
                "TTA slot"
            ::= { ttaChStatusEntry 1 }

        ttaChStatusChIndex  OBJECT-TYPE
            SYNTAX  INTEGER {
                    p1-1(1),
                    p1-2(2),
                    p1-3(3),
                    p2-1(4),
                    p2-2(5),
                    p2-3(6),
                    p3-1(7),
                    p3-2(8),
                    p3-3(9),
                    p4-1(10),
                    p4-2(11),
                    p4-3(12)
                }
            ACCESS  read-only
            STATUS  mandatory
            DESCRIPTION
                " Channel p1-1 to p4-3, Total 12 channels "
            ::= { ttaChStatusEntry 2 }

        ttaChStatusPickUpCnt  OBJECT-TYPE
            SYNTAX  INTEGER{
                    na(256)
                }
            ACCESS  read-only
            STATUS  mandatory
            DESCRIPTION
                " Pick Up Cnt. "
            ::= { ttaChStatusEntry 3 }

        ttaChStatusCrcErrCnt  OBJECT-TYPE
            SYNTAX  INTEGER{
                    na(256)
                }
            ACCESS  read-only
            STATUS  mandatory
            DESCRIPTION
                " CRC Error Cnt. "
            ::= { ttaChStatusEntry 4 }

        ttaChStatusIdStatus  OBJECT-TYPE
            SYNTAX  INTEGER{
                    match(1),
                    mismatch(2),
                    na(3)
                }
            ACCESS  read-only
            STATUS  mandatory
            DESCRIPTION
                " ID Status "
            ::= { ttaChStatusEntry 5 }

--
--  Round Trip Test Results Table
--

        ttaRTTestResultTable  OBJECT-TYPE
            SYNTAX  SEQUENCE OF TtaRTTestResultEntry
            ACCESS  not-accessible
            STATUS  mandatory
            DESCRIPTION
                " The TTA Round Trip Test Results Table "
            ::= { tta-card 4 }

        ttaRTTestResultEntry  OBJECT-TYPE
            SYNTAX  TtaRTTestResultEntry
            ACCESS  not-accessible
            STATUS  mandatory
            DESCRIPTION
                " An entry in the TTA Round Trip Test Results Table "
            INDEX { ttaTestSlotIndex , ttaTestChIndex }
            ::= { ttaRTTestResultTable 1 }

        TtaRTTestResultEntry ::= SEQUENCE {
            ttaTestSlotIndex           LSSlotID,
            ttaTestChIndex             INTEGER,
            ttaTestTriggerTime         DisplayString (SIZE(0..255)),
            ttaTestResponseTime        DisplayString (SIZE(0..255)),
            ttaTestRTrip               DisplayString (SIZE(0..255))
        }

        ttaTestSlotIndex  OBJECT-TYPE
            SYNTAX  LSSlotID
            ACCESS  read-only
            STATUS  mandatory
            DESCRIPTION
                "TTA slot"
            ::= { ttaRTTestResultEntry 1 }

        ttaTestChIndex  OBJECT-TYPE
            SYNTAX  INTEGER {
                    p1-1(1),
                    p1-2(2),
                    p1-3(3),
                    p2-1(4),
                    p2-2(5),
                    p2-3(6),
                    p3-1(7),
                    p3-2(8),
                    p3-3(9),
                    p4-1(10),
                    p4-2(11),
                    p4-3(12)
                }
            ACCESS  read-only
            STATUS  mandatory
            DESCRIPTION
                " Channel p1-1 to p4-3, Total 12 channels "
            ::= { ttaRTTestResultEntry 2 }

        ttaTestTriggerTime  OBJECT-TYPE
            SYNTAX  DisplayString (SIZE(0..255))
            ACCESS  read-only
            STATUS  mandatory
            DESCRIPTION
                " Trigger Time Stamp "
            ::= { ttaRTTestResultEntry 3 }

        ttaTestResponseTime  OBJECT-TYPE
            SYNTAX  DisplayString (SIZE(0..255))
            ACCESS  read-only
            STATUS  mandatory
            DESCRIPTION
                " Response Time Stamp "
            ::= { ttaRTTestResultEntry 4 }

        ttaTestRTrip  OBJECT-TYPE
            SYNTAX  DisplayString (SIZE(0..255))
            ACCESS  read-only
            STATUS  mandatory
            DESCRIPTION
                " R-Trip (ms) "
            ::= { ttaRTTestResultEntry 5 }

--
--PCM Rx Address Table
--

--        ttaPCMRxAddTable         OBJECT-TYPE
--            SYNTAX  SEQUENCE OF TtaPCMRxAddEntry
--            ACCESS  not-accessible
--            STATUS  mandatory
--            DESCRIPTION
--                " The PCM Rx Address Table "
--            ::= { ttaSysStatusTable  6 }

--        ttaPCMRxAddEntry     OBJECT-TYPE
--            SYNTAX  TtaPCMRxAddEntry
--            ACCESS  not-accessible
--            STATUS  mandatory
--            DESCRIPTION
--                " An entry in the PCM Rx Address Table "
--            INDEX  {ttaPCMRxAddSlotIndex, ttaPCMRxAddChanIndex }
--            ::= { ttaPCMRxAddTable 1 }

--        TtaPCMRxAddEntry ::= SEQUENCE {
--            ttaPCMRxAddSlotIndex       LSSlotID,
--            ttaPCMRxAddChanIndex       INTEGER,
--            ttaPCMRxAddAddress         INTEGER
--        }

--        ttaPCMRxAddSlotIndex  OBJECT-TYPE
--            SYNTAX  LSSlotID
--            ACCESS  read-only
--            STATUS  mandatory
--            DESCRIPTION
--                "TTA slot"
--            ::= { ttaPCMRxAddEntry 1 }

--        ttaPCMRxAddChanIndex  OBJECT-TYPE
--            SYNTAX  INTEGER {
--                    channel1(1),
--                    channel2(2),
--                    channel3(3),
--                    channel4(4),
--                    channel5(5),
--                    channel6(6),
--                    channel7(7),
--                    channel8(8),
--                    channel9(9),
--                    channel10(10),
--                    channel11(11),
--                    channel12(12)
--                }
--            ACCESS  read-only
--            STATUS  mandatory
--            DESCRIPTION
--                " Channel 1 to 12, Total 12 channels "
--            ::= { ttaPCMRxAddEntry 2 }

--        ttaPCMRxAddAddress  OBJECT-TYPE
--            SYNTAX  INTEGER
--            ACCESS  read-only
--            STATUS  mandatory
--            DESCRIPTION
--                " PCM Rx Address "
--            ::= { ttaPCMRxAddEntry 3 }


--
-- Card Control Table
--

        ttaCardControlTable  OBJECT-TYPE
            SYNTAX  SEQUENCE OF TtaCardControlEntry
            ACCESS  not-accessible
            STATUS  mandatory
            DESCRIPTION
                " The TTA Card Control Table "
            ::= { tta-card 5 }

        ttaCardControlEntry  OBJECT-TYPE
            SYNTAX  TtaCardControlEntry
            ACCESS  not-accessible
            STATUS  mandatory
            DESCRIPTION
                " An entry in the TTA Card Control Table "
            INDEX { ttaCardIndex }
            ::= { ttaCardControlTable 1 }

        TtaCardControlEntry ::= SEQUENCE {
            ttaCardIndex                LSSlotID,
            ttaReset                    INTEGER,
            ttaLoadDefault              INTEGER
        }

        ttaCardIndex  OBJECT-TYPE
            SYNTAX  LSSlotID
            ACCESS  read-only
            STATUS  mandatory
            DESCRIPTION
                "TTA slot"
            ::= { ttaCardControlEntry 1 }

        ttaReset  OBJECT-TYPE
            SYNTAX  INTEGER {
                    na(1),
                    reset(2)
                }
            ACCESS  read-write
            STATUS  mandatory
            DESCRIPTION
                " Reset TTA card "
            ::= { ttaCardControlEntry 2 }

        ttaLoadDefault  OBJECT-TYPE
            SYNTAX  INTEGER {
                    na(1),
                    default(2)
                }
            ACCESS  read-write
            STATUS  mandatory
            DESCRIPTION
                " Load default "
            ::= { ttaCardControlEntry 3 }


--
--  TTA System Information Table
--

        ttaSystemInfoTable  OBJECT-TYPE
            SYNTAX  SEQUENCE OF TtaSystemInfoEntry
            ACCESS  not-accessible
            STATUS  mandatory
            DESCRIPTION
                " The TTA System Information Table "
            ::= { tta-card 6 }

        ttaSystemInfoEntry  OBJECT-TYPE
            SYNTAX  TtaSystemInfoEntry
            ACCESS  not-accessible
            STATUS  mandatory
            DESCRIPTION
                " An entry in the TTA System Information Table "
            INDEX { ttaSystemInfoSlotIndex }
            ::= { ttaSystemInfoTable 1 }

        TtaSystemInfoEntry ::= SEQUENCE {
            ttaSystemInfoSlotIndex              LSSlotID,
            ttaSystemInfoPROMVersion            DisplayString,
            ttaSystemInfoHardwareVersion        DisplayString,
            ttaSystemInfoFpgaVersion            DisplayString,
            ttaSystemInfoBank1Version           DisplayString,
            ttaSystemInfoBank2Version           DisplayString,
            ttaSystemInfoActiveBank             INTEGER
        }

        ttaSystemInfoSlotIndex  OBJECT-TYPE
            SYNTAX  LSSlotID
            ACCESS  read-only
            STATUS  mandatory
            DESCRIPTION
                "TTA slot"
            ::= { ttaSystemInfoEntry 1 }

        ttaSystemInfoPROMVersion  OBJECT-TYPE
            SYNTAX  DisplayString (SIZE (0..30) )
            ACCESS  read-only
            STATUS  mandatory
            DESCRIPTION
                " TTA PROM Version "
            ::= { ttaSystemInfoEntry 2 }

        ttaSystemInfoHardwareVersion  OBJECT-TYPE
            SYNTAX  DisplayString (SIZE (0..30) )
            ACCESS  read-only
            STATUS  mandatory
            DESCRIPTION
                " TTA Hardware Version "
            ::= { ttaSystemInfoEntry 3 }

        ttaSystemInfoFpgaVersion  OBJECT-TYPE
            SYNTAX  DisplayString (SIZE (0..30))
            ACCESS  read-only
            STATUS  mandatory
            DESCRIPTION
                " FPGA Version "
            ::= { ttaSystemInfoEntry 4 }

        ttaSystemInfoBank1Version    OBJECT-TYPE
            SYNTAX  DisplayString (SIZE (0..30))
            ACCESS  read-only
            STATUS  mandatory
            DESCRIPTION
                " Bank-1 Version "
            ::= { ttaSystemInfoEntry 5 }

        ttaSystemInfoBank2Version    OBJECT-TYPE
            SYNTAX  DisplayString (SIZE (0..30))
            ACCESS  read-only
            STATUS  mandatory
            DESCRIPTION
                " Bank-2 Version "
            ::= { ttaSystemInfoEntry 6}

        ttaSystemInfoActiveBank    OBJECT-TYPE
            SYNTAX  INTEGER{
                    bank-1(1),
                    bank-2(2)
                }
            ACCESS  read-only
            STATUS  mandatory
            DESCRIPTION
                " Active Bank 1/2 "
            ::= { ttaSystemInfoEntry 7 }

        ttaTotalCard   OBJECT-TYPE
            SYNTAX  INTEGER
            ACCESS  read-only
            STATUS  mandatory
            DESCRIPTION
                "Total cards of TTA"
            ::= { tta-card 100 }


--======================================================================--
--======================================================================--
--  dte6-card MIB
--======================================================================--
--======================================================================--

--
-- DTE6 Mode Table
--

        dte6ModeTable  OBJECT-TYPE
            SYNTAX  SEQUENCE OF Dte6ModeEntry
            ACCESS  not-accessible
            STATUS  mandatory
            DESCRIPTION
                ""
            ::= { dte6-card 1 }

        dte6ModeEntry  OBJECT-TYPE
            SYNTAX  Dte6ModeEntry
            ACCESS  not-accessible
            STATUS  mandatory
            DESCRIPTION
                ""
            INDEX { dte6ModeSlotIndex }
            ::= { dte6ModeTable 1 }

        Dte6ModeEntry ::= SEQUENCE {
            dte6ModeSlotIndex     LSSlotID,
            dte6ModeCardMode      INTEGER
        }

        dte6ModeSlotIndex  OBJECT-TYPE
            SYNTAX  LSSlotID
            ACCESS  read-only
            STATUS  mandatory
            DESCRIPTION
                "DTE6 slot index"
            ::= { dte6ModeEntry 1 }

        dte6ModeCardMode  OBJECT-TYPE
            SYNTAX  INTEGER {
                    m1(1),
                    m2(2),
                    m3(3)
                }
            ACCESS  read-write
            STATUS  mandatory
            DESCRIPTION
                "DTE6 Card Mode"
            ::= { dte6ModeEntry 2 }


--
--  DTE6 Configuration
--

        dte6ConfigTable  OBJECT-TYPE
            SYNTAX  SEQUENCE OF Dte6ConfigEntry
            ACCESS  not-accessible
            STATUS  mandatory
            DESCRIPTION
                "The DTE6 Interface Configuration table."
            ::= { dte6-card 2 }

        dte6ConfigEntry  OBJECT-TYPE
            SYNTAX  Dte6ConfigEntry
            ACCESS  not-accessible
            STATUS  mandatory
            DESCRIPTION
                "An entry in the DTE6 Configuration table."
            INDEX { dte6CfgSlotIndex , dte6CfgPortIndex }
            ::= { dte6ConfigTable 1 }

        Dte6ConfigEntry ::= SEQUENCE {
            dte6CfgSlotIndex                LSSlotID,
            dte6CfgPortIndex                SixPortID,
            dte6CfgInterface                INTEGER,
            dte6CfgMux                      INTEGER,
            dte6CfgSyncMode                 INTEGER,
            dte6CfgRate                     INTEGER,
            dte6CfgBitPosition              INTEGER,
            dte6CfgClockPolarity            INTEGER,
            dte6CfgDataPolarity             INTEGER,
            dte6CfgRTS                      INTEGER,
            dte6CfgTTM                      INTEGER,
            dte6CfgBitPosition0Used         INTEGER,
            dte6CfgBitPosition1Used         INTEGER,
            dte6CfgBitPosition2Used         INTEGER,
            dte6CfgBitPosition3Used         INTEGER,
            dte6CfgBitPosition4Used         INTEGER,
            dte6CfgBitPosition5Used         INTEGER,
            dte6CfgBitPosition6Used         INTEGER,
            dte6CfgBitPosition7Used         INTEGER,
            dte6CfgWarrning                 DisplayString
        }

        dte6CfgSlotIndex  OBJECT-TYPE
            SYNTAX  LSSlotID
            ACCESS  read-only
            STATUS  mandatory
            DESCRIPTION
                "DTE6 slot index"
            ::= { dte6ConfigEntry 1 }

        dte6CfgPortIndex  OBJECT-TYPE
            SYNTAX  SixPortID
            ACCESS  read-only
            STATUS  mandatory
            DESCRIPTION
                "Port 1 to 6, Total 6 ports"
            ::= { dte6ConfigEntry 2 }

        dte6CfgInterface  OBJECT-TYPE
            SYNTAX  INTEGER {
                    rs232(1),
                    rs422(2),
                    x21(3)
                }
            ACCESS  read-write
            STATUS  mandatory
            DESCRIPTION
                "DTE6 Interface mode"
            ::= { dte6ConfigEntry 3 }

        dte6CfgMux  OBJECT-TYPE
            SYNTAX  INTEGER {
                    nonMux(1),
                    mux(2)
                }
            ACCESS  read-write
            STATUS  mandatory
            DESCRIPTION
                "DTE6 MUX mode"
            ::= { dte6ConfigEntry 4 }


        dte6CfgSyncMode  OBJECT-TYPE
            SYNTAX  INTEGER {
                    async8(1),
                    async9(2),
                    async10(3),
                    async11(4),
                    async12(5),
                    sync(6)
                }
            ACCESS  read-write
            STATUS  mandatory
            DESCRIPTION
                "DTE6 Sync mode"
            ::= { dte6ConfigEntry 5 }

        dte6CfgRate  OBJECT-TYPE
            SYNTAX  INTEGER {
                    r0-6K(1),
                    r1-2K(2),
                    r2-4K(3),
                    r4-8K(4),
                    r9-6K(5),
                    r19-2K(6),
                    r38-4K(7),
                    r48K(8),
                    r64K(9)
                }
            ACCESS  read-write
            STATUS  mandatory
            DESCRIPTION
                "DTE6 Base Rate"
            ::= { dte6ConfigEntry 6 }

        dte6CfgBitPosition  OBJECT-TYPE
            SYNTAX  INTEGER {
                    position-0(1),
                    position-1(2),
                    position-2(3),
                    position-3(4),
                    position-4(5),
                    position-5(6),
                    position-6(7),
                    position-7(8)
                }
            ACCESS  read-write
            STATUS  mandatory
            DESCRIPTION
                "DTE6 Bit position"
            ::= { dte6ConfigEntry 7 }

        dte6CfgClockPolarity  OBJECT-TYPE
            SYNTAX  INTEGER {
                    clockNormal(1),
                    clockInverted(2),
                    na(3)
                }
            ACCESS  read-write
            STATUS  mandatory
            DESCRIPTION
                "DTE6 Clock Polarity"
            ::= { dte6ConfigEntry 8 }

        dte6CfgDataPolarity  OBJECT-TYPE
            SYNTAX  INTEGER {
                    dataNormal(1),
                    dataInverted(2),
                    na(3)
                }
            ACCESS  read-write
            STATUS  mandatory
            DESCRIPTION
                "DTE6 Data Polarity"
            ::= { dte6ConfigEntry 9 }

        dte6CfgRTS  OBJECT-TYPE
            SYNTAX  INTEGER {
                    rtsActive(1),
                    rtsPermanent(2)
                }
            ACCESS  read-write
            STATUS  mandatory
            DESCRIPTION
                "DTE6 RTS Mode"
            ::= {  dte6ConfigEntry 10 }

        dte6CfgTTM  OBJECT-TYPE
            SYNTAX  INTEGER {
                    ttmOff(1),
                    ttmOn(2),
                    na(3)
                }
            ACCESS  read-write
            STATUS  mandatory
            DESCRIPTION
                "DTE6 TTM Mode"
            ::= { dte6ConfigEntry 11 }

        dte6CfgBitPosition0Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "DTE6 Bits 0 Stream Position Used"
            ::= { dte6ConfigEntry 12 }

        dte6CfgBitPosition1Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "DTE6 Bits 1 Stream Position Used"
            ::= { dte6ConfigEntry 13 }

        dte6CfgBitPosition2Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "DTE6 Bits 2 Stream Position Used"
            ::= { dte6ConfigEntry 14 }

        dte6CfgBitPosition3Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "DTE6 Bits 3 Stream Position Used"
            ::= { dte6ConfigEntry 15 }

        dte6CfgBitPosition4Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "DTE6 Bits 4 Stream Position Used"
            ::= { dte6ConfigEntry 16 }

        dte6CfgBitPosition5Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "DTE6 Bits 5 Stream Position Used"
            ::= { dte6ConfigEntry 17 }

        dte6CfgBitPosition6Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "DTE6 Bits 6 Stream Position Used"
            ::= { dte6ConfigEntry 18 }

        dte6CfgBitPosition7Used  OBJECT-TYPE
            SYNTAX  INTEGER {
                    unused(1),
                    port1(2),
                    port2(3),
                    port3(4),
                    port4(5),
                    port5(6),
                    port6(7),
                    port7(8),
                    port8(9)
                }
            ACCESS  read-only
            STATUS  mandatory
            DESCRIPTION
                "DTE6 Bits 7 Stream Position Used"
            ::= { dte6ConfigEntry 19 }

        dte6CfgWarrning  OBJECT-TYPE
            SYNTAX  DisplayString (SIZE (0..70) )
            ACCESS  read-only
            STATUS  mandatory
            DESCRIPTION
                "DTE6 map setup warning"
            ::= { dte6ConfigEntry 20 }


--
--  DTE6 Status
--

        dte6StatusTable  OBJECT-TYPE
            SYNTAX  SEQUENCE OF Dte6StatusEntry
            ACCESS  not-accessible
            STATUS  mandatory
            DESCRIPTION
                "The DTE6 Status table."
            ::= { dte6-card 3}

        dte6StatusEntry  OBJECT-TYPE
            SYNTAX  Dte6StatusEntry
            ACCESS  not-accessible
            STATUS  mandatory
            DESCRIPTION
                "An entry in the DTE6 Status table."
            INDEX { dte6StatusSlotIndex , dte6StatusPortIndex }
            ::= { dte6StatusTable 1 }

        Dte6StatusEntry ::= SEQUENCE {
            dte6StatusSlotIndex         LSSlotID,
            dte6StatusPortIndex         SixPortID,
            dte6StatusS1                INTEGER,
            dte6StatusS3                INTEGER,
            dte6StatusS4                INTEGER,
            dte6StatusS6                INTEGER,
            dte6StatusS8                INTEGER,
            dte6StatusS9                INTEGER,
            dte6StatusE4                INTEGER,
            dte6StatusE5                INTEGER,
            dte6StatusE6                INTEGER,
            dte6StatusX                 INTEGER,
            dte6StatusDteCTS            INTEGER,
            dte6StatusDteDCD            INTEGER,
            dte6StatusRTSloss           INTEGER,
            dte6StatusEXTCLKloss        INTEGER,
            dte6StatusDSRstatus         INTEGER,
            dte6StatusCTSstatus         INTEGER,
            dte6StatusDCDstatus         INTEGER,
            dte6StatusDTRstatus         INTEGER,
            dte6StatusRTSstatus         INTEGER,
            dte6StatusRemoteAlarm       INTEGER,
            dte6StatusFrameSync         INTEGER,
            dte6StatusRemoteS1          INTEGER,
            dte6StatusRemoteS3          INTEGER,
            dte6StatusRemoteS4          INTEGER,
            dte6StatusRemoteS6          INTEGER,
            dte6StatusRemoteS8          INTEGER,
            dte6StatusRemoteS9          INTEGER,
            dte6StatusRemoteE4          INTEGER,
            dte6StatusRemoteE5          INTEGER,
            dte6StatusRemoteE6          INTEGER,
            dte6StatusRemoteX           INTEGER
        }

        dte6StatusSlotIndex  OBJECT-TYPE
            SYNTAX  LSSlotID
            ACCESS  read-only
            STATUS  mandatory
            DESCRIPTION
                "DTE6 slot index"
            ::= { dte6StatusEntry 1 }

        dte6StatusPortIndex  OBJECT-TYPE
            SYNTAX  SixPortID
            ACCESS  read-only
            STATUS  mandatory
            DESCRIPTION
                "Port 1 to 6, Total 6 ports"
            ::= { dte6StatusEntry 2 }

        dte6StatusS1  OBJECT-TYPE
            SYNTAX  INTEGER {
                    off(1),
                    on(2),
                    rts(3),
                    dtr(4),
                    dsr(5),
                    na(14)
                }
            ACCESS  read-write
            STATUS  mandatory
            DESCRIPTION
                "DTE6 Status bit S1"
            ::= { dte6StatusEntry 3 }

        dte6StatusS3  OBJECT-TYPE
            SYNTAX  INTEGER {
                    off(1),
                    on(2),
                    rts(3),
                    dtr(4),
                    dsr(5),
                    na(14)
                }
            ACCESS  read-write
            STATUS  mandatory
            DESCRIPTION
                "DTE6 Status bit S3"
            ::= { dte6StatusEntry 4 }

        dte6StatusS4  OBJECT-TYPE
            SYNTAX  INTEGER {
                    off(1),
                    on(2),
                    rts(3),
                    dtr(4),
                    dsr(5),
                    na(14)
                }
            ACCESS  read-write
            STATUS  mandatory
            DESCRIPTION
                "DTE6 Status bit S4"
            ::= { dte6StatusEntry 5 }

        dte6StatusS6  OBJECT-TYPE
            SYNTAX  INTEGER {
                    off(1),
                    on(2),
                    rts(3),
                    dtr(4),
                    dsr(5),
                    na(14)
                }
            ACCESS  read-write
            STATUS  mandatory
            DESCRIPTION
                "DTE6 Status bit S6"
            ::= { dte6StatusEntry 6 }

        dte6StatusS8  OBJECT-TYPE
            SYNTAX  INTEGER {
                    off(1),
                    on(2),
                    rts(3),
                    dtr(4),
                    dsr(5),
                    na(14)
                }
            ACCESS  read-write
            STATUS  mandatory
            DESCRIPTION
                "DTE6 Status bit S8"
            ::= { dte6StatusEntry 7 }

        dte6StatusS9  OBJECT-TYPE
            SYNTAX  INTEGER {
                    off(1),
                    on(2),
                    rts(3),
                    dtr(4),
                    dsr(5),
                    na(14)
                }
            ACCESS  read-write
            STATUS  mandatory
            DESCRIPTION
                "DTE6 Status bit S9"
            ::= { dte6StatusEntry 8 }

        dte6StatusE4  OBJECT-TYPE
            SYNTAX  INTEGER {
                    off(1),
                    on(2),
                    na(14)
                }
            ACCESS  read-write
            STATUS  mandatory
            DESCRIPTION
                "DTE6 Status bit E4"
            ::= { dte6StatusEntry 9 }

        dte6StatusE5  OBJECT-TYPE
            SYNTAX  INTEGER {
                    off(1),
                    on(2),
                    na(14)
                }
            ACCESS  read-write
            STATUS  mandatory
            DESCRIPTION
                "DTE6 Status bit E5"
            ::= { dte6StatusEntry 10 }

        dte6StatusE6  OBJECT-TYPE
            SYNTAX  INTEGER {
                    off(1),
                    on(2),
                    na(14)
                }
            ACCESS  read-write
            STATUS  mandatory
            DESCRIPTION
                "DTE6 Status bit E6"
            ::= { dte6StatusEntry 11 }

        dte6StatusX  OBJECT-TYPE
            SYNTAX  INTEGER {
                    off(1),
                    on(2),
                    rtswithFrameSYNC(12),
                    frameSYNC(13),
                    na(14)
                }
            ACCESS  read-write
            STATUS  mandatory
            DESCRIPTION
                "DTE6 Status bit X"
            ::= { dte6StatusEntry 12 }

        dte6StatusDteCTS  OBJECT-TYPE
            SYNTAX  INTEGER {
                    off(1),
                    on(2),
                    rts(3),
                    remote-S1(6),
                    remote-S3(7),
                    remote-S4(8),
                    remote-S6(9),
                    remote-S8(10),
                    remote-S9(11),
                    na(14)
                }
            ACCESS  read-write
            STATUS  mandatory
            DESCRIPTION
                "DTE6 Status bit DTE CTS"
            ::= { dte6StatusEntry 13 }

        dte6StatusDteDCD  OBJECT-TYPE
            SYNTAX  INTEGER {
                    off(1),
                    on(2),
                    rts(3),
                    remote-S1(6),
                    remote-S3(7),
                    remote-S4(8),
                    remote-S6(9),
                    remote-S8(10),
                    remote-S9(11)
                }
            ACCESS  read-write
            STATUS  mandatory
            DESCRIPTION
                "DTE6 Status bit DTE DCD"
            ::= { dte6StatusEntry 14 }

        dte6StatusRTSloss  OBJECT-TYPE
            SYNTAX  INTEGER {
                    no(1),
                    yes(2),
                    na(3)
                }
            ACCESS  read-only
            STATUS  mandatory
            DESCRIPTION
                "DTE6 RTS loss"
            ::= { dte6StatusEntry 15 }

        dte6StatusEXTCLKloss  OBJECT-TYPE
            SYNTAX  INTEGER {
                    no(1),
                    yes(2),
                    na(3)
                }
            ACCESS  read-only
            STATUS  mandatory
            DESCRIPTION
                "DTE6 EXT-CLK loss"
            ::= { dte6StatusEntry 16 }

        dte6StatusDSRstatus  OBJECT-TYPE
            SYNTAX  INTEGER {
                    no(1),
                    yes(2),
                    na(3)
                }
            ACCESS  read-only
            STATUS  mandatory
            DESCRIPTION
                "DTE6 DSR"
            ::= { dte6StatusEntry 17 }

        dte6StatusCTSstatus  OBJECT-TYPE
            SYNTAX  INTEGER {
                    no(1),
                    yes(2),
                    na(3)
                }
            ACCESS  read-only
            STATUS  mandatory
            DESCRIPTION
                "DTE6 CTS"
            ::= { dte6StatusEntry 18 }

        dte6StatusDCDstatus  OBJECT-TYPE
            SYNTAX  INTEGER {
                    no(1),
                    yes(2),
                    na(3)
                }
            ACCESS  read-only
            STATUS  mandatory
            DESCRIPTION
                "DTE6 DCD"
            ::= { dte6StatusEntry 19 }

        dte6StatusDTRstatus  OBJECT-TYPE
            SYNTAX  INTEGER {
                    no(1),
                    yes(2),
                    na(3)
                }
            ACCESS  read-only
            STATUS  mandatory
            DESCRIPTION
                "DTE6 DTR"
            ::= { dte6StatusEntry 20 }

        dte6StatusRTSstatus  OBJECT-TYPE
            SYNTAX  INTEGER {
                    no(1),
                    yes(2),
                    na(3)
                }
            ACCESS  read-only
            STATUS  mandatory
            DESCRIPTION
                "DTE6 RTS"
            ::= { dte6StatusEntry 21 }

        dte6StatusRemoteAlarm  OBJECT-TYPE
            SYNTAX  INTEGER {
                    no(1),
                    yes(2),
                    na(3)
                }
            ACCESS  read-only
            STATUS  mandatory
            DESCRIPTION
                "DTE6 Rdmote_X"
            ::= { dte6StatusEntry 22 }

        dte6StatusFrameSync  OBJECT-TYPE
            SYNTAX  INTEGER {
                    no(1),
                    yes(2),
                    na(3)
                }
            ACCESS  read-only
            STATUS  mandatory
            DESCRIPTION
                "DTE6 Local Sync"
            ::= { dte6StatusEntry 23 }

        dte6StatusRemoteS1  OBJECT-TYPE
            SYNTAX  INTEGER {
                    off(1),
                    on(2),
                    na(14)
                }
            ACCESS  read-only
            STATUS  mandatory
            DESCRIPTION
                "DTE6 remote status bit S1"
            ::= { dte6StatusEntry 24 }

        dte6StatusRemoteS3  OBJECT-TYPE
            SYNTAX  INTEGER {
                    off(1),
                    on(2),
                    na(14)
                }
            ACCESS  read-only
            STATUS  mandatory
            DESCRIPTION
                "DTE6 remote status bit S3"
            ::= { dte6StatusEntry 25 }

        dte6StatusRemoteS4  OBJECT-TYPE
            SYNTAX  INTEGER {
                    off(1),
                    on(2),
                    na(14)
                }
            ACCESS  read-only
            STATUS  mandatory
            DESCRIPTION
                "DTE6 remote status bit S4"
            ::= { dte6StatusEntry 26 }

        dte6StatusRemoteS6  OBJECT-TYPE
            SYNTAX  INTEGER {
                    off(1),
                    on(2),
                    na(14)
                }
            ACCESS  read-only
            STATUS  mandatory
            DESCRIPTION
                "DTE6 remote status bit S6"
            ::= { dte6StatusEntry 27 }

        dte6StatusRemoteS8  OBJECT-TYPE
            SYNTAX  INTEGER {
                    off(1),
                    on(2),
                    na(14)
                }
            ACCESS  read-only
            STATUS  mandatory
            DESCRIPTION
                "DTE6 remote status bit S8"
            ::= { dte6StatusEntry 28 }

        dte6StatusRemoteS9  OBJECT-TYPE
            SYNTAX  INTEGER {
                    off(1),
                    on(2),
                    na(14)
                }
            ACCESS  read-only
            STATUS  mandatory
            DESCRIPTION
                "DTE6 remote status bit S9"
            ::= { dte6StatusEntry 29 }

        dte6StatusRemoteE4  OBJECT-TYPE
            SYNTAX  INTEGER {
                    off(1),
                    on(2),
                    na(14)
                }
            ACCESS  read-only
            STATUS  mandatory
            DESCRIPTION
                "DTE6 remote status bit E4"
            ::= { dte6StatusEntry 30}

        dte6StatusRemoteE5  OBJECT-TYPE
            SYNTAX  INTEGER {
                    off(1),
                    on(2),
                    na(14)
                }
            ACCESS  read-only
            STATUS  mandatory
            DESCRIPTION
                "DTE6 remote status bit E5"
            ::= { dte6StatusEntry 31 }

        dte6StatusRemoteE6  OBJECT-TYPE
            SYNTAX  INTEGER {
                    off(1),
                    on(2),
                    na(14)
                }
            ACCESS  read-only
            STATUS  mandatory
            DESCRIPTION
                "DTE6 remote status bit E6"
            ::= { dte6StatusEntry 32 }

        dte6StatusRemoteX  OBJECT-TYPE
            SYNTAX  INTEGER {
                    off(1),
                    on(2),
                    na(14)
                }
            ACCESS  read-only
            STATUS  mandatory
            DESCRIPTION
                "DTE6 remote status bit X"
            ::= { dte6StatusEntry 33 }

--
--  Alarm Control Table
--

        dte6AlarmControlTable  OBJECT-TYPE
            SYNTAX  SEQUENCE OF Dte6AlarmControlEntry
            ACCESS  not-accessible
            STATUS  mandatory
            DESCRIPTION
                "The DTE6 alarm control table."
            ::= { dte6-card 4 }

        dte6AlarmControlEntry  OBJECT-TYPE
            SYNTAX  Dte6AlarmControlEntry
            ACCESS  not-accessible
            STATUS  mandatory
            DESCRIPTION
                "An entry in the DTE6 alarm control table."
            INDEX { dte6AlarmSlotIndex , dte6AlarmPortIndex }
            ::= { dte6AlarmControlTable 1 }

        Dte6AlarmControlEntry ::= SEQUENCE {
            dte6AlarmSlotIndex           LSSlotID,
            dte6AlarmPortIndex           SixPortID,
            dte6AlarmSetup               LsAlarmSeverity
        }

        dte6AlarmSlotIndex  OBJECT-TYPE
            SYNTAX  LSSlotID
            ACCESS  read-only
            STATUS  mandatory
            DESCRIPTION
                "DTE6 slot index"
            ::= { dte6AlarmControlEntry 1 }

        dte6AlarmPortIndex  OBJECT-TYPE
            SYNTAX  SixPortID
            ACCESS  read-only
            STATUS  mandatory
            DESCRIPTION
                "Port 1 to 6, Total 6 ports"
            ::= { dte6AlarmControlEntry 2 }

        dte6AlarmSetup  OBJECT-TYPE
            SYNTAX  LsAlarmSeverity
            ACCESS  read-write
            STATUS  mandatory
            DESCRIPTION
                "Alarm is enabled or not"
            ::= { dte6AlarmControlEntry 3 }


--
--  Alarm History Table
--

        dte6AlmHistoryTable  OBJECT-TYPE
            SYNTAX  SEQUENCE OF Dte6AlmHistoryEntry
            ACCESS  not-accessible
            STATUS  mandatory
            DESCRIPTION
                " Key: dte6AlmHistoryUnitIndex "
            ::= { dte6-card 5 }

        dte6AlmHistoryEntry  OBJECT-TYPE
            SYNTAX  Dte6AlmHistoryEntry
            ACCESS  not-accessible
            STATUS  mandatory
            DESCRIPTION
                " "
            INDEX { dte6AlmHisSlotIndex , dte6AlmHisPortIndex }
            ::= { dte6AlmHistoryTable 1 }

        Dte6AlmHistoryEntry ::= SEQUENCE {
            dte6AlmHisSlotIndex      LSSlotID,
            dte6AlmHisPortIndex      SixPortID,
            dte6AlmHistoryState          INTEGER,
            dte6AlmHistoryCount          Counter,
            dte6AlmHistoryEnable         LsAlarmSeverity
        }

        dte6AlmHisSlotIndex  OBJECT-TYPE
            SYNTAX  LSSlotID
            ACCESS  read-only
            STATUS  mandatory
            DESCRIPTION
                "DTE6 slot index"
            ::= { dte6AlmHistoryEntry 1 }

        dte6AlmHisPortIndex  OBJECT-TYPE
            SYNTAX  SixPortID
            ACCESS  read-only
            STATUS  mandatory
            DESCRIPTION
                "Port 1 to 6, Total 6 ports"
            ::= { dte6AlmHistoryEntry 2 }

        dte6AlmHistoryState  OBJECT-TYPE
            SYNTAX  INTEGER {
                    ok(1),
                    alarm(2),
                    disable(3),
                    na(4)
                }
            ACCESS  read-only
            STATUS  mandatory
            DESCRIPTION
                " Alarm Current State"
            ::= { dte6AlmHistoryEntry 3 }

        dte6AlmHistoryCount  OBJECT-TYPE
            SYNTAX  Counter
            ACCESS  read-only
            STATUS  mandatory
            DESCRIPTION
                " Alarm Count which happened "
            ::= { dte6AlmHistoryEntry 4 }

        dte6AlmHistoryEnable  OBJECT-TYPE
            SYNTAX  LsAlarmSeverity
            ACCESS  read-only
            STATUS  mandatory
            DESCRIPTION
                "Alarm is enabled or not"
            ::= { dte6AlmHistoryEntry 5 }


--
-- Diagnostic Control Table
--

        dte6DiagControlTable  OBJECT-TYPE
            SYNTAX  SEQUENCE OF Dte6DiagControlEntry
            ACCESS  not-accessible
            STATUS  mandatory
            DESCRIPTION
                ""
            ::= { dte6-card 6 }

        dte6DiagControlEntry  OBJECT-TYPE
            SYNTAX  Dte6DiagControlEntry
            ACCESS  not-accessible
            STATUS  mandatory
            DESCRIPTION
                ""
            INDEX { dte6DiagCtrlSlotIndex , dte6DiagCtrlPortIndex }
            ::= { dte6DiagControlTable 1 }

        Dte6DiagControlEntry ::= SEQUENCE {
            dte6DiagCtrlSlotIndex     LSSlotID,
            dte6DiagCtrlPortIndex     SixPortID,
            dte6NearLoopback          INTEGER
        }

        dte6DiagCtrlSlotIndex  OBJECT-TYPE
            SYNTAX  LSSlotID
            ACCESS  read-only
            STATUS  mandatory
            DESCRIPTION
                "DTE6 slot index"
            ::= { dte6DiagControlEntry 1 }

        dte6DiagCtrlPortIndex  OBJECT-TYPE
            SYNTAX  SixPortID
            ACCESS  read-only
            STATUS  mandatory
            DESCRIPTION
                "Port 1 to 6, Total 6 ports"
            ::= { dte6DiagControlEntry 2 }

        dte6NearLoopback  OBJECT-TYPE
            SYNTAX  INTEGER {
                    noLoopback(1),
                    toDTE(2),
                    toLocal(3)
                }
            ACCESS  read-write
            STATUS  mandatory
            DESCRIPTION
                "DTE6 Loopback Type"
            ::= { dte6DiagControlEntry 3 }

--
-- DTE6 Card Control Table
--

        dte6CardControlTable  OBJECT-TYPE
            SYNTAX  SEQUENCE OF Dte6CardControlEntry
            ACCESS  not-accessible
            STATUS  mandatory
            DESCRIPTION
                "The DTE6 Card control table."
            ::= { dte6-card 7 }

        dte6CardControlEntry  OBJECT-TYPE
            SYNTAX  Dte6CardControlEntry
            ACCESS  not-accessible
            STATUS  mandatory
            DESCRIPTION
                "An entry in the RS232A Card control table."
            INDEX { dte6CardIndex }
            ::= { dte6CardControlTable 1 }

        Dte6CardControlEntry ::= SEQUENCE {
            dte6CardIndex                LSSlotID,
            dte6Reset                    INTEGER,
            dte6LoadDefault              INTEGER
        }

        dte6CardIndex  OBJECT-TYPE
            SYNTAX  LSSlotID
            ACCESS  read-only
            STATUS  mandatory
            DESCRIPTION
                "DTE6 slot index"
            ::= { dte6CardControlEntry 1 }

        dte6Reset  OBJECT-TYPE
            SYNTAX  INTEGER {
                    na(1),
                    reset(2)
                }
            ACCESS  read-write
            STATUS  mandatory
            DESCRIPTION
                "Reset dte6 card"
            ::= { dte6CardControlEntry 2 }

        dte6LoadDefault  OBJECT-TYPE
            SYNTAX  INTEGER {
                    na(1),
                    default(2)
                }
            ACCESS  read-write
            STATUS  mandatory
            DESCRIPTION
                "Load default"
            ::= { dte6CardControlEntry 3 }


--
--  DTE6 System Information Table
--

        dte6SystemInfoTable  OBJECT-TYPE
            SYNTAX  SEQUENCE OF Dte6SystemInfoEntry
            ACCESS  not-accessible
            STATUS  mandatory
            DESCRIPTION
                "The DTE6 system information table."
            ::= { dte6-card 8}

        dte6SystemInfoEntry  OBJECT-TYPE
            SYNTAX  Dte6SystemInfoEntry
            ACCESS  not-accessible
            STATUS  mandatory
            DESCRIPTION
                "An entry in the DTE6 system information table."
            INDEX { dte6SISlotIndex }
            ::= { dte6SystemInfoTable 1 }

        Dte6SystemInfoEntry ::= SEQUENCE {
            dte6SISlotIndex            LSSlotID,
            dte6PROMVersion            DisplayString,
            dte6HardwareVersion        DisplayString,
            dte6FpgaVersion            DisplayString,
            dte6Bank1Version           DisplayString,
            dte6Bank2Version           DisplayString,
            dte6ActiveBank             INTEGER
        }

        dte6SISlotIndex  OBJECT-TYPE
            SYNTAX  LSSlotID
            ACCESS  read-only
            STATUS  mandatory
            DESCRIPTION
                "DTE6 slot index"
            ::= { dte6SystemInfoEntry 1 }

        dte6PROMVersion  OBJECT-TYPE
            SYNTAX  DisplayString (SIZE (0..30) )
            ACCESS  read-only
            STATUS  mandatory
            DESCRIPTION
                " DTE6 PROM Version"
            ::= { dte6SystemInfoEntry 2 }

        dte6HardwareVersion  OBJECT-TYPE
            SYNTAX  DisplayString (SIZE (0..30) )
            ACCESS  read-only
            STATUS  mandatory
            DESCRIPTION
                " DTE6 Hardware Version"
            ::= { dte6SystemInfoEntry 3 }

        dte6FpgaVersion  OBJECT-TYPE
            SYNTAX  DisplayString (SIZE (0..30))
            ACCESS  read-only
            STATUS  mandatory
            DESCRIPTION
                "FPGA Version"
            ::= { dte6SystemInfoEntry 4 }

        dte6Bank1Version    OBJECT-TYPE
            SYNTAX  DisplayString (SIZE (0..30))
            ACCESS  read-only
            STATUS  mandatory
            DESCRIPTION
                "Bank-1 Version"
            ::= { dte6SystemInfoEntry 5 }

        dte6Bank2Version    OBJECT-TYPE
            SYNTAX  DisplayString (SIZE (0..30))
            ACCESS  read-only
            STATUS  mandatory
            DESCRIPTION
                "Bank-2 Version"
            ::= { dte6SystemInfoEntry 6}

        dte6ActiveBank    OBJECT-TYPE
            SYNTAX  INTEGER{
                    bank-1(1),
                    bank-2(2)
                }
            ACCESS  read-only
            STATUS  mandatory
            DESCRIPTION
                "Active Bank 1/2"
            ::= { dte6SystemInfoEntry 7 }

--
--  DTE6 M2 Configuration
--

        dte6M2ConfigTable  OBJECT-TYPE
            SYNTAX  SEQUENCE OF Dte6M2ConfigEntry
            ACCESS  not-accessible
            STATUS  mandatory
            DESCRIPTION
                "The DTE6 Interface M2 Configuration table."
            ::= { dte6-card 9 }

        dte6M2ConfigEntry  OBJECT-TYPE
            SYNTAX  Dte6M2ConfigEntry
            ACCESS  not-accessible
            STATUS  mandatory
            DESCRIPTION
                "An entry in the DTE6 Configuration table."
            INDEX { dte6M2CfgSlotIndex , dte6M2CfgPortIndex }
            ::= { dte6M2ConfigTable 1 }

        Dte6M2ConfigEntry ::= SEQUENCE {
            dte6M2CfgSlotIndex                LSSlotID,
            dte6M2CfgPortIndex                SixPortID,
            dte6M2CfgInterface                INTEGER,
            dte6M2CfgChannel                  INTEGER,
            dte6M2CfgDS0Rate                  INTEGER,
            dte6M2CfgClockPolarity            INTEGER,
            dte6M2CfgDataPolarity             INTEGER,
            dte6M2CfgTTM                      INTEGER,
            dte6M2CfgRTS                      INTEGER,
            dte6M2CfgDTR                      INTEGER,
            dte6M2CfgOversamplingRate         INTEGER,
            dte6M2CfgSupportDataRate          DisplayString,
            dte6M2CfgWarrning                 DisplayString
        }

        dte6M2CfgSlotIndex  OBJECT-TYPE
            SYNTAX  LSSlotID
            ACCESS  read-only
            STATUS  mandatory
            DESCRIPTION
                "DTE6 slot index"
            ::= { dte6M2ConfigEntry 1 }

        dte6M2CfgPortIndex  OBJECT-TYPE
            SYNTAX  SixPortID
            ACCESS  read-only
            STATUS  mandatory
            DESCRIPTION
                "Port 1 to 6, Total 6 ports"
            ::= { dte6M2ConfigEntry 2 }

        dte6M2CfgInterface  OBJECT-TYPE
            SYNTAX  INTEGER {
                    rs232(1),
                    rs422(2),
                    x21(3),
                    v35(4),
                    v36(5),
                    eia530Rs449(6)
                }
            ACCESS  read-write
            STATUS  mandatory
            DESCRIPTION
                "DTE6 Interface mode"
            ::= { dte6M2ConfigEntry 3 }

        dte6M2CfgChannel  OBJECT-TYPE
            SYNTAX  INTEGER (0..32)
            ACCESS  read-only
            STATUS  mandatory
            DESCRIPTION
                "DTE6 Channel"
            ::= { dte6M2ConfigEntry 4 }


        dte6M2CfgDS0Rate  OBJECT-TYPE
            SYNTAX  INTEGER {
                    r64K(1),
                    r56K(2)
                }
            ACCESS  read-write
            STATUS  mandatory
            DESCRIPTION
                "DTE6 DS0 Rate"
            ::= { dte6M2ConfigEntry 5 }

        dte6M2CfgClockPolarity  OBJECT-TYPE
            SYNTAX  INTEGER {
                    clockNormal(1),
                    clockInverted(2),
                    na(3)
                }
            ACCESS  read-write
            STATUS  mandatory
            DESCRIPTION
                "DTE6 Clock Polarity"
            ::= { dte6M2ConfigEntry 6 }

        dte6M2CfgDataPolarity  OBJECT-TYPE
            SYNTAX  INTEGER {
                    dataNormal(1),
                    dataInverted(2),
                    na(3)
                }
            ACCESS  read-write
            STATUS  mandatory
            DESCRIPTION
                "DTE6 Data Polarity"
            ::= { dte6M2ConfigEntry 7 }

        dte6M2CfgTTM  OBJECT-TYPE
            SYNTAX  INTEGER {
                    ttmOff(1),
                    ttmOn(2),
                    na(3)
                }
            ACCESS  read-write
            STATUS  mandatory
            DESCRIPTION
                "DTE6 TTM Mode"
            ::= { dte6M2ConfigEntry 8 }

        dte6M2CfgRTS  OBJECT-TYPE
            SYNTAX  INTEGER {
                    rtsActive(1),
                    rtsPermanent(2)
                }
            ACCESS  read-write
            STATUS  mandatory
            DESCRIPTION
                "DTE6 RTS Mode"
            ::= { dte6M2ConfigEntry 9 }

        dte6M2CfgDTR  OBJECT-TYPE
            SYNTAX  INTEGER {
                    dtrActive(1),
                    dtrPermanent(2),
                    na(3)
                }
            ACCESS  read-write
            STATUS  mandatory
            DESCRIPTION
                "DTE6 DTR Mode"
            ::= {  dte6M2ConfigEntry 10 }

        dte6M2CfgOversamplingRate  OBJECT-TYPE
            SYNTAX  INTEGER (0..384)
            ACCESS  read-only
            STATUS  mandatory
            DESCRIPTION
                "DTE6 Oversampling Rate"
            ::= { dte6M2ConfigEntry 11 }

        dte6M2CfgSupportDataRate  OBJECT-TYPE
            SYNTAX  DisplayString (SIZE (0..160) )
            ACCESS  read-only
            STATUS  mandatory
            DESCRIPTION
                "DTE6 Support Data Rate"
            ::= { dte6M2ConfigEntry 12 }

        dte6M2CfgWarrning  OBJECT-TYPE
            SYNTAX  DisplayString (SIZE (0..70) )
            ACCESS  read-only
            STATUS  mandatory
            DESCRIPTION
                "DTE6 Warrning"
            ::= { dte6M2ConfigEntry 13 }

--
--  DTE6 M2 Status
--

        dte6M2StatusTable  OBJECT-TYPE
            SYNTAX  SEQUENCE OF Dte6M2StatusEntry
            ACCESS  not-accessible
            STATUS  mandatory
            DESCRIPTION
                "The DTE6 M2Status table."
            ::= { dte6-card 10}

        dte6M2StatusEntry  OBJECT-TYPE
            SYNTAX  Dte6M2StatusEntry
            ACCESS  not-accessible
            STATUS  mandatory
            DESCRIPTION
                "An entry in the DTE6 Status table."
            INDEX { dte6M2StatusSlotIndex , dte6M2StatusPortIndex }
            ::= { dte6M2StatusTable 1 }

        Dte6M2StatusEntry ::= SEQUENCE {
            dte6M2StatusSlotIndex         LSSlotID,
            dte6M2StatusPortIndex         SixPortID,
            dte6M2StatusDteDCD            INTEGER,
            dte6M2StatusRTSloss           INTEGER,
            dte6M2StatusEXTCLKloss        INTEGER,
            dte6M2StatusDSRstatus         INTEGER,
            dte6M2StatusCTSstatus         INTEGER,
            dte6M2StatusDCDstatus         INTEGER,
            dte6M2StatusDTRstatus         INTEGER,
            dte6M2StatusRTSstatus         INTEGER,
            dte6M2StatusRxBytesCounter    INTEGER,
            dte6M2StatusTxBytesCounter    INTEGER
        }

        dte6M2StatusSlotIndex  OBJECT-TYPE
            SYNTAX  LSSlotID
            ACCESS  read-only
            STATUS  mandatory
            DESCRIPTION
                "DTE6 slot index"
            ::= { dte6M2StatusEntry 1 }

        dte6M2StatusPortIndex  OBJECT-TYPE
            SYNTAX  SixPortID
            ACCESS  read-only
            STATUS  mandatory
            DESCRIPTION
                "Port 1 to 6, Total 6 ports"
            ::= { dte6M2StatusEntry 2 }

        dte6M2StatusDteDCD  OBJECT-TYPE
            SYNTAX  INTEGER {
                    off(1),
                    on(2)
                }
            ACCESS  read-write
            STATUS  mandatory
            DESCRIPTION
                "DTE6 Status bit DTE DCD"
            ::= { dte6M2StatusEntry 3 }

        dte6M2StatusRTSloss  OBJECT-TYPE
            SYNTAX  INTEGER {
                    no(1),
                    yes(2),
                    na(3)
                }
            ACCESS  read-only
            STATUS  mandatory
            DESCRIPTION
                "DTE6 RTS loss"
            ::= { dte6M2StatusEntry 4 }

        dte6M2StatusEXTCLKloss  OBJECT-TYPE
            SYNTAX  INTEGER {
                    no(1),
                    yes(2),
                    na(3)
                }
            ACCESS  read-only
            STATUS  mandatory
            DESCRIPTION
                "DTE6 EXT-CLK loss"
            ::= { dte6M2StatusEntry 5 }

        dte6M2StatusDSRstatus  OBJECT-TYPE
            SYNTAX  INTEGER {
                    no(1),
                    yes(2),
                    na(3)
                }
            ACCESS  read-only
            STATUS  mandatory
            DESCRIPTION
                "DTE6 DSR"
            ::= { dte6M2StatusEntry 6 }

        dte6M2StatusCTSstatus  OBJECT-TYPE
            SYNTAX  INTEGER {
                    no(1),
                    yes(2),
                    na(3)
                }
            ACCESS  read-only
            STATUS  mandatory
            DESCRIPTION
                "DTE6 CTS"
            ::= { dte6M2StatusEntry 7 }

        dte6M2StatusDCDstatus  OBJECT-TYPE
            SYNTAX  INTEGER {
                    no(1),
                    yes(2),
                    na(3)
                }
            ACCESS  read-only
            STATUS  mandatory
            DESCRIPTION
                "DTE6 DCD"
            ::= { dte6M2StatusEntry 8 }

        dte6M2StatusDTRstatus  OBJECT-TYPE
            SYNTAX  INTEGER {
                    no(1),
                    yes(2),
                    na(3)
                }
            ACCESS  read-only
            STATUS  mandatory
            DESCRIPTION
                "DTE6 DTR"
            ::= { dte6M2StatusEntry 9 }

        dte6M2StatusRTSstatus  OBJECT-TYPE
            SYNTAX  INTEGER {
                    no(1),
                    yes(2),
                    na(3)
                }
            ACCESS  read-only
            STATUS  mandatory
            DESCRIPTION
                "DTE6 RTS"
            ::= { dte6M2StatusEntry 10 }

        dte6M2StatusRxBytesCounter  OBJECT-TYPE
            SYNTAX  INTEGER (0..131071)
            ACCESS  read-only
            STATUS  mandatory
            DESCRIPTION
                "DTE6 RxBytesCounter"
            ::= { dte6M2StatusEntry 11 }

        dte6M2StatusTxBytesCounter  OBJECT-TYPE
            SYNTAX  INTEGER (0..131071)
            ACCESS  read-only
            STATUS  mandatory
            DESCRIPTION
                "DTE6 TxBytesCounter"
            ::= { dte6M2StatusEntry 12 }

        dte6TotalCard   OBJECT-TYPE
            SYNTAX  INTEGER
            ACCESS  read-only
            STATUS  mandatory
            DESCRIPTION
                "Total cards of 6UDTE"
            ::= { dte6-card 100 }

--======================================================================--
--======================================================================--
--  6CDA Card MIB
--======================================================================--
--======================================================================--

--
--Config Table
--

        cda6ConfigTable     OBJECT-TYPE
            SYNTAX  SEQUENCE OF Cda6ConfigEntry
            ACCESS  not-accessible
            STATUS  mandatory
            DESCRIPTION
                " The Config Table "
            ::= { cda6-card 1 }

        cda6ConfigEntry     OBJECT-TYPE
            SYNTAX  Cda6ConfigEntry
            ACCESS  not-accessible
            STATUS  mandatory
            DESCRIPTION
                " An entry in the Config Table "
            INDEX { cda6ConfigSlotIndex , cda6ConfigPortIndex }
            ::= { cda6ConfigTable 1 }

        Cda6ConfigEntry ::= SEQUENCE {
            cda6ConfigSlotIndex       LSSlotID,
            cda6ConfigPortIndex       SixPortID,
            cda6ConfigInterface       INTEGER,
            cda6ConfigType            INTEGER,
            cda6ConfigOctetClock         INTEGER,
            cda6ConfigTxClock         INTEGER
        }

        cda6ConfigSlotIndex  OBJECT-TYPE
            SYNTAX  LSSlotID
            ACCESS  read-only
            STATUS  mandatory
            DESCRIPTION
                "6CDA slot "
            ::= { cda6ConfigEntry 1 }

        cda6ConfigPortIndex  OBJECT-TYPE
            SYNTAX  SixPortID
            ACCESS  read-only
            STATUS  mandatory
            DESCRIPTION
                " Port 1 to 6, Total 6 ports "
            ::= { cda6ConfigEntry 2 }

        cda6ConfigInterface  OBJECT-TYPE
            SYNTAX  INTEGER {
                    contradirectional(1),
                    codirectional(2)
                }
            ACCESS  read-write
            STATUS  mandatory
            DESCRIPTION
                " Interface "
            ::= { cda6ConfigEntry 3 }

        cda6ConfigType  OBJECT-TYPE
            SYNTAX  INTEGER {
 --                   subordinate(1),
                    controlling(2),
                    na(3)
                }
            ACCESS  read-write
            STATUS  mandatory
            DESCRIPTION
                " Type "
            ::= { cda6ConfigEntry 4 }

        cda6ConfigOctetClock  OBJECT-TYPE
            SYNTAX  INTEGER {
                    fromControl(1),
                  --  fromSub(2),
                    na(3)
                }
            ACCESS  read-write
            STATUS  mandatory
            DESCRIPTION
                " Octet Clock "
            ::= { cda6ConfigEntry 5 }

        cda6ConfigTxClock  OBJECT-TYPE
            SYNTAX  INTEGER {
                    rxPin(1),
                    txPin(2),
                    na(3)
                }
            ACCESS  read-write
            STATUS  mandatory
            DESCRIPTION
                " Tx Clock "
            ::= { cda6ConfigEntry 6 }

--
-- Loopback Test Table
--

        cda6LpbackTestTable  OBJECT-TYPE
            SYNTAX  SEQUENCE OF Cda6LpbackTestEntry
            ACCESS  not-accessible
            STATUS  mandatory
            DESCRIPTION
                " The Loopback Test Table "
            ::= { cda6-card 2 }

        cda6LpbackTestEntry  OBJECT-TYPE
            SYNTAX  Cda6LpbackTestEntry
            ACCESS  not-accessible
            STATUS  mandatory
            DESCRIPTION
                " An entry in the Loopback Test Table "
            INDEX { cda6SlotIndex , cda6PortIndex }
            ::= { cda6LpbackTestTable 1 }

        Cda6LpbackTestEntry ::= SEQUENCE {
            cda6SlotIndex               LSSlotID,
            cda6PortIndex               SixPortID,
            cda6NearEndLoopback         INTEGER
--          cda6SendTestPattern         INTEGER,
--           cda6Bert                    INTEGER,
--            cda6BitError                INTEGER,
--            cda6ErrorSeconds            INTEGER,
--            cda6ElapsedSeconds          INTEGER

    }

        cda6SlotIndex  OBJECT-TYPE
            SYNTAX  LSSlotID
            ACCESS  read-only
            STATUS  mandatory
            DESCRIPTION
                "6CDA slot "
            ::= { cda6LpbackTestEntry 1 }

        cda6PortIndex  OBJECT-TYPE
            SYNTAX  SixPortID
            ACCESS  read-only
            STATUS  mandatory
            DESCRIPTION
                " Port 1 to 6, Total 6 ports "
            ::= { cda6LpbackTestEntry 2 }

        cda6NearEndLoopback  OBJECT-TYPE
            SYNTAX  INTEGER {
                    off(1),
                    local(2),
                    line(3)
                }
            ACCESS  read-write
            STATUS  mandatory
            DESCRIPTION
                " NEAR-END LOOPBACK "
            ::= { cda6LpbackTestEntry 3 }

--        cda6SendTestPattern  OBJECT-TYPE
--            SYNTAX  INTEGER {
--                    off(1),
--                    on(2),
--                    reset(3),
--                    injectError(4)
--                }
--            ACCESS  read-write
--            STATUS  mandatory
--            DESCRIPTION
--                " Send Test Pattern "
--            ::= { cda6LpbackTestEntry 4 }
--
--        cda6Bert  OBJECT-TYPE
--            SYNTAX  INTEGER {
--                    sync(1),
--                    unsync(2),
--                    notActive(3)
--                }
--            ACCESS  read-only
--            STATUS  mandatory
--            DESCRIPTION
--                " BERT "
--            ::= { cda6LpbackTestEntry 5 }
--
--        cda6BitError  OBJECT-TYPE
--            SYNTAX  INTEGER
--            ACCESS  read-only
--            STATUS  mandatory
--            DESCRIPTION
--                " BIT ERROR "
--            ::= { cda6LpbackTestEntry 6 }
--
--        cda6ErrorSeconds OBJECT-TYPE
--            SYNTAX  INTEGER
--            ACCESS  read-only
--            STATUS  mandatory
--            DESCRIPTION
--                " ERROR SECONDS "
--            ::= { cda6LpbackTestEntry 7 }
--
--        cda6ElapsedSeconds  OBJECT-TYPE
--            SYNTAX  INTEGER
--            ACCESS  read-only
--            STATUS  mandatory
--            DESCRIPTION
--                " ELAPSED SECONDS "
--            ::= { cda6LpbackTestEntry 8 }
--

--
--  Status Table
--

        cda6StatusTable  OBJECT-TYPE
            SYNTAX  SEQUENCE OF Cda6StatusEntry
            ACCESS  not-accessible
            STATUS  mandatory
            DESCRIPTION
                " The Status Table "
            ::= { cda6-card 3 }

        cda6StatusEntry  OBJECT-TYPE
            SYNTAX  Cda6StatusEntry
            ACCESS  not-accessible
            STATUS  mandatory
            DESCRIPTION
                " An entry in the Status Table "
            INDEX { cda6StatusSlotIndex , cda6StatusPortIndex }
            ::= { cda6StatusTable 1 }

        Cda6StatusEntry ::= SEQUENCE {
            cda6StatusSlotIndex         LSSlotID,
            cda6StatusPortIndex         SixPortID,
            cda6StatusLos               INTEGER,
            cda6StatusLoo               INTEGER,
            cda6StatusLocalLpback       INTEGER,
            cda6StatusLineLpback     INTEGER
        }

        cda6StatusSlotIndex  OBJECT-TYPE
            SYNTAX  LSSlotID
            ACCESS  read-only
            STATUS  mandatory
            DESCRIPTION
                "6CDA slot "
            ::= { cda6StatusEntry 1 }

        cda6StatusPortIndex  OBJECT-TYPE
            SYNTAX  SixPortID
            ACCESS  read-only
            STATUS  mandatory
            DESCRIPTION
                " Port 1 to 6, Total 6 ports "
            ::= { cda6StatusEntry 2 }

        cda6StatusLos  OBJECT-TYPE
            SYNTAX  INTEGER {
                    no(1),
                    yes(2),
                    na(3)
                }
            ACCESS  read-only
            STATUS  mandatory
            DESCRIPTION
                " LINE - LOS "
            ::= { cda6StatusEntry 3 }

        cda6StatusLoo  OBJECT-TYPE
            SYNTAX  INTEGER {
                    no(1),
                    yes(2),
                    na(3)
                }
            ACCESS  read-only
            STATUS  mandatory
            DESCRIPTION
                " LINE - LOO "
            ::= { cda6StatusEntry 4 }

        cda6StatusLocalLpback  OBJECT-TYPE
            SYNTAX  INTEGER {
                    no(1),
                    yes(2)
                }
            ACCESS  read-only
            STATUS  mandatory
            DESCRIPTION
                " TEST - LOCAL LOOPBACK "
            ::= { cda6StatusEntry 5 }

        cda6StatusLineLpback  OBJECT-TYPE
            SYNTAX  INTEGER {
                    no(1),
                    yes(2)
                }
            ACCESS  read-only
            STATUS  mandatory
            DESCRIPTION
                " TEST - Line LOOPBACK "
            ::= { cda6StatusEntry 6 }

--
--  Alarm Setup Table
--

        cda6AlarmSetupTable  OBJECT-TYPE
            SYNTAX  SEQUENCE OF Cda6AlarmSetupEntry
            ACCESS  not-accessible
            STATUS  mandatory
            DESCRIPTION
                " Alarm Setup Table "
            ::= { cda6-card 4 }

        cda6AlarmSetupEntry  OBJECT-TYPE
            SYNTAX  Cda6AlarmSetupEntry
            ACCESS  not-accessible
            STATUS  mandatory
            DESCRIPTION
                " An entry in the Alarm Setup Table "
            INDEX { cda6AlmStpSlotIndex , cda6AlmStpPortIndex , cda6AlmStpTypeIndex }
            ::= { cda6AlarmSetupTable 1 }

        Cda6AlarmSetupEntry ::= SEQUENCE {
            cda6AlmStpSlotIndex         LSSlotID,
            cda6AlmStpPortIndex         SixPortID,
            cda6AlmStpTypeIndex         INTEGER,
            cda6AlmStpAlarm             INTEGER
        }

        cda6AlmStpSlotIndex  OBJECT-TYPE
            SYNTAX  LSSlotID
            ACCESS  read-only
            STATUS  mandatory
            DESCRIPTION
                "6CDA slot "
            ::= { cda6AlarmSetupEntry 1 }

        cda6AlmStpPortIndex  OBJECT-TYPE
            SYNTAX  SixPortID
            ACCESS  read-only
            STATUS  mandatory
            DESCRIPTION
                " Port 1 to 6, Total 6 ports "
            ::= { cda6AlarmSetupEntry 2 }

        cda6AlmStpTypeIndex  OBJECT-TYPE
            SYNTAX  INTEGER {
                    los(1),
                    loo(2),
                    txClkLoss(3),
                    rxClkLoss(4)
                }
            ACCESS  read-only
            STATUS  mandatory
            DESCRIPTION
                " Type "
            ::= { cda6AlarmSetupEntry 3 }

        cda6AlmStpAlarm  OBJECT-TYPE
            SYNTAX  INTEGER {
                    disable(1),
                    major(2),
                    critical(3),
                    minor(4),
                    na(5)
                }
            ACCESS  read-write
            STATUS  mandatory
            DESCRIPTION
                " Alarm "
            ::= { cda6AlarmSetupEntry 4 }

--
--  Alarm History Table
--

        cda6AlmHistoryTable  OBJECT-TYPE
            SYNTAX  SEQUENCE OF Cda6AlmHistoryEntry
            ACCESS  not-accessible
            STATUS  mandatory
            DESCRIPTION
                " Alarm History Table "
            ::= { cda6-card 5 }

        cda6AlmHistoryEntry  OBJECT-TYPE
            SYNTAX  Cda6AlmHistoryEntry
            ACCESS  not-accessible
            STATUS  mandatory
            DESCRIPTION
                " An entry in the Alarm History Table "
            INDEX { cda6AlmHistorySlotIndex , cda6AlmHistoryPortIndex , cda6AlmHistoryTypeIndex }
            ::= { cda6AlmHistoryTable 1 }

        Cda6AlmHistoryEntry ::= SEQUENCE {
            cda6AlmHistorySlotIndex     LSSlotID,
            cda6AlmHistoryPortIndex     SixPortID,
            cda6AlmHistoryTypeIndex     INTEGER,
            cda6AlmHistoryState         INTEGER,
            cda6AlmHistoryCount         INTEGER,
            cda6AlmHistoryAlarm         INTEGER
        }

        cda6AlmHistorySlotIndex  OBJECT-TYPE
            SYNTAX  LSSlotID
            ACCESS  read-only
            STATUS  mandatory
            DESCRIPTION
                "6CDA slot "
            ::= { cda6AlmHistoryEntry 1 }

        cda6AlmHistoryPortIndex  OBJECT-TYPE
            SYNTAX  SixPortID
            ACCESS  read-only
            STATUS  mandatory
            DESCRIPTION
                " Port 1 to 6, Total 6 ports "
            ::= { cda6AlmHistoryEntry 2 }

        cda6AlmHistoryTypeIndex  OBJECT-TYPE
            SYNTAX  INTEGER {
                    los(1),
                    loo(2),
                    txClkLoss(3),
                    rxClkLoss(4)
                }
            ACCESS  read-only
            STATUS  mandatory
            DESCRIPTION
                " Type "
            ::= { cda6AlmHistoryEntry 3 }

        cda6AlmHistoryState  OBJECT-TYPE
            SYNTAX  INTEGER {
                    ok(1),
                    alarm(2),
                    disable(3),
                    na(4)
                }
            ACCESS  read-only
            STATUS  mandatory
            DESCRIPTION
                " State "
            ::= { cda6AlmHistoryEntry 4 }

        cda6AlmHistoryCount  OBJECT-TYPE
            SYNTAX  INTEGER
            ACCESS  read-only
            STATUS  mandatory
            DESCRIPTION
                " Count "
            ::= { cda6AlmHistoryEntry 5 }

        cda6AlmHistoryAlarm  OBJECT-TYPE
            SYNTAX  INTEGER {
                    disable(1),
                    major(2),
                    critical(3),
                    minor(4),
                    na(5)
                }
            ACCESS  read-only
            STATUS  mandatory
            DESCRIPTION
                " Alarm "
            ::= { cda6AlmHistoryEntry 6 }

--
-- Card Control Table
--

        cda6CardControlTable  OBJECT-TYPE
            SYNTAX  SEQUENCE OF Cda6CardControlEntry
            ACCESS  not-accessible
            STATUS  mandatory
            DESCRIPTION
                " The CDA6 Card Control Table "
            ::= { cda6-card 6 }

        cda6CardControlEntry  OBJECT-TYPE
            SYNTAX  Cda6CardControlEntry
            ACCESS  not-accessible
            STATUS  mandatory
            DESCRIPTION
                " An entry in the CDA6 Card Control Table "
            INDEX { cda6CardIndex }
            ::= { cda6CardControlTable 1 }

        Cda6CardControlEntry ::= SEQUENCE {
            cda6CardIndex                LSSlotID,
            cda6Reset                    INTEGER,
            cda6LoadDefault              INTEGER,
            cda6AlarmReset            INTEGER
        }

        cda6CardIndex  OBJECT-TYPE
            SYNTAX  LSSlotID
            ACCESS  read-only
            STATUS  mandatory
            DESCRIPTION
                "6CDA slot "
            ::= { cda6CardControlEntry 1 }

        cda6Reset  OBJECT-TYPE
            SYNTAX  INTEGER {
                    na(1),
                    reset(2)
                }
            ACCESS  read-write
            STATUS  mandatory
            DESCRIPTION
                " Reset CDA6 card "
            ::= { cda6CardControlEntry 2 }

        cda6LoadDefault  OBJECT-TYPE
            SYNTAX  INTEGER {
                    na(1),
                    default(2)
                }
            ACCESS  read-write
            STATUS  mandatory
            DESCRIPTION
                " Load default "
            ::= { cda6CardControlEntry 3 }

        cda6AlarmReset  OBJECT-TYPE
            SYNTAX  INTEGER {
                    na(1),
                    reset(2)
                }
            ACCESS  read-write
            STATUS  mandatory
            DESCRIPTION
                " Alarm Counr Reset "
            ::= { cda6CardControlEntry 4 }
--
--  CDA6 System Information Table
--

        cda6SystemInfoTable  OBJECT-TYPE
            SYNTAX  SEQUENCE OF Cda6SystemInfoEntry
            ACCESS  not-accessible
            STATUS  mandatory
            DESCRIPTION
                " The CDA6 System Information Table "
            ::= { cda6-card 7 }

        cda6SystemInfoEntry  OBJECT-TYPE
            SYNTAX  Cda6SystemInfoEntry
            ACCESS  not-accessible
            STATUS  mandatory
            DESCRIPTION
                " An entry in the CDA6 System Information Table "
            INDEX { cda6SystemInfoSlotIndex }
            ::= { cda6SystemInfoTable 1 }

        Cda6SystemInfoEntry ::= SEQUENCE {
            cda6SystemInfoSlotIndex              LSSlotID,
            cda6SystemInfoPROMVersion            DisplayString,
            cda6SystemInfoHardwareVersion        DisplayString,
            cda6SystemInfoFpgaVersion            DisplayString,
            cda6SystemInfoBank1Version           DisplayString,
            cda6SystemInfoBank2Version           DisplayString,
            cda6SystemInfoActiveBank             INTEGER
        }

        cda6SystemInfoSlotIndex  OBJECT-TYPE
            SYNTAX  LSSlotID
            ACCESS  read-only
            STATUS  mandatory
            DESCRIPTION
                "6CDA slot "
            ::= { cda6SystemInfoEntry 1 }

        cda6SystemInfoPROMVersion  OBJECT-TYPE
            SYNTAX  DisplayString (SIZE (0..30) )
            ACCESS  read-only
            STATUS  mandatory
            DESCRIPTION
                " CDA6 PROM Version "
            ::= { cda6SystemInfoEntry 2 }

        cda6SystemInfoHardwareVersion  OBJECT-TYPE
            SYNTAX  DisplayString (SIZE (0..30) )
            ACCESS  read-only
            STATUS  mandatory
            DESCRIPTION
                " CDA6 Hardware Version "
            ::= { cda6SystemInfoEntry 3 }

        cda6SystemInfoFpgaVersion  OBJECT-TYPE
            SYNTAX  DisplayString (SIZE (0..30))
            ACCESS  read-only
            STATUS  mandatory
            DESCRIPTION
                " FPGA Version "
            ::= { cda6SystemInfoEntry 4 }

        cda6SystemInfoBank1Version    OBJECT-TYPE
            SYNTAX  DisplayString (SIZE (0..30))
            ACCESS  read-only
            STATUS  mandatory
            DESCRIPTION
                " Bank-1 Version "
            ::= { cda6SystemInfoEntry 5 }

        cda6SystemInfoBank2Version    OBJECT-TYPE
            SYNTAX  DisplayString (SIZE (0..30))
            ACCESS  read-only
            STATUS  mandatory
            DESCRIPTION
                " Bank-2 Version "
            ::= { cda6SystemInfoEntry 6}

        cda6SystemInfoActiveBank    OBJECT-TYPE
            SYNTAX  INTEGER{
                    bank-1(1),
                    bank-2(2)
                }
            ACCESS  read-only
            STATUS  mandatory
            DESCRIPTION
                " Active Bank 1/2 "
            ::= { cda6SystemInfoEntry 7 }


        cda6TotalCard   OBJECT-TYPE
            SYNTAX  INTEGER
            ACCESS  read-only
            STATUS  mandatory
            DESCRIPTION
                " Total cards of CDA6 "
            ::= { cda6-card 100 }

--============================================================================--





--======================================================================--
--  trap MIB

        sysLocalTrap  TRAP-TYPE
            ENTERPRISE loop-O9500
            VARIABLES  {alarmQueueString,
                alarmQueueTimeStamp,
                alarmQueueSubrack,
                alarmQueueUnit,
                alarmQueueCardModel,
                alarmQueueRegModel,
                alarmQueuePortNum,
                alarmQueueVcChan,
                alarmQueueAlmNum,
                alarmQueueVC43STS31Type,
                alarmQueueTU1xVTxType,
                alarmQueueVC4STS3,
                alarmQueueVC3TUG3,
                alarmQueueTUG2VTG,
                alarmQueueTU1xVTx,
                alarmQueueStatus,
                alarmQueueSeverity }
            DESCRIPTION
                "Local alarm trap"
            ::= 3

        sysXcuLedTrap  TRAP-TYPE
            ENTERPRISE loop-O9500
            VARIABLES  {ccLedIndex,
                ccLedName,
                ccLedColor }
            DESCRIPTION
                "XCU LED color change trap"
            ::= 4

        sysSeverityChangeTrap  TRAP-TYPE
            ENTERPRISE loop-O9500
            VARIABLES  { ccSysSeverityLevel }
            DESCRIPTION
                "Highest sdh/sonet/tributary severity alarm change trap,
                including PI-LOS,MS-AIS,
                AU-LOP..,HP-PLM...,
                TU-LOP,TU-AIS,..,
                E1-LOS,E1-AIS,etc.."
            ::= 5

        sysCriticalAlmActiveTrap  TRAP-TYPE
            ENTERPRISE loop-O9500
            VARIABLES  {alarmQueueString,
                alarmQueueTimeStamp,
                alarmQueueSubrack,
                alarmQueueUnit,
                alarmQueueCardModel,
                alarmQueueRegModel,
                alarmQueuePortNum,
                alarmQueueVcChan,
                alarmQueueAlmNum,
                alarmQueueVC43STS31Type,
                alarmQueueTU1xVTxType,
                alarmQueueVC4STS3,
                alarmQueueVC3TUG3,
                alarmQueueTUG2VTG,
                alarmQueueTU1xVTx,
                alarmQueueStatus,
                alarmQueueSeverity }
            DESCRIPTION
                "Critical alarm active trap"
            ::= 6

        sysCriticalAlmClearedTrap  TRAP-TYPE
            ENTERPRISE loop-O9500
            VARIABLES  {alarmQueueString,
                alarmQueueTimeStamp,
                alarmQueueSubrack,
                alarmQueueUnit,
                alarmQueueCardModel,
                alarmQueueRegModel,
                alarmQueuePortNum,
                alarmQueueVcChan,
                alarmQueueAlmNum,
                alarmQueueVC43STS31Type,
                alarmQueueTU1xVTxType,
                alarmQueueVC4STS3,
                alarmQueueVC3TUG3,
                alarmQueueTUG2VTG,
                alarmQueueTU1xVTx,
                alarmQueueStatus,
                alarmQueueSeverity }
            DESCRIPTION
                "Critical alarm clear trap"
            ::= 7

        sysMajorAlmActiveTrap  TRAP-TYPE
            ENTERPRISE loop-O9500
            VARIABLES  {alarmQueueString,
                alarmQueueTimeStamp,
                alarmQueueSubrack,
                alarmQueueUnit,
                alarmQueueCardModel,
                alarmQueueRegModel,
                alarmQueuePortNum,
                alarmQueueVcChan,
                alarmQueueAlmNum,
                alarmQueueVC43STS31Type,
                alarmQueueTU1xVTxType,
                alarmQueueVC4STS3,
                alarmQueueVC3TUG3,
                alarmQueueTUG2VTG,
                alarmQueueTU1xVTx,
                alarmQueueStatus,
                alarmQueueSeverity }
            DESCRIPTION
                "Major alarm active trap"
            ::= 8

        sysMajorAlmClearedTrap  TRAP-TYPE
            ENTERPRISE loop-O9500
            VARIABLES  {alarmQueueString,
                alarmQueueTimeStamp,
                alarmQueueSubrack,
                alarmQueueUnit,
                alarmQueueCardModel,
                alarmQueueRegModel,
                alarmQueuePortNum,
                alarmQueueVcChan,
                alarmQueueAlmNum,
                alarmQueueVC43STS31Type,
                alarmQueueTU1xVTxType,
                alarmQueueVC4STS3,
                alarmQueueVC3TUG3,
                alarmQueueTUG2VTG,
                alarmQueueTU1xVTx,
                alarmQueueStatus,
                alarmQueueSeverity }
            DESCRIPTION
                "Major alarm clear trap"
            ::= 9

        sysMinorAlmActiveTrap  TRAP-TYPE
            ENTERPRISE loop-O9500
            VARIABLES  {alarmQueueString,
                alarmQueueTimeStamp,
                alarmQueueSubrack,
                alarmQueueUnit,
                alarmQueueCardModel,
                alarmQueueRegModel,
                alarmQueuePortNum,
                alarmQueueVcChan,
                alarmQueueAlmNum,
                alarmQueueVC43STS31Type,
                alarmQueueTU1xVTxType,
                alarmQueueVC4STS3,
                alarmQueueVC3TUG3,
                alarmQueueTUG2VTG,
                alarmQueueTU1xVTx,
                alarmQueueStatus,
                alarmQueueSeverity }
            DESCRIPTION
                "Minor alarm active trap"
            ::= 10

        sysMinorAlmClearedTrap  TRAP-TYPE
            ENTERPRISE loop-O9500
            VARIABLES  {alarmQueueString,
                alarmQueueTimeStamp,
                alarmQueueSubrack,
                alarmQueueUnit,
                alarmQueueCardModel,
                alarmQueueRegModel,
                alarmQueuePortNum,
                alarmQueueVcChan,
                alarmQueueAlmNum,
                alarmQueueVC43STS31Type,
                alarmQueueTU1xVTxType,
                alarmQueueVC4STS3,
                alarmQueueVC3TUG3,
                alarmQueueTUG2VTG,
                alarmQueueTU1xVTx,
                alarmQueueStatus,
                alarmQueueSeverity }
            DESCRIPTION
                "Minor alarm clear trap"
            ::= 11

        sysInfoActiveTrap  TRAP-TYPE
            ENTERPRISE loop-O9500
            VARIABLES  {alarmQueueString,
                alarmQueueTimeStamp,
                alarmQueueSubrack,
                alarmQueueUnit,
                alarmQueueCardModel,
                alarmQueueRegModel,
                alarmQueuePortNum,
                alarmQueueVcChan,
                alarmQueueAlmNum,
                alarmQueueVC43STS31Type,
                alarmQueueTU1xVTxType,
                alarmQueueVC4STS3,
                alarmQueueVC3TUG3,
                alarmQueueTUG2VTG,
                alarmQueueTU1xVTx,
                alarmQueueStatus,
                alarmQueueSeverity }
            DESCRIPTION
                "Info active trap"
            ::= 12

        sysInfoClearedTrap  TRAP-TYPE
            ENTERPRISE loop-O9500
            VARIABLES  {alarmQueueString,
                alarmQueueTimeStamp,
                alarmQueueSubrack,
                alarmQueueUnit,
                alarmQueueCardModel,
                alarmQueueRegModel,
                alarmQueuePortNum,
                alarmQueueVcChan,
                alarmQueueAlmNum,
                alarmQueueVC43STS31Type,
                alarmQueueTU1xVTxType,
                alarmQueueVC4STS3,
                alarmQueueVC3TUG3,
                alarmQueueTUG2VTG,
                alarmQueueTU1xVTx,
                alarmQueueStatus,
                alarmQueueSeverity }
            DESCRIPTION
                "Info clear trap"
            ::= 13


--======================================================================--
--  notification MIB

    sysNotification     OBJECT IDENTIFIER ::= { loop-O9500 0 }

        sysLocalTrap3  NOTIFICATION-TYPE
            OBJECTS {
                alarmQueueString,
                alarmQueueTimeStamp,
                alarmQueueSubrack,
                alarmQueueUnit,
                alarmQueueCardModel,
                alarmQueueRegModel,
                alarmQueuePortNum,
                alarmQueueVcChan,
                alarmQueueAlmNum,
                alarmQueueVC43STS31Type,
                alarmQueueTU1xVTxType,
                alarmQueueVC4STS3,
                alarmQueueVC3TUG3,
                alarmQueueTUG2VTG,
                alarmQueueTU1xVTx,
                alarmQueueStatus,
                alarmQueueSeverity }
            STATUS current
            DESCRIPTION
                "Local alarm trap"
            ::= {  sysNotification  103  }

        sysXcuLedTrap3  NOTIFICATION-TYPE
            OBJECTS  { ccLedIndex,
                ccLedName,
                ccLedColor }
            STATUS current
            DESCRIPTION
                "XCU LED color change trap"
            ::= {  sysNotification  104  }

        sysSeverityChangeTrap3  NOTIFICATION-TYPE
            OBJECTS  { ccSysSeverityLevel }
            STATUS current
            DESCRIPTION
                "Highest sdh/sonet/tributary severity alarm change trap,
                including PI-LOS,MS-AIS,
                AU-LOP..,HP-PLM...,
                TU-LOP,TU-AIS,..,
                E1-LOS,E1-AIS,etc.."
            ::= {  sysNotification  105  }


--======================================================================--
        END
